module ciena-ui {
  namespace "urn:ciena:params:xml:ns:yang:ciena-ui";
  prefix ui;

  import ciena-publish {
    prefix publish;
  }

  organization
    "Ciena";
  contact
    "";
  description
    "UI";

  revision 2015-04-07 {
    description
      "Added last-modified and etag meta-data to root container.";
    reference
      "";
  }

  extension ui-name {
    argument name;
    description
      "Name to use in external UIs.";
  }

  publish:enabled "false";
}
