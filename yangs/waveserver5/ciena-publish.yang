module ciena-publish {
  namespace "urn:ciena:params:xml:ns:yang:ciena-publish";
  prefix publish;

  organization
    "Ciena Corporation";
  contact
    "Web URL: http://www.ciena.com/
     Postal:  7035 Ridge Road
             Hanover, Maryland 21076
             U.S.A.
     Phone:   +1 800-921-1144
     Fax:     +1 410-694-5750";
  description
    "This module is used to block publishing of internal modules";

  revision 2016-12-12 {
    description
      "Created publishing control module";
    reference
      "";
  }

  extension enabled {
    argument value;
    description
      "A boolean value of \"true\" of \"false\", false is default.  If used
       within a module, and the value is not \"true\", then the module
       will not be published for non-internal usage.";
  }

  publish:enabled "false";
}
