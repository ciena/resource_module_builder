module ciena-common-version {
  namespace "urn:ciena:params:xml:ns:yang:ciena-common-version";
  prefix version;

  organization
    "Ciena";
  contact
    "";
  description
    "Holds definitions and extensions for semantic versioning.";

  revision 2020-06-19 {
    description
      "Adding a new version grouping";
  }
  revision 2019-04-08 {
    description
      "Initial revision for semantic versioning";
  }

  extension version {
    argument version;
    description
      "This is the container that holds the Semantic versioning for an element.";
  }

  extension string {
    argument value;
    description
      "String represenation of version field.  Must be in M.m.p
       format, which M = major, m = minor, and p = patch version";
  }

  extension major {
    argument value;
    description
      "Major revision for the module.  Changes to this indicate a
       non-backwards compatible change.  Changes must be incremental.";
  }

  extension minor {
    argument value;
    description
      "Minor revision for the module.  Changes to this indicate a
       backwards compatible change.  Changes must be incremental.";
  }

  extension patch {
    argument value;
    description
      "Patch revision for the module.  Changes to this indicate a
       internal change to implementaiton and no API change.
       Changes must be incremental.";
  }

  grouping version {
    leaf string {
      type string;
    }

    container numeric {
      leaf major {
        type uint32;
      }

      leaf minor {
        type uint32;
      }

      leaf patch {
        type uint32;
      }
    }
  }
}
