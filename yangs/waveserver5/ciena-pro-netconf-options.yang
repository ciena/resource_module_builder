module ciena-pro-netconf-options {
  namespace "urn:ciena:params:xml:ns:yang:ciena-pro-netconf-options";
  prefix ciena-pro-netconf-options;

  import ciena-common-version {
    prefix version;
  }

  organization
    "Ciena Corporation";
  contact
    "Web URL: http://www.ciena.com/
     Postal:  7035 Ridge Road
             Hanover, Maryland 21076
             U.S.A.
     Phone:   +1 800-921-1144
     Fax:     +1 410-694-5750";
  description
    "This module describes Netconf deployment wide options.";

  revision 2019-10-17 {
    version:version "version" {
      version:string "1.0.0";
    }
    description
      "Initial revision.";
  }

  container netconf-options {
    leaf client-schema-dir {
      type string;
      description
        "Directory where netconf client stores default schemas and
         schemas retrieved from server.
         If unset, default is <install-prefix>/share/libnetconf2";
    }

    leaf server-validation {
      type boolean;
      default "true";
      description
        "Flag to enable or disable northbound validation on the server";
    }
  }
}
