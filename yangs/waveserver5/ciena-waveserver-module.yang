module ciena-waveserver-module {
  namespace "urn:ciena:params:xml:ns:yang:ciena-ws:ciena-waveserver-module";
  prefix mod;

  import yuma-ncx {
    prefix ncx;
  }

  import ciena-waveserver-typedefs {
    prefix cienawstypes;
  }

  import ciena-waveserver-chassis {
    prefix ciena-ws-chassis;
  }

  import ciena-waveserver-xcvr {
    prefix xcvr;
  }

  import ciena-ui {
    prefix ui;
  }

  organization
    "Ciena Corporation";
  contact
    "Web URL: http://www.ciena.com/
     Postal:  7035 Ridge Road
             Hanover, Maryland 21076
             U.S.A.
     Phone:   +1 800-921-1144
     Fax:     +1 410-694-5750";
  description
    "This module defines Module data for the Waveserver Platform.";

  revision 2021-08-28 {
    description
      "Added 'motr-400-2-12' enum value to 'module-type' typedef value for the WL5e 12x MOTR.";
    reference
      "Waveserver OS R2.2 user's guide.";
  }
  revision 2021-04-28 {
    description
      "Added 'motr-400-1-8' enum value to 'module-type' typedef value for WSAi 1x800 MOTR.
       Added output container to module-restart rpcs.
       Added 'motr-dco-400-3-12' enum value to 'module-type' typedef value for WS5 SHIM module.
       Replaced module-operational-state value 'shutting-down' with 'restarting'.";
    reference
      "Waveserver OS R2.1 user's guide.";
  }
  revision 2020-06-22 {
    description
      "Added 'mated' and 'mated-oducn-regen' enum values to 'module-mode' typedef.";
    reference
      "Waveserver OS R2.0.2 user's guide.";
  }
  revision 2020-02-27 {
    description
      "Added 'motr-400-2-16' enum value to 'module-type' typedef.
       Added leaf 'width' to 'properties' container.";
    reference
      "Waveserver OS R2.0 user's guide.";
  }
  revision 2018-10-08 {
    description
      "Added 'cmd-10', 'motr-100-2p', and 'motr-agg-1' module type enum values.";
    reference
      "Waveserver Ai R1.4 user's guide.";
  }
  revision 2018-07-25 {
    description
      "Added 'reserved-1' module type enum value.";
    reference
      "Internal use only (Ai R1.3-CP).";
  }
  revision 2018-07-19 {
    description
      "Added 'motr-crypto' module type support.";
    reference
      "Waveserver Ai R1.3 user's guide.";
  }
  revision 2018-05-07 {
    description
      "Added 'motr-100-1' module type support.
       Specified module type as a create-only attribute.
       Added 'properties' container and 'mode' leaf to the modules list.";
    reference
      "Waveserver Ai R1.2 user's guide.";
  }
  revision 2017-12-12 {
    description
      "Added 'cmd-4' module type support.
       Renamed 'faulted' operational-state to 'fault' and add 'down' state.
       Renamed 'motr-8x100' enum to 'motr-100-2'.";
    reference
      "Waveserver Ai R1.1 user's guide.";
  }
  revision 2017-09-05 {
    description
      "Waveserver Platform Data Model
       Initial revision.";
    reference
      "Waveserver Ai R1.0 user's guide.";
  }

  typedef module-type {
    type enumeration {
      enum "unknown" {
        description
          "Unknown module type.";
      }
      enum "filler" {
        description
          "Filler card. Operational only, cannot be used for user create.";
      }
      enum "motr-100-2" {
        description
          "Waveserver Ai Chassis MOTR service module with 2 WaveLogic Ai line ports
           and 8 100G capable client ports.";
      }
      enum "cmd-4" {
        description
          "Waveserver Ai Chassis 4-channel mux/demux passive photonics module.";
      }
      enum "motr-100-1" {
        description
          "Waveserver Ai Chassis MOTR service module with 1 WaveLogic Ai line port
           and 4 100G capable client ports.";
      }
      enum "motr-crypto" {
        description
          "Waveserver Ai Chassis MOTR service module with 1 WaveLogic Ai line port
           and 4 100G capable client ports, and supports datapath encryption.";
      }
      enum "cmd-10" {
        description
          "Waveserver Ai Chassis 10-channel mux/demux photonics module with OSC.";
      }
      enum "motr-100-2p" {
        description
          "Waveserver Ai Chassis MOTR service module with 2 WaveLogic Ai line ports
           with integrated OPS and 8 100G capable client ports.";
      }
      enum "motr-agg-1" {
        description
          "Waveserver Ai Chassis MOTR service module with 1 WaveLogic Ai line port
           and 10 client ports capable of 4x10G, 40G, or 100G signals.";
      }
      enum "motr-400-2-16" {
        description
          "Waveserver 5 Chassis MOTR service module with 2 WaveLogic 5e line ports,
           4 client ports capable of 400G or 100G signals, and 12 client ports
           capable of 100G signals.";
      }
      enum "motr-400-1-8" {
        description
          "Waveserver Ai Chassis MOTR service module with 1 WaveLogic 5e line port,
           2 client ports capabile of 400G or 100G signals, and 6 client ports
           capable of 100G signals.";
      }
      enum "motr-dco-400-3-12" {
        description
          "Waveserver 5 Chassis MOTR service module with 3 400ZR DCO line pluggables,
           3 client ports capable of 400G or 4x100G signals, and 12 client ports
           capable of 100G signals.";
      }
      enum "motr-400-2-12" {
        description
          "Waveserver 5 Chassis MOTR service module with 2 WaveLogic 5e line ports,
           4 client ports capable of 400G or 100G signals, and 8 client ports
           capable of 100G signals.";
      }
      enum "reserved-1" {
        value 1000;
        description
          "Reserved for internal use.";
      }
    }
    description
      "Module type.";
  }

  typedef module-mode {
    type enumeration {
      enum "none" {
        description
          "Default module configuration mode: Standalone line terminal";
      }
      enum "oducn-regen" {
        description
          "Standalone line regen with external FOIC client hand-off between two modems.";
      }
      enum "mated" {
        description
          "Mated line terminal.";
      }
      enum "mated-oducn-regen" {
        description
          "Mated line regen with external FOIC client hand-off between two modules.";
      }
    }
    description
      "Module configuration mode.";
  }

  typedef module-width {
    type enumeration {
      enum "single" {
        description
          "Module is single width.";
      }
      enum "double" {
        description
          "Module is double width.";
      }
    }
    description
      "Module width single or double.";
  }

  typedef module-operational-state {
    type enumeration {
      enum "unequipped" {
        value 0;
        description
          "Module is not detected.";
      }
      enum "deprovisioned" {
        value 1;
        description
          "Module is detected but uninitialized.";
      }
      enum "initializing" {
        value 2;
        description
          "Module initialization started.";
      }
      enum "up" {
        value 3;
        description
          "Module is up/operational.";
      }
      enum "fault" {
        value 4;
        description
          "Module is faulted.";
      }
      enum "shutdown" {
        value 5;
        description
          "Module is shutdown/powered off.";
      }
      enum "restarting" {
        value 6;
        description
          "Module is restarting.";
      }
      enum "unsupported" {
        value 7;
        description
          "Module type is not supported.";
      }
      enum "mismatched" {
        value 8;
        description
          "Detected module type does not match provisioned module type.";
      }
      enum "down" {
        value 9;
        description
          "Module is down/disabled.";
      }
    }
    description
      "Module operational state.";
  }

  container waveserver-modules {
    ui:ui-name "Modules";
    description
      "Waveserver service module configuration data and operational data.";
    list modules {
      ui:ui-name "Module List";
      key "module-id";
      description
        "Module list.";
      leaf module-id {
        ui:ui-name "Module ID";
        type cienawstypes:name-string;
        mandatory true;
        description
          "Unique access identifier string of the Module, which may just be a slot number (e.g. '1'). Key value for the Module list. Read-only attribute.";
      }

      container id {
        ui:ui-name "Module ID";
        description
          "ID information of this Module instance.";
        leaf type {
          ui:ui-name "Module Type";
          ncx:user-write "create";
          type module-type;
          mandatory true;
          description
            "The service module type. Must be specified on creation, and cannot be modified.";
        }

        leaf label {
          ui:ui-name "Module User Label";
          type cienawstypes:description-string;
          description
            "The user-specified label string for this module.";
        }

        uses ciena-ws-chassis:device-id-group;
      }

      container state {
        ui:ui-name "Module State";
        description
          "State information of this Module instance.";
        leaf admin-state {
          ui:ui-name "Module Admin State";
          type cienawstypes:enabled-disabled-enum;
          description
            "Whether Admin State is enabled or disabled for this Module.";
        }

        leaf operational-state {
          ui:ui-name "Module Operational State";
          type module-operational-state;
          config false;
          description
            "Operational state of this Module.";
        }

        leaf last-restart {
          ui:ui-name "Last Restart";
          type cienawstypes:string-maxl-32;
          config false;
          description
            "Date and time of last restart, in 'YYYY-MM-DDTHH:MM:SS[+|-]hh:mm'
             format, or omitted if not applicable or unavailable.

             The string format follows IETF yang date-and-time specifications, compliant
             with RFC-6991. The base date and time portion of the string represents
             Coordinated Universal Time (UTC), and a non-zero hh:mm offset suffix indicates the
             system-configured local timezone offset at the time the event was recorded, and not
             necessarily when it was retrieved.

             When system timezone is set to UTC or no time-offset value is provisioned,
             the '+00:00' suffix will be used to indicate UTC time with no local offset.";
          reference
            "RFC 3339: Date and Time on the Internet: Timestamps
             RFC 6991: Common Yang Data Types";
        }

        leaf last-restart-reason {
          ui:ui-name "Last Restart Reason";
          type cienawstypes:restart-reason;
          config false;
          description
            "Cause for the last restart.";
        }

        leaf uptime {
          ui:ui-name "Module Uptime";
          type cienawstypes:string-maxl-32;
          config false;
          description
            "The time since last restart of the module, in the format of a human
             readable string. e.g '041d 11h 29m 53s', or 'N/A' if unavailable.";
        }
      }

      container properties {
        ui:ui-name "Module Properties";
        description
          "Configuration properties of this Module instance.";
        leaf mode {
          ui:ui-name "Module Mode";
          type module-mode;
          description
            "The module configuration mode.";
        }

        leaf width {
          ui:ui-name "Module Width";
          type module-width;
          config false;
          description
            "The module width single or double.";
        }
      }

      container subcomponents {
        ui:ui-name "Module Subcomponents";
        config false;
        description
          "Module subcomponent (XCVR) references.";
        leaf-list xcvrs {
          ui:ui-name "Module XCVR List";
          type leafref {
            path "/xcvr:waveserver-xcvrs/xcvr:xcvrs/xcvr:xcvr-id";
          }
          description
            "Module subcomponent (XCVR) reference list.";
        }
      }
    }
  }

  rpc waveserver-module-restart {
    description
      "Initiates a module warm restart.";
    input {
      leaf module-id {
        ui:ui-name "Module ID";
        type cienawstypes:name-string;
        mandatory true;
        description
          "Unique Module ID string.";
      }
    }

    output {
      leaf return-code {
        type uint32;
        description
          "return code: 0 is success; non-zero is failure";
      }

      leaf return-string {
        type cienawstypes:string-maxl-254;
        description
          "Return code description";
      }
    }
  }

  rpc waveserver-module-restart-cold {
    description
      "Initiates a module cold restart.";
    input {
      leaf module-id {
        ui:ui-name "Module ID";
        type cienawstypes:name-string;
        mandatory true;
        description
          "Unique Module ID string.";
      }
    }

    output {
      leaf return-code {
        type uint32;
        description
          "return code: 0 is success; non-zero is failure";
      }

      leaf return-string {
        type cienawstypes:string-maxl-254;
        description
          "Return code description";
      }
    }
  }
}
