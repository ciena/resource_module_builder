module ciena-pro-cpu {
  namespace "urn:ciena:params:xml:ns:yang:ciena-pro-cpu";
  prefix ciena-pro-cpu;

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's 6500r platform slot model";

  revision 2017-01-01 {
    description
      "Initial revision";
  }

  container cpu {
    list processes {
      key "id";
      config false;
      leaf id {
        type uint32;
      }

      leaf name {
        type string;
      }

      leaf cpu-usage {
        type decimal64 {
          fraction-digits 1;
        }
        units "percent";
      }

      leaf memory-percent {
        type decimal64 {
          fraction-digits 1;
        }
        units "percent";
      }

      leaf memory-usage {
        type string;
        units "kB";
      }
    }
  }
}
