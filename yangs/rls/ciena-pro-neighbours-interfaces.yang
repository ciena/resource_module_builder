module ciena-pro-neighbours-interfaces {
  namespace "urn:ciena:params:xml:ns:yang:ciena-pro-neighbours-interfaces";
  prefix neighbours-interfaces;

  import ciena-common-version {
    prefix ciena-common-version;
  }

  organization
    "Ciena Corporation";
  contact
    "Web URL: http://www.ciena.com/
     Postal:  7035 Ridge Road
              Hanover, Maryland 21076
              U.S.A.
     Phone:   +1 800-921-1144
     Fax:     +1 410-694-5750";
  description
    "This model is used to control and monitor LLDP interfaces.";

  revision 2021-08-10 {
    description
      "Initial revision added for RLS 2.5.";
    ciena-common-version:version "version" {
      ciena-common-version:string "1.0.0";
    }
  }

  container neighbour-setup {
    description
      "Element used for control and monitoring of the LLDP interface.";
    list excluded-interfaces {
      key "name";
      leaf name {
        type string;
        description
          "The name of the interface that will not be used to discover LLDP neighbours.";
      }
    }
  }
}
