module CIENA-6500R-INVENTORY-MIB {
  namespace "urn:ietf:params:xml:ns:yang:smiv2:CIENA-6500R-INVENTORY-MIB";
  prefix ciena-6500r-inventory;

  import CIENA-6500R-SLOTS-MIB {
    prefix ciena-6500r;
  }
  import CIENA-6500R-TYPES-MIB {
    prefix ciena-6500r-types;
  }
  import CIENA-PRO-TYPES-MIB {
    prefix ciena-pro;
  }
  import SNMPv2-TC {
    prefix smiv2;
  }

  organization
    "Ciena Corporation";
  contact
    "Web URL: http://www.ciena.com/
     Postal:  7035 Ridge Road
     Hanover, Maryland 21076
     U.S.A.
     Phone:   +1 800-921-1144
     Fax:     +1 410-694-5750";
  description
    "This modules describes inventory for the 6500r platform";

  revision 2021-11-22 {
    description
      "Added rlsInventoryPM.";
  }
  revision 2021-11-15 {
    description
      "Adding rlsInventoryNmcmons";
  }
  revision 2021-10-22 {
    description
      "[Revision added by libsmi due to a LAST-UPDATED clause.]";
  }
  revision 2021-10-22 {
    description
      "Added rlsInventoryLinks.";
  }
  revision 2020-09-30 {
    description
      "Initial revision.";
  }

  container rlsCircuitPack {
    list rlsCircuitPackEntry {
      config false;
      key "rlsCircuitPackSlotName";
      description
        "";
      leaf rlsCircuitPackSlotName {
        type ciena-pro:DisplayString32;
        config false;
        description
          "The name of the slot.";
      }
      leaf rlsCircuitPackPec {
        type ciena-6500r-types:PecCode;
        config false;
        description
          "Product equipment code.";
      }
      leaf rlsCircuitPackCtype {
        type ciena-pro:DisplayString64;
        config false;
        description
          "c-type.";
      }
      leaf rlsCircuitPackLabel {
        type ciena-pro:DisplayString64;
        config false;
        description
          "Operator identifier for equipment description. 64 Character Maximum.";
      }
      leaf rlsCircuitPackLowPower {
        type int32 {
          range "0..960";
        }
        config false;
        description
          "Low power (in W) for this card.";
      }
      leaf rlsCircuitPackMaxPower {
        type int32 {
          range "0..960";
        }
        config false;
        description
          "Maximum power (in W) for this card.";
      }
      leaf rlsCircuitPackAdminState {
        type ciena-6500r-types:AdminState;
        config false;
        description
          "Identify the administrative state.";
      }
      leaf rlsCircuitPackOperationalState {
        type enumeration {
          enum active {
            value 0;
          }
          enum idle {
            value 1;
          }
        }
        config false;
        description
          "operational state.";
      }
      leaf rlsCircuitPackSlotType {
        type enumeration {
          enum single {
            value 0;
          }
          enum doubleWide {
            value 1;
          }
          enum doubleHigh {
            value 2;
          }
          enum quad {
            value 3;
          }
          enum tripleHigh {
            value 4;
          }
        }
        config false;
        description
          "Card Slot type.";
      }
      leaf rlsCircuitPackType {
        type ciena-pro:DisplayString32;
        config false;
        description
          "The associated equipment family.";
      }
      leaf rlsCircuitPackFormFactor {
        type enumeration {
          enum backplane {
            value 0;
          }
          enum accessPanel {
            value 1;
          }
          enum ctm {
            value 2;
          }
          enum fan {
            value 3;
          }
          enum power {
            value 4;
          }
          enum i2c {
            value 5;
          }
          enum passive {
            value 6;
          }
          enum sfp {
            value 7;
          }
          enum sfpplus {
            value 8;
          }
          enum cfp {
            value 9;
          }
          enum cfp2 {
            value 10;
          }
          enum xfp {
            value 11;
          }
          enum qsfp {
            value 12;
          }
          enum qsfp28 {
            value 13;
          }
          enum ctmFrontPanel {
            value 14;
          }
          enum backplane300mm {
            value 15;
          }
        }
        config false;
        description
          "";
      }
      leaf rlsCircuitPackPowerType {
        type ciena-6500r-types:PowerEnum;
        config false;
        description
          "Power Input Module type, i.e. DC or AC.";
      }
      leaf rlsCircuitPackRamSize {
        type ciena-6500r-types:RamEnum;
        config false;
        description
          "RAM size, i.e. 8G or 16G.";
      }
      leaf rlsCircuitPackBandInfo {
        type ciena-6500r-types:BandOccupancy;
        config false;
        description
          "supported band types of the circuit-pack";
      }
      leaf rlsCircuitPackCctEncoding {
        type enumeration {
          enum none {
            value 0;
          }
          enum snBin {
            value 1;
          }
          enum xml {
            value 2;
          }
        }
        config false;
        description
          "Indicate how CCT is being encoded for the supported circuit-pack.";
      }
      leaf rlsCircuitPackDiagActive {
        type smiv2:TruthValue;
        config false;
        description
          "Active, carrying traffic.";
      }
      leaf rlsCircuitPackDiagFailed {
        type smiv2:TruthValue;
        config false;
        description
          "Card Failed.";
      }
      leaf rlsCircuitPackDiagHardwareSubsystemFailed {
        type smiv2:TruthValue;
        config false;
        description
          "Equipment hardware subsystem fail.";
      }
      leaf rlsCircuitPackDiagSoftwareSubsytemFailed {
        type smiv2:TruthValue;
        config false;
        description
          "Equipment software subsystem fail.";
      }
      leaf rlsCircuitPackDiagHiTempWarning {
        type smiv2:TruthValue;
        config false;
        description
          "High temperature warning.";
      }
      leaf rlsCircuitPackDiagHiTemp {
        type smiv2:TruthValue;
        config false;
        description
          "High temperature.";
      }
      leaf rlsCircuitPackHardwareRelease {
        type ciena-pro:DisplayString32;
        config false;
        description
          "Release Level.";
      }
      leaf rlsCircuitPackCommonLanguageEquipmentIndentifier {
        type ciena-pro:DisplayString32;
        config false;
        description
          "Common language equipment identifier.";
      }
      leaf rlsCircuitPackSerialNumber {
        type ciena-pro:DisplayString32;
        config false;
        description
          "Serial Number.";
      }
      leaf rlsCircuitPackManufacturingDate {
        type ciena-pro:DisplayString32;
        config false;
        description
          "Date of Manufacture, in the format: year-week of year (YYYY-MM-DD).";
      }
      leaf rlsCircuitPackAge {
        type ciena-pro:DisplayString16;
        config false;
        description
          "Cumulative in-service time elapsed since manufacture, in the format: days:hours:minutes:seconds (DDDD:HH:MM:00).";
      }
      leaf rlsCircuitPackUptime {
        type ciena-pro:DisplayString16;
        config false;
        description
          "Cumulative uptime since the unit was last restarted (warm or cold), in the format: days:hours:minutes:seconds (DDDD:HH:MM:SS).";
      }
      leaf rlsCircuitPackLastRestartType {
        type ciena-6500r-types:RestartType;
        config false;
        description
          "Last restart type reported by the card.";
      }
      leaf rlsCircuitPackCurrTemprature {
        type int32;
        config false;
        description
          "Current card temperature in celsius.";
      }
      leaf rlsCircuitPackAvgTemprature {
        type int32;
        config false;
        description
          "Average card temperature in celsius.";
      }
      leaf rlsCircuitPackFanSpeedValue {
        type int32;
        units "rpm";
        config false;
        description
          "Current fan speed value (units rpm).";
      }
      leaf rlsCircuitPackFanSpeedMeansurementType {
        type ciena-6500r-types:MeansurementType;
        config false;
        description
          "Flag to indicate if fan speed is measured, estimated or unknown.";
      }
      leaf rlsCircuitPackCurrPowerValue {
        type int32;
        units "W";
        config false;
        description
          "Current power value (units W).";
      }
      leaf rlsCircuitPackCurrPowerMeansurementType {
        type ciena-6500r-types:MeansurementType;
        config false;
        description
          "Flag to indicate if current power is measured, estimated or unknown.";
      }
      leaf rlsCircuitPackPoweredUpTime {
        type ciena-pro:DisplayString16;
        config false;
        description
          "Cumulative time since the card was last powered on, in the format: days:hours:minutes:seconds (DDDD:HH:MM:SS).";
      }
    }
  }
}
