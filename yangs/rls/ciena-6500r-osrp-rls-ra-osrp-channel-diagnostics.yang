module ciena-6500r-osrp-rls-ra-osrp-channel-diagnostics {
  namespace "urn:ciena:params:xml:ns:yang:ciena-6500r-osrp-rls-ra-osrp-channel-diagnostics";
  prefix osrp-channel-diagnostics;

  import ciena-osrp-common-channel-diagnostics {
    prefix common-channel-diagnostics;
  }
  import ciena-common-version {
    prefix ciena-common-version;
  }

  organization
    "Ciena Corporation";
  contact
    "Web URL: http://www.ciena.com
     Postal: Ciena India Pvt. Ltd.
     Sector 32, Plot 14,
     Gurgaon 122001,
     Haryana, India";
  description
    "This module describes Ciena's osrp-rls-ra end-to-end channel diagnostics data.";

  revision 2021-10-14 {
    description
      "Channel-diagnostics made config false.";
    ciena-common-version:string "1.0.1";
  }
  revision 2021-08-05 {
    description
      "Initial revision.";
    ciena-common-version:string "1.0.0";
  }

  container channel-diagnostics {
    uses common-channel-diagnostics:ccs-instance-common;
    config false;
  }
}
