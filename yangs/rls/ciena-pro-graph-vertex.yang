module ciena-pro-graph-vertex {
  yang-version 1.1;
  namespace "urn:ciena:params:xml:ns:yang:ciena-pro-graph-vertex";
  prefix graph-vertex;

  import ciena-common-version {
    prefix version;
  }

  import ciena-pro-graph-interface {
    prefix ciena-pro-graph-interface;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's graph vertex for the 6500r-Series platform";

  revision 2020-11-16 {
    version:version "version" {
      version:string "0.1.0";
    }
    description
      "RLS 2.3 Add downstream channel occupancy and channel";
  }
  revision 2020-08-20 {
    version:version "version" {
      version:string "0.0.0";
    }
    description
      "RLS 2.1 module creation";
  }

  grouping nmc {
    description
      "A channel";
    leaf center-freq {
      type uint32;
      description
        "Center frequency of the channel (in MHz)";
    }

    leaf spectral-width {
      type uint32;
      description
        "Spectral width of the channel (in MHz)";
    }
  }

  grouping ciena-pro-graph-vertex-mount {
    list vertex {
      key "name";
      leaf name {
        type string {
          length "1..200";
        }
        description
          "Vertex name";
      }

      leaf all-channel-fault {
        type boolean;
        description
          "True if all the channels are faulted (service affecting fault).";
      }

      leaf all-channel-degrade {
        type boolean;
        description
          "True if all the channels are degraded (potentially service affecting fault).";
      }

      leaf channel-occupancy {
        type ciena-pro-graph-interface:channel-bitmap-type;
        description
          "List of provisioned channels";
      }

      leaf channel-fault {
        type ciena-pro-graph-interface:channel-bitmap-type;
        description
          "List of service affected channels";
      }

      leaf channel-degrade {
        type ciena-pro-graph-interface:channel-bitmap-type;
        description
          "List of potentially service affected channels";
      }

      leaf upstream-all-channel-fault {
        type boolean;
        description
          "True if all the channels are faulted (service affecting fault).";
      }

      leaf upstream-all-channel-degrade {
        type boolean;
        description
          "True if all the channels are degraded (potentially service affecting fault).";
      }

      leaf upstream-channel-occupancy {
        type ciena-pro-graph-interface:channel-bitmap-type;
        description
          "List of provisioned channels";
      }

      leaf upstream-channel-fault {
        type ciena-pro-graph-interface:channel-bitmap-type;
        description
          "List of service affected channels";
      }

      leaf upstream-channel-degrade {
        type ciena-pro-graph-interface:channel-bitmap-type;
        description
          "List of potentially service affected channels";
      }

      list channel {
        key "center-freq";
        description
          "List of channels on the vertex";
        uses nmc;
      }

      leaf downstream-channel-occupancy {
        type ciena-pro-graph-interface:channel-bitmap-type;
        description
          "List of provisioned channels propagated from downstream";
      }

      list downstream-channel {
        key "center-freq";
        description
          "List of channels on the vertex propagated from downstream";
        uses nmc;
      }
    }
  }

  grouping ciena-pro-graph-vertex-mount-actions;

  uses ciena-pro-graph-vertex-mount;
}
