module ciena-pro-pm-types {
  namespace "urn:ciena:params:xml:ns:yang:ciena-pro-pm-types";
  prefix pm-types;

  import ciena-6500r-types {
    prefix types;
  }

  import ciena-common-version {
    prefix ciena-common-version;
  }

  import ciena-pro-link {
    prefix ciena-pro-link;
  }

  import ciena-pro-optical-types {
    prefix ciena-pro-optical-types;
  }

  organization
    "Ciena Corporation";
  contact
    "Web URL: http://www.ciena.com";
  description
    "This module describes Ciena's pm runtime objects for the 6500r platform";

  revision 2021-03-29 {
    ciena-common-version:string "1.2.0";
    description
      "Add new custom facility type";
  }
  revision 2020-11-24 {
    ciena-common-version:string "1.1.0";
    description
      "Add custom-interval and read-type";
  }
  revision 2020-08-18 {
    ciena-common-version:string "1.0.0";
    description
      "Add sdmon and nmcmon list";
  }
  revision 2019-08-22 {
    description
      "Initial revision";
  }

  typedef read-type {
    type enumeration {
      enum "read" {
        value 0;
      }
      enum "readreset" {
        value 1;
      }
      enum "readroll" {
        value 2;
      }
    }
    description
      "customize read type";
  }

  typedef custom-interval {
    type enumeration {
      enum "untimed" {
        value 0;
      }
      enum "15min" {
        value 1;
      }
    }
    description
      "Interval of PM bin";
  }

  typedef current-interval {
    type enumeration {
      enum "untimed" {
        value 0;
      }
      enum "15min" {
        value 1;
      }
      enum "1day" {
        value 2;
      }
    }
    description
      "Interval of PM bin";
  }

  typedef historical-interval {
    type enumeration {
      enum "15min" {
        value 1;
      }
      enum "1day" {
        value 2;
      }
    }
    description
      "Interval of PM bin";
  }

  typedef data-type {
    type union {
      type uint64;
      type int64;
      type decimal64 {
        fraction-digits 1;
      }
      type decimal64 {
        fraction-digits 2;
      }
    }
  }

  typedef validity {
    type enumeration {
      enum "notAvailable" {
        value 0;
      }
      enum "complete" {
        value 1;
      }
      enum "partial" {
        value 2;
      }
      enum "suspect" {
        value 3;
      }
    }
    description
      "Validity of data";
  }

  typedef montype {
    type enumeration {
      enum "opticalPower" {
        value 0;
        description
          "Optical Power (OPT-OTS, OPR-OTS). Total optical power";
      }
      enum "opticalPowerMin" {
        value 1;
        description
          "Optical Power (OPTMIN-OTS, OPRMIN-OTS). Total optical power";
      }
      enum "opticalPowerMax" {
        value 2;
        description
          "Optical Power (OPTMAX-OTS, OPRMAX-OTS). Total optical power";
      }
      enum "opticalPowerAvg" {
        value 3;
        description
          "Optical Power (OPTAVG-OTS, OPRAVG-OTS). Total optical power";
      }
      enum "opticalPowerOutput" {
        value 4;
        description
          "Optical Power Output (OPOUT-OTS, OPOUT-OMS, OPT-OCH). Total optical power includes Variable Optical Attenuator (VOA) attenuation";
      }
      enum "opticalPowerOutputMin" {
        value 5;
        description
          "Minimum Optical Power Output (OPOUTMIN-OTS). Total optical power includes Variable Optical Attenuator (VOA) attenuation";
      }
      enum "opticalPowerOutputMax" {
        value 6;
        description
          "Maximum Optical Power Output (OPOUTMAX-OTS). Total optical power includes Variable Optical Attenuator (VOA) attenuation";
      }
      enum "opticalPowerOutputAvg" {
        value 7;
        description
          "Average Optical Power Output (OPOUTAVG-OTS). Total optical power includes Variable Optical Attenuator (VOA) attenuation";
      }
      enum "opticalPowerInput" {
        value 8;
        description
          "Optical Power Input (OPIN-OTS, OPIN-OMS, OPR-OCH). Total optical power";
      }
      enum "opticalPowerInputMin" {
        value 9;
        description
          "Minimum Optical Power Input (OPINMIN-OTS). Total optical power";
      }
      enum "opticalPowerInputMax" {
        value 10;
        description
          "Maximum Optical Power Input (OPINMAX-OTS). Total optical power";
      }
      enum "opticalPowerInputAvg" {
        value 11;
        description
          "Average Optical Power Input (OPINAVG-OTS). Total optical power";
      }
      enum "opticalPowerOutputOSC" {
        value 12;
        description
          "OSC Optical Power Output (OPT-OSC). OSC Transmit power on MW port";
      }
      enum "opticalPowerOutputOSCMin" {
        value 13;
        description
          "Minimum OSC Optical Power Output (OPTMIN-OSC). OSC Transmit power on MW port";
      }
      enum "opticalPowerOutputOSCMax" {
        value 14;
        description
          "Maximum OSC Optical Power Output (OPTMAX-OSC). OSC Transmit power on MW port";
      }
      enum "opticalPowerOutputOSCAvg" {
        value 15;
        description
          "Average OSC Optical Power Output (OPTAVG-OSC). OSC Transmit power on MW port";
      }
      enum "opticalPowerInputOSC" {
        value 16;
        description
          "OSC Optical Power Input (OPR-OSC). OSC Receive power on MW port";
      }
      enum "opticalPowerInputOSCMin" {
        value 17;
        description
          "Minimum OSC Optical Power Input (OPRMIN-OSC). OSC Receive power on MW port";
      }
      enum "opticalPowerInputOSCMax" {
        value 18;
        description
          "Maximum OSC Optical Power Input (OPRMAX-OSC). OSC Receive power on MW port";
      }
      enum "opticalPowerInputOSCAvg" {
        value 19;
        description
          "Average OSC Optical Power Input (OPRAVG-OSC). OSC Receive power on MW port";
      }
      enum "opticalReturnLoss" {
        value 20;
        description
          "Optical Return Loss (ORL-OTS) - at MW port(s) B";
      }
      enum "opticalReturnLossMin" {
        value 21;
        description
          "Optical Return Loss (ORLMIN-OTS) - at MW port(s) B";
      }
      enum "opticalReturnLossMax" {
        value 22;
        description
          "Optical Return Loss (ORLMAX-OTS) - at MW port(s) B";
      }
      enum "opticalReturnLossAvg" {
        value 23;
        description
          "Optical Return Loss (ORLAVG-OTS) - at MW port(s) B";
      }
      enum "inputOpticalReturnLoss" {
        value 24;
        description
          "Input Optical Return Loss (ORLIN-OTS) - at MW port(s) B";
      }
      enum "inputOpticalReturnLossMin" {
        value 25;
        description
          "Input Optical Return Loss (ORLINMIN-OTS) - at MW port(s) B";
      }
      enum "inputOpticalReturnLossMax" {
        value 26;
        description
          "Input Optical Return Loss (ORLINMAX-OTS) - at MW port(s) B";
      }
      enum "inputOpticalReturnLossAvg" {
        value 27;
        description
          "InputOptical Return Loss (ORLINAVG-OTS) - at MW port(s) B";
      }
      enum "outputOpticalReturnLoss" {
        value 28;
        description
          "output Optical Return Loss (ORLOUT-OTS) - at MW port(s) B";
      }
      enum "outputOpticalReturnLossMin" {
        value 29;
        description
          "output Optical Return Loss (ORLOUTMIN-OTS) - at MW port(s) B";
      }
      enum "outputOpticalReturnLossMax" {
        value 30;
        description
          "output Optical Return Loss (ORLOUTMAX-OTS) - at MW port(s) B";
      }
      enum "outputOpticalReturnLossAvg" {
        value 31;
        description
          "output Optical Return Loss (ORLOUTAVG-OTS) - at MW port(s) B";
      }
      enum "gain" {
        value 32;
        description
          "gain - dB";
      }
      enum "gainTilt" {
        value 33;
        description
          "gain tilt - dB";
      }
      enum "link" {
        value 34;
        description
          "link data";
      }
      enum "opm" {
        value 35;
        description
          "opm data";
      }
    }
  }

  typedef qualifier {
    type enumeration {
      enum "current" {
        value 0;
        description
          "current montype";
      }
      enum "minimum" {
        value 1;
        description
          "minimum montype";
      }
      enum "maximum" {
        value 2;
        description
          "maximum montype";
      }
      enum "average" {
        value 3;
        description
          "average montype";
      }
    }
  }

  typedef location {
    type enumeration {
      enum "nearEnd" {
        value 0;
      }
      enum "farEnd" {
        value 1;
      }
    }
  }

  typedef direction {
    type enumeration {
      enum "tx" {
        value 0;
      }
      enum "rx" {
        value 1;
      }
      enum "bidirectional" {
        value 2;
      }
      enum "notApplicable" {
        value 3;
      }
    }
  }

  typedef signal-type {
    type enumeration {
      enum "NMCMON" {
        value 0;
      }
      enum "SDMON" {
        value 1;
      }
    }
  }

  grouping pm-measurement {
    description
      "Set of parameters related to a PM Measurement";
    leaf power-value {
      type decimal64 {
        fraction-digits 1;
        range "-150.. 150";
      }
      units "dBm";
      description
        "analog power";
    }

    leaf validity {
      type validity;
      mandatory false;
    }

    list sdmon {
      key "frequency";
      leaf frequency {
        type types:frequency;
        description
          "Center frequency";
      }

      leaf power {
        type types:power-dBm-1-precision;
        description
          "Power measured in a slice in dBm.";
      }
    }

    list nmcmon {
      key "center-frequency";
      leaf center-frequency {
        type types:frequency;
        description
          "Center frequency";
      }

      leaf spectral-width {
        type types:frequency;
        description
          "Spectral width.";
      }

      leaf power {
        type types:power-dBm-1-precision;
        description
          "Optical measured power for the channel";
      }

      leaf expected-power {
        type types:power-dBm-1-precision;
        description
          "Expected power for the channel";
      }
    }

    list loss {
      key "spectral-type loss-type";
      uses ciena-pro-link:loss-desc;

      uses ciena-pro-link:loss-value;
    }

    list slice {
      key "frequency";
      config false;
      leaf frequency {
        type ciena-pro-optical-types:frequency;
        config false;
        description
          "Center frequency";
      }

      leaf power {
        type ciena-pro-optical-types:power {
          range "-75..75.00";
        }
        units "dBm";
        config false;
        description
          "Power measured in an OPM slice in dBm.";
      }
    }
  }
}
