module ciena-common-test-ns {
  namespace "urn:ciena:params:xml:ns:yang:ciena-common-test-ns";
  prefix test-ns;

  include ciena-common-test-submodule;
  import ciena-common-test {
    prefix abc;
  }

  organization
    "Ciena Corporation";
  contact
    "Web URL: http://www.ciena.com";
  description
    "Test module to test namespace collisions.";

  revision 2023-10-20 {
    description
      "Changing container name to create a difference in deserialization with other red container in ciena-common-test";
  }
  revision 2020-09-14 {
    description
      "Adding in an identity defined in another module";
  }

  identity aes {
    base abc:crypto-alg;
  }

  container red {
    container different {
      uses abc_group;
    }
  }
}
