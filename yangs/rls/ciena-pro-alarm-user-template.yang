module ciena-pro-alarm-user-template {
  namespace "urn:ciena:params:xml:ns:yang:ciena-pro-alarm-user-template";
  prefix user-template;

  import ciena-common-version {
    prefix version;
  }

  import ciena-pro-alarm {
    prefix alarm;
  }

  import ciena-pro-alarm-template {
    prefix alarm-template;
  }

  organization
    "Ciena Corporation";
  contact
    "Web URL: http://www.ciena.com/
     Postal:  7035 Ridge Road
             Hanover, Maryland 21076
             U.S.A.
     Phone:   +1 800-921-1144
     Fax:     +1 410-694-5750";
  description
    "This module describes Ciena's alarm user template objects for the Pro platform";

  revision 2020-08-25 {
    version:version "version" {
      version:string "1.0.0";
    }
    description
      "Add externally visible alarm template sets, defined-alarms and changed-alarms.";
  }

  list defined-alarms {
    key "name";
    config false;
    description
      "List of alarm templates in the system as they will be used to generate
       active-alarm records, including all changes made by the user.";
    uses alarm-template:template-grouping;
  }

  list changed-alarms {
    key "name";
    description
      "List of edits/changes to the defined-alarms, limited to a maximum of
       one set of changes per user alarm template.";
    uses alarm-template:template-grouping;
  }
}
