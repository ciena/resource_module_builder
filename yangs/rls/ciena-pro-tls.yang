module ciena-pro-tls {
  namespace "urn:ciena:params:xml:ns:yang:ciena-pro-tls";
  prefix ciena-pro-tls;

  import ciena-common-version {
    prefix ciena-common-version;
  }

  organization
    "Ciena Corporation";
  contact
    "Web URL: http://www.ciena.com/
     Postal:  7035 Ridge Road
             Hanover, Maryland 21076
             U.S.A.
     Phone:   +1 800-921-1144
     Fax:     +1 410-694-5750";
  description
    "This module defines TLS functionality and support objects.";

  revision 2020-10-22 {
    ciena-common-version:string "0.1.0";
    description
      "Make model platform independent";
  }
  revision 2019-07-09 {
    description
      "Initial version";
  }

  typedef tls-version-base {
    type enumeration {
      enum "tls-1.2" {
        description
          "TLS Protocol Version 1.2.";
        reference
          "RFC 5246: The Transport Layer Security (TLS) Protocol
                     Version 1.2";
      }
    }
    description
      "Base typedef used to identify TLS protocol versions.";
  }

  typedef cipher-suite-base {
    type enumeration {
      enum "ecdhe-ecdsa-with-aes-256-gcm-sha384" {
        description
          "Cipher suite TLS_ECDHE_ECDSA_WITH_AES_256_GCM_SHA384.";
        reference
          "RFC 5289: TLS Elliptic Curve Cipher Suites with
                     SHA-256/384 and AES Galois Counter Mode (GCM)";
      }
      enum "ecdhe-rsa-with-aes-256-gcm-sha384" {
        description
          "Cipher suite TLS_ECDHE_RSA_WITH_AES_256_GCM_SHA384.";
        reference
          "RFC 5289: TLS Elliptic Curve Cipher Suites with
                     SHA-256/384 and AES Galois Counter Mode (GCM)";
      }
      enum "ecdhe-ecdsa-with-aes-128-gcm-sha256" {
        description
          "Cipher suite TLS_ECDHE_ECDSA_WITH_AES_128_GCM_SHA256.";
        reference
          "RFC 5289: TLS Elliptic Curve Cipher Suites with
                     SHA-256/384 and AES Galois Counter Mode (GCM)";
      }
      enum "ecdhe-rsa-with-aes-128-gcm-sha256" {
        description
          "Cipher suite TLS_ECDHE_RSA_WITH_AES_128_GCM_SHA256.";
        reference
          "RFC 5289: TLS Elliptic Curve Cipher Suites with
                     SHA-256/384 and AES Galois Counter Mode (GCM)";
      }
      enum "ecdhe-ecdsa-with-aes-256-cbc-sha384" {
        description
          "Cipher suite TLS_ECDHE_ECDSA_WITH_AES_256_CBC_SHA384.";
        reference
          "RFC 5289: TLS Elliptic Curve Cipher Suites with
                     SHA-256/384 and AES Galois Counter Mode (GCM)";
      }
      enum "ecdhe-rsa-with-aes-256-cbc-sha384" {
        description
          "Cipher suite TLS_ECDHE_RSA_WITH_AES_256_CBC_SHA384.";
        reference
          "RFC 5289: TLS Elliptic Curve Cipher Suites with
                     SHA-256/384 and AES Galois Counter Mode (GCM)";
      }
      enum "ecdhe-ecdsa-with-aes-128-cbc-sha256" {
        description
          "Cipher suite TLS_ECDHE_ECDSA_WITH_AES_128_CBC_SHA256.";
        reference
          "RFC 5289: TLS Elliptic Curve Cipher Suites with
                     SHA-256/384 and AES Galois Counter Mode (GCM)";
      }
      enum "ecdhe-rsa-with-aes-128-cbc-sha256" {
        description
          "Cipher suite TLS_ECDHE_RSA_WITH_AES_128_CBC_SHA256.";
        reference
          "RFC 5289: TLS Elliptic Curve Cipher Suites with
                     SHA-256/384 and AES Galois Counter Mode (GCM)";
      }
    }
    description
      "Base typedef used to identify TLS cipher suites.";
  }

  grouping hello-params-grouping {
    description
      "A reusable grouping for TLS hello message parameters.";
    reference
      "RFC 5246: The Transport Layer Security (TLS) Protocol
                 Version 1.2";
    container tls-versions {
      description
        "Parameters regarding TLS versions.";
      leaf-list tls-version {
        type tls-version-base;
        description
          "Acceptable TLS protocol versions.";
      }
    }

    container cipher-suites {
      description
        "Parameters regarding cipher suites.";
      leaf-list cipher-suite {
        type cipher-suite-base;
        min-elements 1;
        ordered-by user;
        description
          "Acceptable cipher suites in order of descending
           preference.  The configured host key algorithms should
           be compatible with the algorithm used by the configured
           private key.  Please see Section 5 of RFC XXXX for
           valid combinations.";
        reference
          "RFC XXXX: YANG Groupings for TLS Clients and TLS Servers";
      }
    }
  }

  container tls-server {
    config false;
    description
      "A reusable grouping for configuring a TLS servers without
       any consideration for how underlying TCP sessions are
       established.";
    uses hello-params-grouping;
  }
}
