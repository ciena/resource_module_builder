module ciena-6500r-plug-defaults {
  yang-version 1.1;
  namespace "urn:ciena:params:xml:ns:yang:ciena-6500r-plug-defaults";
  prefix ciena-6500r-plug-defaults;

  import ciena-6500r-types {
    prefix ciena-6500r-types;
  }

  import ciena-pro-frequencies {
    prefix ciena-pro-frequencies;
  }

  import ciena-common-version {
    prefix ciena-common-version;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's plug-defaults for the 6500r platform";

  revision 2019-05-21 {
    ciena-common-version:string "1.0.0";
    description
      "Expanding range greater than -35 in order to accept the sfp config data .";
  }
  revision 2017-10-01 {
    description
      "ciena 6500r Release 1.0";
  }

  grouping ciena-6500r-plug-defaults-mount {
    container plug-defaults {
      leaf frequency {
        type leafref {
          path "/ciena-pro-frequencies:freq-group/ciena-pro-frequencies:name";
        }
        description
          "Circuit-pack frequency";
      }

      container optical-power {
        leaf low-tx-power {
          type ciena-6500r-types:DECIMAL {
            range "-60 .. 60";
          }
          units "dbm";
          description
            "Low tx power (in dbm) for this circuit pack";
        }

        leaf max-tx-power {
          type ciena-6500r-types:DECIMAL {
            range "-60 .. 60";
          }
          units "dbm";
          description
            "Maximum tx power (in dbm) for this circuit pack";
        }

        leaf low-rx-power {
          type ciena-6500r-types:DECIMAL {
            range "-60 .. 60";
          }
          units "dbm";
          description
            "Low rx power (in dbm) for this circuit pack";
        }

        leaf max-rx-power {
          type ciena-6500r-types:DECIMAL {
            range "-60 .. 60";
          }
          units "dbm";
          description
            "Maximum rx power (in dbm) for this circuit pack";
        }

        leaf low-tx-mon-power {
          type ciena-6500r-types:DECIMAL {
            range "-60 .. 60";
          }
          units "dbm";
          description
            "Low tx monitor power (in dbm) for this circuit pack";
        }

        leaf max-tx-mon-power {
          type ciena-6500r-types:DECIMAL {
            range "-60 .. 60";
          }
          units "dbm";
          description
            "Maximum tx monitor power (in dbm) for this circuit pack";
        }

        leaf low-rx-mon-power {
          type ciena-6500r-types:DECIMAL {
            range "-60 .. 60";
          }
          units "dbm";
          description
            "Low rx monitor power (in dbm) for this circuit pack";
        }

        leaf max-rx-mon-power {
          type ciena-6500r-types:DECIMAL {
            range "-60 .. 60";
          }
          units "dbm";
          description
            "Maximum rx monitor power (in dbm) for this circuit pack";
        }
      }
    }
  }

  grouping ciena-6500r-plug-defaults-mount-actions;

  uses ciena-6500r-plug-defaults-mount;
}
