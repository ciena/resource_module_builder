module ciena-cc-debug {
  namespace "urn:ciena:params:xml:ns:yang:ciena-cc-debug";
  prefix cc-debug;

  import ciena-common-version {
    prefix ciena-common-version;
  }

  organization
    "Ciena Corporation";
  contact
    "Web URL: http://www.ciena.com";
  description
    "Cluster Controller (CC) - debug module";

  revision 2022-01-01 {
    description
      "Initial revision";
    ciena-common-version:string "1.0.0";
  }

  container cc-config {
    leaf mode {
      type enumeration {
        enum normal {
          value 1;
          description
            "Mode to be used when deployed on hardware. (Default)";
        }
        enum sim {
          value 2;
          description
            "Mode to be used when deployed on a simulator (bfc, wacsim, etc.).";
        }
      }
      default "normal";
      description
        "Operating mode of the control filter.";
    }
  }
}
