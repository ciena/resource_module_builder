module ciena-pro-dnss {
  namespace "urn:ciena:params:xml:ns:yang:ciena-pro-dnss";
  prefix ciena-pro-dnss;

  import ciena-6500r-types {
    prefix ciena-6500r-types;
  }

  import ietf-inet-types {
    prefix inet;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's 6500r platform dnss model";

  revision 2017-01-01 {
    description
      "Initial revision";
  }

  container dns {
    uses ciena-6500r-types:admin-state;

    leaf domain-name {
      type string {
        length "1..63";
      }
      description
        "Domain Name";
    }

    container config-state {
      leaf name-server {
        type enumeration {
          enum "Enabled" {
            description
              "Service is Enabled.";
          }
          enum "Disabled" {
            description
              "Service is Disabled.";
          }
        }
        description
          "Identify the name server state";
      }

      leaf domain-name {
        type enumeration {
          enum "Enabled" {
            description
              "Service is Enabled.";
          }
          enum "Disabled" {
            description
              "Service is Disabled.";
          }
        }
        description
          "Identify the domain name state";
      }
    }

    list dns-server {
      key "address";
      leaf address {
        type string {
          length "1..63";
        }
        description
          "dns server address";
      }

      uses ciena-6500r-types:admin-state;

      leaf operation-state {
        type enumeration {
          enum "Enabled" {
            description
              "Service is Enabled.";
          }
          enum "Disabled" {
            description
              "Service is Disabled.";
          }
        }
        description
          "Identify the operation state";
      }

      leaf priority {
        type ciena-6500r-types:INT {
          range "1..99";
        }
        default "1";
        description
          "Priority Number";
      }
    }
  }
}
