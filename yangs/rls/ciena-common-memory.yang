module ciena-common-memory {
  namespace "urn:ciena:params:xml:ns:yang:ciena-common-memory";
  prefix memory;

  import ciena-common-version {
    prefix version;
  }

  organization
    "Ciena Corporation";
  contact
    "Web URL: http://www.ciena.com/
     Postal:  7035 Ridge Road
             Hanover, Maryland 21076
             U.S.A.
     Phone:   +1 800-921-1144
     Fax:     +1 410-694-5750";
  description
    "Model to obtain memory releated information";

  revision 2023-07-05 {
    description
      "Added background-free option";
    version:version "version" {
      version:string "1.1.0";
    }
  }
  revision 2021-04-05 {
    description
      "Initial revision";
    version:version "version" {
      version:string "1.0.0";
    }
  }

  container memory-options {
    description
      "Used by depo to define default memory options";
    leaf trim-interval {
      description
        "interval in seconds, for calling malloc_trim() to free bloated memory";
      type uint32;
      units "s";
    }
    leaf status {
      config false;
      description
        "status of malloc_trim timer active, inactive, not-supported";
      type enumeration {
        enum not-supported {
          value 0;
        }
        enum active {
          value 1;
        }
        enum inactive {
          value 2;
        }
      }
    }
    leaf background-free {
      description
        "Flag that indicates if data trees should be freed in a background
         thread or inline.";
      type boolean;
      default "false";
    }
    leaf outstanding-frees {
      config false;
      description
        "Counter for the number of outstanding frees that need to occur";
      type uint64;
    }
    leaf background-ratio {
      config false;
      description
        "Percentage of frees that have been processed in the background";
      type uint8;
    }
  }
}
