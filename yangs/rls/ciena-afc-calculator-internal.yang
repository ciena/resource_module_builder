module ciena-afc-calculator-internal {
  yang-version 1.1;
  namespace "urn:ciena:params:xml:ns:yang:ciena-afc-calculator-internal";
  prefix afc-calculator-internal;

  import ciena-common-version {
    prefix ciena-common-version;
  }

  organization
    "Ciena Corporation";
  contact
    "dicksonw";
  description
    "afc-calculator-internal";

  revision 2023-07-14 {
    description
      "Add yang version";
    ciena-common-version:string "1.0.0";
  }
  revision 2023-02-07 {
    description
      "Add support for updater notification.";
    reference
      "None";
  }
  revision 2022-09-13 {
    description
      "Add distributed capability.";
    reference
      "None";
  }
  revision 2022-03-08 {
    description
      "Add incarnation number.";
    reference
      "None";
  }

  notification initiate-data-processing-internal {
    description
      "internal notification to asynchronously initiate data collection";
    leaf node-name {
      type string;
      description
        "Name of node where section is defined under";
    }
    leaf section-name {
      type string;
      description
        "Name of section";
    }
    leaf freq-idx {
      type uint32;
      description
        "freq index of job";
    }
    leaf span-idx {
      type uint32;
      description
        "span index of job";
    }
    leaf get-new-topology-data {
      type boolean;
      description
        "indicates if new data needs to be collected for topology data";
    }
  }

  notification initiate-update-internal {
    description
      "internal notification to asynchronously initiate updater job";
    leaf node-name {
      type string;
      description
        "Name of node where section is defined under";
    }
    leaf section-name {
      type string;
      description
        "Name of section";
    }
  }
}
