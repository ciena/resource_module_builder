module ciena-pro-security-options {
  namespace "urn:ciena:params:xml:ns:yang:ciena-pro-security-options";
  prefix ciena-pro-security-options;

  import ciena-common-version {
    prefix ciena-common-version;
  }

  organization
    "Ciena Corporation";
  contact
    "Web URL: http://www.ciena.com/
     Postal:  7035 Ridge Road
             Hanover, Maryland 21076
             U.S.A.
     Phone:   +1 800-921-1144
     Fax:     +1 410-694-5750";
  description
    "This module defines security options";

  revision 2023-01-12 {
    description
      "adding certificate-file-path leaf to security-options";
    ciena-common-version:string "1.1.0";
  }
  revision 2022-09-30 {
    description
      "Initial version of security-options";
    ciena-common-version:string "1.0.0";
  }

  container security-options {
    description
      "Security options for different products";
    leaf product-name {
      type string;
      description
        "This is the product name (O-NID, ELS, RLS, etc) to be printed in the banner (example string: Ciena O-NID)";
    }
    leaf certificate-file-path {
      type string {
        length "0..128";
      }
      description
        "This is the path where certificate files will be stored";
    }
  }
}
