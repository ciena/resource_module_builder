module ciena-pro-data-collector-debug {
  namespace "urn:ciena:params:xml:ns:yang:ciena-pro-data-collector-debug";
  prefix data-collector-debug;

  import ietf-inet-types {
    prefix ietf;
  }
  import ietf-yang-types {
    prefix ietf-yang;
  }
  import ciena-pro-data-collector {
    prefix data-collector;
  }
  import ciena-common-yang {
    prefix ciena-common-yang;
  }

  organization
    "Ciena Corporation";
  contact
    "Web URL: http://www.ciena.com/
     Postal:  7035 Ridge Road
              Hanover, Maryland 21076
              U.S.A.
     Phone:   +1 800-921-1144
     Fax:     +1 410-694-5750";
  description
    "This model captures debug RPCs for manipulating data collector.";

  revision 2020-04-07 {
    description
      "Added opm specific RPCs";
  }
  revision 2019-09-04 {
    description
      "Initial Revision";
  }

  rpc set-publish {
    input {
      leaf enabled {
        type boolean;
        description
          "Publishing state, TRUE will publish, FALSE will not";
      }
    }
    output {
      leaf result {
        type enumeration {
          enum success;
          enum failed;
        }
      }
    }
  }

  rpc set-cadence {
    input {
      leaf cadence {
        type uint32;
        description
          "The cadence we want data collector to run at in Miliseconds";
      }
    }
    output {
      leaf result {
        type enumeration {
          enum success;
          enum failed;
        }
      }
    }
  }

  rpc set-deadzone {
    input {
      leaf threshold {
        type decimal64 {
          fraction-digits 2;
          range "0.2 .. 60";
        }
        description
          "The deadzone we want to apply in dBm";
      }
      leaf enabled {
        type boolean;
        description
          "Deadzoning state, TRUE will deadzone, FALSE will not";
      }
    }
    output {
      leaf result {
        type enumeration {
          enum success;
          enum failed;
        }
      }
    }
  }

  rpc set-noise-floor {
    input {
      leaf threshold {
        type decimal64 {
          fraction-digits 2;
          range "-70 .. 60";
        }
        description
          "The noise floor we want to apply in dBm";
      }
      leaf enabled {
        type boolean;
        description
          "Noise floor state, TRUE will apply a noise floor, FALSE will not";
      }
    }
    output {
      leaf result {
        type enumeration {
          enum success;
          enum failed;
        }
      }
    }
  }

  rpc set-opm-deadzone {
    input {
      leaf threshold {
        type decimal64 {
          fraction-digits 2;
          range "0.2 .. 60";
        }
        description
          "The deadzone we want to apply in dBm";
      }
      leaf enabled {
        type boolean;
        description
          "Deadzoning state, TRUE will deadzone, FALSE will not";
      }
    }
    output {
      leaf result {
        type enumeration {
          enum success;
          enum failed;
        }
      }
    }
  }

  rpc set-opm-noise-floor {
    input {
      leaf threshold {
        type decimal64 {
          fraction-digits 2;
          range "-70 .. 60";
        }
        description
          "The noise floor we want to apply in dBm";
      }
      leaf enabled {
        type boolean;
        description
          "Noise floor state, TRUE will apply a noise floor, FALSE will not";
      }
    }
    output {
      leaf result {
        type enumeration {
          enum success;
          enum failed;
        }
      }
    }
  }

  rpc set-filter {
    input {
      leaf filter {
        type string {
          length "1..2048";
        }
        description
          "The filter we want to apply to snmp get requests";
      }
    }
    output {
      leaf result {
        type enumeration {
          enum success;
          enum failed;
        }
      }
    }
  }

  rpc dc-debug {
    description
      "Enables debug logs specific to certain areas";
    input {
      leaf trace {
        type enumeration {
          enum time {
            description
              "Enable/disable time diff logs.";
          }
        }
      }
      leaf enabled {
        type boolean;
        description
          "To enable or not to enable...";
      }
    }
    output {
      leaf result {
        type enumeration {
          enum success;
          enum failed;
        }
      }
    }
  }
}
