module CIENA-6500R-INVENTORY-OSCS-MIB {
  namespace "urn:ietf:params:xml:ns:yang:smiv2:CIENA-6500R-INVENTORY-OSCS-MIB";
  prefix ciena-6500r-inventory;

  import CIENA-6500R-INVENTORY-MIB {
    prefix ciena-6500r;
  }
  import CIENA-6500R-TYPES-MIB {
    prefix ciena-6500r-types;
  }
  import CIENA-PRO-TYPES-MIB {
    prefix ciena-pro;
  }
  import SNMPv2-TC {
    prefix smiv2;
  }

  organization
    "Ciena Corporation";
  contact
    "Web URL: http://www.ciena.com/
     Postal:  7035 Ridge Road
     Hanover, Maryland 21076
     U.S.A.
     Phone:   +1 800-921-1144
     Fax:    Inventory +1 410-694-5750";
  description
    "This modules describes Ciena's photonic OSC object.";

  revision 2021-09-30 {
    description
      "Initial revision.";
  }

  container cienaRlsInventoryOscsMIB {
    list rlsInventoryOscsEntry {
      config false;
      key "rlsInventoryOscsSlotName rlsInventoryOscsSubslotName
           rlsInventoryOscsName";
      description
        "";
      leaf rlsInventoryOscsSlotName {
        type ciena-pro:DisplayString32;
        config false;
        description
          "The name of the slot.";
      }
      leaf rlsInventoryOscsSubslotName {
        type ciena-pro:DisplayString32;
        config false;
        description
          "The name of the subslot.";
      }
      leaf rlsInventoryOscsName {
        type ciena-pro:DisplayString128;
        config false;
        description
          "OSC name.";
      }
      leaf rlsInventoryOscTXPower {
        type ciena-pro:DisplayString32;
        config false;
        description
          "tx-power in dB.";
      }
      leaf rlsInventoryOscRXPower {
        type ciena-pro:DisplayString32;
        config false;
        description
          "rx-power in dB.";
      }
    }
  }
}
