module ciena-6500r-voa {
  yang-version 1.1;
  namespace "urn:ciena:params:xml:ns:yang:ciena-6500r-voa";
  prefix voas;

  import ciena-6500r-types {
    prefix ciena-6500r-types;
  }

  import ciena-6500r-ports {
    prefix ports;
  }

  import ciena-common-version {
    prefix version;
  }

  import ciena-pro-voa {
    prefix ciena-pro-voa;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's voas object for the 6500r platform";

  revision 2020-09-08 {
    version:version "version" {
      version:string "1.1.3";
    }
    description
      "Use ciena-pro-voa";
  }
  revision 2020-06-30 {
    version:version "version" {
      version:string "1.0.3";
    }
    description
      "Fix version formating";
  }
  revision 2019-12-05 {
    version:version "version" {
      version:string "1.0.2";
    }
    description
      "Added baseine-target-loss
       Added baseine-time-stamp";
  }
  revision 2019-09-03 {
    version:version "version" {
      version:string "1.0.1";
    }
    description
      "Added parameter ranges";
  }
  revision 2019-05-10 {
    version:version "version" {
      version:string "1.0.0";
    }
    description
      "Added additional info for alarms";
  }
  revision 2018-01-30 {
    description
      "6500r Release 1.0";
  }

  grouping ciena-6500r-voa-mount {
    list voa {
      key "name";
      uses ciena-pro-voa:voa;

      leaf parent-link {
        type instance-identifier;
        description
          "parent-link identifier";
      }
    }
  }

  grouping ciena-6500r-voa-mount-actions;

  uses ciena-6500r-voa-mount;
}
