module ciena-6500r-remote-data {
  yang-version 1.1;
  namespace "urn:ciena:params:xml:ns:yang:ciena-6500r-remote-data";
  prefix ciena-6500r-remote-data;

  import ciena-common-yang {
    prefix yang;
  }

  import ciena-6500r-types {
    prefix ciena-6500r-types;
  }

  organization
    "Ciena Corporation";
  contact
    "Web URL: http://www.ciena.com/
     Postal:  7035 Ridge Road
              Hanover, Maryland 21076
              U.S.A.
     Phone:   +1 800-921-1144
     Fax:     +1 410-694-5750";
  description
    "This modules describes data on remote shelves accessible through the oms-topo-svc.";

  revision 2019-03-19 {
    description
      "Initial revision";
  }

  grouping ciena-6500r-remote-data-mount {
    list remote-data {
      key "data-name";
      config false;
      leaf data-name {
        type ciena-6500r-types:object-name;
        description
          "Name of remote data, ie Line In Port";
      }

      leaf instance-identifier {
        type string;
        description
          "Instance identifier for the data at the remote node";
      }

      leaf domain-name {
        type string;
        description
          "Remote domain name";
      }

      leaf service-name {
        type string;
        description
          "Remote service name";
      }

      anyxml data {
        description
          "Data from remote node";
      }
    }
  }

  grouping ciena-6500r-remote-data-mount-actions;

  uses ciena-6500r-remote-data-mount;
}
