module ciena-6500r-span-calibr-orch-private {
  yang-version 1.1;
  namespace "urn:ciena:params:xml:ns:yang:ciena-6500r-span-calibr-orch-private";
  prefix span-calibr-orch-private;

  import ciena-common-version {
    prefix ciena-common-version;
  }
  import ciena-common-yang {
    prefix ciena-common-yang;
  }

  organization
    "Ciena Corporation";
  contact
    "Web URL: http://www.ciena.com;
     Postal:  7035 Ridge Road
             Hanover, Maryland 21076
             U.S.A.
     Phone:   +1 800-921-1144
     Fax:     +1 410-694-5750";
  description
    "This module describes the private data for SCO Service";

  revision 2023-02-01 {
    description
      "Introduced new leaf upgrade-status";
    ciena-common-version:string "1.1.0";
  }
  revision 2022-09-14 {
    description
      "Initial version for SCO Private";
    ciena-common-version:string "1.0.0";
  }

  list sco-private {
    key "name";
    leaf name {
      type string;
      description
        "Name of the SCO this raw relates to";
    }
    leaf first-time {
      type boolean;
      description
        "Indicates if this SCO runs first time.
         That could be in such cases like after SLAT or it was provisioned
         It will be reset to FALSE after first calibration completed";
    }
    leaf upgrade-status {
      type boolean;
      description
        "Set to TRUE if that was upgrade from pre-3.0
         Will be reset back to FALSE when calibration for this SCO instance completed";
    }
  }
}
