module CIENA-6500R-INVENTORY-RAMANS-MIB {
  namespace "urn:ietf:params:xml:ns:yang:smiv2:CIENA-6500R-INVENTORY-RAMANS-MIB";
  prefix ciena-6500r-inventory;

  import CIENA-6500R-INVENTORY-MIB {
    prefix ciena-6500r;
  }
  import CIENA-6500R-TYPES-MIB {
    prefix ciena-6500r-types;
  }
  import CIENA-PRO-TYPES-MIB {
    prefix ciena-pro;
  }
  import SNMPv2-TC {
    prefix smiv2;
  }

  organization
    "Ciena Corporation";
  contact
    "Web URL: http://www.ciena.com/
     Postal:  7035 Ridge Road
     Hanover, Maryland 21076
     U.S.A.
     Phone:   +1 800-921-1144
     Fax:    Inventory +1 410-694-5750";
  description
    "This modules describes Ciena's photonic ramans object.";

  revision 2022-01-09 {
    description
      "Fix Raman Entry sequence numbers.";
  }
  revision 2021-09-30 {
    description
      "Initial revision.";
  }

  container cienaRlsInventoryRamansMIB {
    list rlsInventoryRamansEntry {
      config false;
      key "rlsInventoryRamansSlotName rlsInventoryRamansName";
      description
        "";
      leaf rlsInventoryRamansSlotName {
        type ciena-pro:DisplayString32;
        config false;
        description
          "The name of the slot.";
      }
      leaf rlsInventoryRamansName {
        type ciena-pro:DisplayString128;
        config false;
        description
          "Raman name.";
      }
      leaf rlsInventoryRamansPumpMode {
        type enumeration {
          enum shutoff {
            value 1;
          }
          enum normal {
            value 2;
          }
          enum bootstrap {
            value 3;
          }
        }
        config false;
        description
          "Operating State of the RAMAN.";
      }
      leaf rlsInventoryRamansTargetPower {
        type ciena-pro:DisplayString32;
        config false;
        description
          "Target Power in dB.";
      }
      leaf rlsInventoryRamansGainMode {
        type enumeration {
          enum provisioned {
            value 1;
          }
          enum recommended {
            value 2;
          }
          enum bootstrap {
            value 3;
          }
        }
        config false;
        description
          "Gain Mode of the RAMAN.";
      }
      leaf rlsInventoryRamansProvisionedGain {
        type ciena-pro:DisplayString32;
        config false;
        description
          "Provisioned Gain in dB.";
      }
    }
    config false;
    list rlsInventoryRamansPumpsEntry {
      config false;
      key "rlsInventoryRamansPumpsSlotName
           rlsInventoryRamansPumpsName
           rlsInventoryRamansPumpsIndex";
      description
        "";
      leaf rlsInventoryRamansPumpsSlotName {
        type ciena-pro:DisplayString32;
        config false;
        description
          "The name of the slot.";
      }
      leaf rlsInventoryRamansPumpsName {
        type ciena-pro:DisplayString128;
        config false;
        description
          "Raman name.";
      }
      leaf rlsInventoryRamansPumpsIndex {
        type ciena-pro:DisplayString32;
        config false;
        description
          "Ramans Pump Index.";
      }
      leaf rlsInventoryRamansPumpsPower {
        type ciena-pro:DisplayString32;
        config false;
        description
          "Pump Power in dB.";
      }
    }
  }
}
