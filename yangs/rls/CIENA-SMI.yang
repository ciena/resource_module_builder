module CIENA-SMI {
  namespace "urn:ietf:params:xml:ns:yang:smiv2:CIENA-SMI";
  prefix ciena-smi;

  organization
    "Ciena Corp.";
  contact
    "   Mib Meister
     7035 Ridge Road
     Hanover, Maryland 21076
     USA
     Phone:  +1 800 921 1144
     Email:  support@ciena.com";
  description
    "MIB Version: MIBS-CIENA-CES-XX-XX-XX-XXX.";

  revision 2023-01-27 {
    description
      "Updated for cienaOnid.";
  }
  revision 2021-06-25 {
    description
      "Updated for cienaEls.";
  }
  revision 2020-11-24 {
    description
      "Updated for cienaRls and cienaPro.";
  }
  revision 2017-06-07 {
    description
      "Updated contact info.";
  }
  revision 2015-07-15 {
    description
      "Updated for cienaGenericMIBs and cienaOpterametro.";
  }
  revision 2013-04-22 {
    description
      "Fixed miscellaneous spelling and description errors.";
  }
  revision 2012-12-26 {
    description
      "Fixed the revision and description minor errors.";
  }
  revision 2010-09-27 {
    description
      "Initial creation of MIB file structure for Ciena Packet Networking Products.";
  }
}
