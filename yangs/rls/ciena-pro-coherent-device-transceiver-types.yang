module ciena-pro-coherent-device-transceiver-types {
  namespace "urn:ciena:ns:yang:coherent-device-transceiver-types";
  prefix coherent-device-transceiver-types;

  import ciena-common-version {
    prefix version;
  }
  import ciena-pro-coherent-device-common-types {
    prefix coherent-device-common-types;
  }

  organization
    "Ciena Corporation";
  contact
    "Web URL: http://www.ciena.com/
     Postal:  7035 Ridge Road
              Hanover, Maryland 21076
              U.S.A.
     Phone:   +1 800-921-1144
     Fax:     +1 410-694-5750";
  description
    "Transceiver definitions for coherent devices.";

  revision 2024-01-01 {
    description
      "Initial version.";
    version:version "version" {
      version:string "1.0.0";
    }
    reference
      "1.0.0";
  }

  typedef transceiver-type-enum {
    type enumeration {
      enum unknown {
        description
          "Transceiver type is unknown.";
      }
      enum QSFP-DD {
        description
          "Transceiver type is QSFP-DD.";
      }
      enum CFP2-DCO {
        description
          "Transceiver type is CFP2-DCO.";
      }
      enum NIC-WL6e {
        description
          "Transceiver type is an integrated Network Interface Card.";
      }
    }
    description
      "Type to represent the form-factor of a transceiver.";
  }

  typedef transceiver-power-state-config-enum {
    type enumeration {
      enum automatic {
        description
          "Transceiver device power-state is determined by the system.";
      }
      enum low-power-mode {
        description
          "Transceiver device power-state is forced to be in low-power-mode.";
      }
    }
    description
      "Type to represent the administrative value of a transceiver's power-state.";
  }

  typedef transceiver-power-state-actual-enum {
    type enumeration {
      enum high-power-mode {
        description
          "Transceiver is powered-on and fully operational.";
      }
      enum low-power-mode {
        description
          "Transceiver is in low power mode.";
      }
      enum reset {
        description
          "Transceiver is powered-off.";
      }
    }
    description
      "Type to represent the operational/actual state of a transceiver's power-state.
       When disabled may be powered-off or in reset, or in low-power-mode. When enabled
       the device is in normal operation.";
  }

  grouping ciena-id-group {
    leaf ciena-item-number {
      type coherent-device-common-types:string12;
      config false;
      description
        "The Ciena Item Number or orderable product-code.";
    }
    leaf revision {
      type coherent-device-common-types:string32;
      config false;
      description
        "The hardware revision for a Ciena manufactured device.";
    }
    leaf description {
      type coherent-device-common-types:string255;
      config false;
      description
        "A description of the Ciena manufactured device.";
    }
    description
      "Grouping of data that represents the Ciena-specific identification information of
       a transceiver device. This group is only relevant for a Ciena manufactured device.";
  }

  grouping vendor-id-group {
    leaf name {
      type coherent-device-common-types:string32;
      description
        "The vendor name that produced this device.";
    }
    leaf part-number {
      type coherent-device-common-types:string32;
      description
        "The vendor part-number for this device.";
    }
    leaf revision {
      type coherent-device-common-types:string32;
      description
        "The vendor hardware revision for this device.";
    }
    leaf serial-number {
      type coherent-device-common-types:string32;
      description
        "The vendor serial-number for this device.";
    }
    leaf manufacture-date {
      type coherent-device-common-types:string16;
      description
        "The manufacture data for this device";
    }
    description
      "Grouping of common identification information for a transceiver device. This group
       only contains attributes that are relevant to all form-factors of device. Form-factor
       specific attributes are defined in other groupings.";
  }

  grouping transceiver-base-device-id-group {
    container ciena-id {
      uses ciena-id-group;
      description
        "Ciena specific device identification information. If the manufacturer is not Ciena,
         this container may be ommitted.";
    }
    container vendor-id {
      uses vendor-id-group;
      description
        "Common device identification information.";
    }
    description
      "Generic grouping of basic identification information for a transceiver device.
       This grouping only contains attributes that are relevant to all device types.
       Form-factor specific attributes are defined in other groupings and should be
       conditionally defined based on the specific device-type where this grouping is used.";
  }
}
