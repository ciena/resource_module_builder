module ciena-pro-comms-apps-mgr {
  namespace "urn:ciena:params:xml:ns:yang:ciena-pro-comms-apps-mgr";
  prefix ciena-pro-comms-apps-mgr;

  import ciena-common-version {
    prefix ciena-common-version;
  }

  import ciena-common-yang {
    prefix ciena-common-yang;
  }

  organization
    "Ciena Corporation";
  contact
    "Web URL: http://www.ciena.com/";
  description
    "Provides RPC for comms-apps-mgr service";

  revision 2021-02-19 {
    ciena-common-version:string "1.0.0";
    description
      "Add RPC force-ntp-sync";
  }

  rpc force-ntp-sync {
    description
      "Sync the time with the provisioned ntp server.";
    input {
      leaf confirm {
        type enumeration {
          enum "ntp-restart";
        }
        mandatory true;
        description
          "Confirmation string to safeguard against accidental
           ntp restart.";
      }
    }

    output {
      uses ciena-common-yang:rpc-result-common;
    }
  }
}
