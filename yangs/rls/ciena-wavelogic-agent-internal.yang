module ciena-wavelogic-agent-internal {
  namespace "urn:ciena:params:xml:ns:yang:ciena-wavelogic-agent-internal";
  prefix wavelogic-agent-internal;

  import ciena-common-version {
    prefix ciena-common-version;
  }

  organization
    "Ciena Corporation";
  contact
    "Web URL: http://www.ciena.com";
  description
    "Wavelogic Agent internal module";

  revision 2022-09-09 {
    description
      "Initial revision";
    ciena-common-version:string "1.0.0";
    reference
      "1.0.0";
  }

  container caches {
    anyxml management;
    anyxml config;
    anyxml state;
    anyxml inventory;
    anyxml statistics;
    anyxml defects;
    anyxml pc-shim-config;
    anyxml pc-shim-running;
    anyxml pc-shim-update;
    anyxml pc-shim-poller;
    anyxml host-services;
  }
  container plug-controller-proxy {
    anyxml data;
  }

  rpc trigger-test {
    description
      "Internal RPC used to trigger internal function for unit testing.";
    input {
      leaf id {
        type uint32;
        description
          "Test ID.";
      }
    }
    output {
      leaf result {
        type boolean;
        description
          "Pass/fail indication.";
      }
      leaf output-string {
        type string;
        description
          "Output string.";
      }
    }
  }
}
