module ciena-pro-ospf-types {
  yang-version 1;
  namespace "http://openconfig.net/yang/ciena-pro-ospf-types";
  prefix ciena-pro-ospft;

  import ciena-common-version {
    prefix ciena-common-version;
  }

  organization
    "Ciena Corporation";
  contact
    "Web URL: http://www.ciena.com/
     Postal:  7035 Ridge Road
             Hanover, Maryland 21076
             U.S.A.
     Phone:   +1 800-921-1144
     Fax:     +1 410-694-5750";
  description
    "This module augments Ciena's 6500r platform OSC attributes into
     OpenConfig network interface object.";

  revision 2019-08-28 {
    ciena-common-version:string "1.0.0";
    description
      "Initial revision";
  }

  identity OSPF-AREA-TYPE {
    description
      "Base identity for OSPF area type.";
  }

  identity NORMAL {
    base OSPF-AREA-TYPE;
    description
      "OSPF normal area.";
  }

  identity STUB {
    base OSPF-AREA-TYPE;
    description
      "OSPF stub area.";
  }

  identity NSSA {
    base OSPF-AREA-TYPE;
    description
      "OSPF NSSA area.";
  }

  identity OSPF-ABR-TYPE {
    description
      "Base identity for OSPF area boarder router type.";
  }

  identity RFC3509-COMPATIBLE {
    base OSPF-ABR-TYPE;
    description
      "OSPF ABR requires backbone area as one of the multiple
       areas.";
  }

  identity RFC2328-COMPATIBLE {
    base OSPF-ABR-TYPE;
    description
      "OSPF ABR does not require backbone area as one of
       the multiple areas.";
  }
}
