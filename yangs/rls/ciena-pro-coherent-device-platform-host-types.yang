module ciena-pro-coherent-device-platform-host-types {
  namespace "urn:ciena:ns:yang:ciena-pro-coherent-device-platform-host-types";
  prefix coherent-device-platform-host-types;

  import ciena-common-version {
    prefix version;
  }

  organization
    "Ciena Corporation";
  contact
    "Web URL: http://www.ciena.com/
     Postal:  7035 Ridge Road
            Hanover, Maryland 21076
            U.S.A.
     Phone:   +1 800-921-1144
     Fax:     +1 410-694-5750";
  description
    "Coherent-device platform host types model.";

  revision 2023-11-01 {
    description
      "Initial version";
    version:version "version" {
      version:string "1.0.0";
    }
    reference
      "1.0.0";
  }

  identity data-rate-identity {
    description
      "base identity for data-rate. The intention of this identity is to list all protocol rates.";
  }

  identity OTU0 {
    base data-rate-identity;
    description
      "Optical Transport Unit (OTU) with data-rate value approx. 1.24G";
  }

  identity OTU1 {
    base data-rate-identity;
    description
      "Optical Transport Unit (OTU) with data-rate value: 2.67 Gbit/s (approx. 2.5G)";
  }

  identity OTU1e {
    base data-rate-identity;
    description
      "Optical Transport Unit (OTU) with data-rate value: 11.05 Gbit/s (approx. 10G)";
  }

  identity OTU2 {
    base data-rate-identity;
    description
      "Optical Transport Unit (OTU) with data-rate value: 10.71 Gbit/s (approx. 10G)";
  }

  identity OTU2e {
    base data-rate-identity;
    description
      "Optical Transport Unit (OTU) with data-rate value: 11.09 Gbit/s (approx. 10G)";
  }

  identity OTU3 {
    base data-rate-identity;
    description
      "Optical Transport Unit (OTU) with data-rate value: 43.02 Gbit/s (approx. 40G)";
  }

  identity OTU4 {
    base data-rate-identity;
    description
      "Optical Transport Unit (OTU) with data-rate value: 111.81 Gbit/s (approx. 100G)";
  }

  identity OTUCn {
    base data-rate-identity;
    description
      "Optical Transport Unit (OTU) with data-rate value nx100G (N times 100G)";
  }

  identity ODU0 {
    base data-rate-identity;
    description
      "Optical Data Unit (ODU) with data-rate value: approx. 1.24Gbit/s (ie. 1.25 G)";
  }

  identity ODU1 {
    base data-rate-identity;
    description
      "Optical Data Unit (ODU) with data-rate value: approx. 2.50 Gbit/s (ie. 2.5 G)";
  }

  identity ODU1e {
    base data-rate-identity;
    description
      "Optical Data Unit (ODU) with data-rate value: approx. 2.50 Gbit/s (ie. 2.5 G)";
  }

  identity ODU2 {
    base data-rate-identity;
    description
      "Optical Data Unit (ODU) with data-rate value: approx. 10.04 Gbit/s (ie. 10G)";
  }

  identity ODU2e {
    base data-rate-identity;
    description
      "Optical Data Unit (ODU) with data-rate value: approx. 10.40 Gbit/s (ie. 10G)";
  }

  identity ODU3 {
    base data-rate-identity;
    description
      "Optical Data Unit (ODU) with data-rate value: approx. 40.32 Gbit/s (ie. 40G)";
  }

  identity ODU3e2 {
    base data-rate-identity;
    description
      "Optical Data Unit (ODU) with data-rate value: approx. 41.79 Gbit/s (ie. 40G)";
  }

  identity ODU4 {
    base data-rate-identity;
    description
      "Optical Data Unit (ODU) with data-rate value: approx. 104.79 Gbit/s (ie. 100G)";
  }

  identity ODUCn {
    base data-rate-identity;
    description
      "Optical Data Unit (ODU) with data-rate value nx100G (N times 100G)";
  }

  identity ODUflex {
    base data-rate-identity;
    description
      "Optical Data Unit (ODU) with data-rate value: approx. nx~1.24 Gbit/s (ie. N times 1.25 G).";
  }

  identity ETH-10M {
    base data-rate-identity;
    description
      "Optical Transport Network (OTN) Ethernet with data-rate value: 10 Mbit/s";
  }

  identity ETH-100M {
    base data-rate-identity;
    description
      "Optical Transport Network (OTN) Ethernet with data-rate value: 100 Mbit/s";
  }

  identity ETH-1G {
    base data-rate-identity;
    description
      "Optical Transport Network (OTN) Ethernet with data-rate value: 1 Gbit/s";
  }

  identity ETH-2G5 {
    base data-rate-identity;
    description
      "Optical Transport Network (OTN) Ethernet with data-rate value: 2.5 Gbit/s";
  }

  identity ETH-5G {
    base data-rate-identity;
    description
      "Optical Transport Network (OTN) Ethernet with data-rate value: 5 Gbit/s";
  }

  identity ETH-10G {
    base data-rate-identity;
    description
      "Optical Transport Network (OTN) Ethernet with data-rate value: ~ 10 Gbit/s";
  }

  identity ETH-25G {
    base data-rate-identity;
    description
      "Optical Transport Network (OTN) Ethernet with data-rate value: ~ 25 Gbit/s";
  }

  identity ETH-40G {
    base data-rate-identity;
    description
      "Optical Transport Network (OTN) Ethernet with data-rate value: ~ 40 Gbit/s";
  }

  identity ETH-50G {
    base data-rate-identity;
    description
      "Optical Transport Network (OTN) Ethernet with data-rate value: ~ 50 Gbit/s";
  }

  identity ETH-100G {
    base data-rate-identity;
    description
      "Optical Transport Network (OTN) Ethernet with data-rate value: ~ 100 Gbit/s)";
  }

  identity ETH-200G {
    base data-rate-identity;
    description
      "Optical Transport Network (OTN) Ethernet with data-rate value: ~ 200 Gbit/s)";
  }

  identity ETH-400G {
    base data-rate-identity;
    description
      "Optical Transport Network (OTN) Ethernet with data-rate value: ~ 400 Gbit/s)";
  }

  identity ETH-800G {
    base data-rate-identity;
    description
      "Optical Transport Network (OTN) Ethernet with data-rate value: ~ 800 Gbit/s)";
  }

  identity FC-100 {
    base data-rate-identity;
    description
      "FC-100 Fiber Channel (FC)";
  }

  identity FC-200 {
    base data-rate-identity;
    description
      "FC-200 Fiber Channel (FC)";
  }

  identity FC-400 {
    base data-rate-identity;
    description
      "FC-400 Fiber Channel (FC)";
  }

  identity FC-800 {
    base data-rate-identity;
    description
      "FC-800 Fiber Channel (FC)";
  }

  identity FC-1200 {
    base data-rate-identity;
    description
      "FC-1200 Fiber Channel (FC)";
  }

  identity FC-1600 {
    base data-rate-identity;
    description
      "FC-1600 Fiber Channel (FC)";
  }

  identity FC-3200 {
    base data-rate-identity;
    description
      "FC-3200 Fiber Channel (FC)";
  }

  identity STM-0 {
    base data-rate-identity;
    description
      "STM-0 Synchronous Transport Module (STM)";
  }

  identity STM-1 {
    base data-rate-identity;
    description
      "STM-1 Synchronous Transport Module (STM)";
  }

  identity STM-4 {
    base data-rate-identity;
    description
      "STM-4 Synchronous Transport Module (STM)";
  }

  identity STM-16 {
    base data-rate-identity;
    description
      "STM-16 Synchronous Transport Module (STM)";
  }

  identity STM-64 {
    base data-rate-identity;
    description
      "STM-64 Synchronous Transport Module (STM)";
  }

  identity STM-256 {
    base data-rate-identity;
    description
      "STM-256 Synchronous Transport Module (STM)";
  }

  identity OC-1 {
    base data-rate-identity;
    description
      "OC-1 Synchronous Optical NETwork (SONET)";
  }

  identity OC-3 {
    base data-rate-identity;
    description
      "OC-3 Synchronous Optical NETwork (SONET)";
  }

  identity OC-12 {
    base data-rate-identity;
    description
      "OC-12 Synchronous Optical NETwork (SONET)";
  }

  identity OC-48 {
    base data-rate-identity;
    description
      "OC-48 Synchronous Optical NETwork (SONET)";
  }

  identity OC-192 {
    base data-rate-identity;
    description
      "OC-192 Synchronous Optical NETwork (SONET)";
  }

  identity OC-768 {
    base data-rate-identity;
    description
      "OC-768 Synchronous Optical NETwork (SONET)";
  }
}
