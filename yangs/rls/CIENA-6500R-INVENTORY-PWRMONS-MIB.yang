module CIENA-6500R-INVENTORY-PWRMONS-MIB {
  namespace "urn:ietf:params:xml:ns:yang:smiv2:CIENA-6500R-INVENTORY-PWRMONS-MIB";
  prefix ciena-6500r-inventory;

  import CIENA-6500R-INVENTORY-MIB {
    prefix ciena-6500r;
  }
  import CIENA-6500R-TYPES-MIB {
    prefix ciena-6500r-types;
  }
  import CIENA-PRO-TYPES-MIB {
    prefix ciena-pro;
  }
  import SNMPv2-TC {
    prefix smiv2;
  }

  organization
    "Ciena Corporation";
  contact
    "Web URL: http://www.ciena.com/
     Postal:  7035 Ridge Road
     Hanover, Maryland 21076
     U.S.A.
     Phone:   +1 800-921-1144
     Fax:    Inventory +1 410-694-5750";
  description
    "This module describes Ciena's photonic pwrmon object.";

  revision 2023-02-06 {
    description
      "set rlsInventoryPwrmonsOptmonInputPower and rlsInventoryPwrmonsOptmonOutputPower
       STATUS to deprecated and add rlsInventoryOptmonsPower to the RlsInventoryOptmonsEntry.";
  }
  revision 2021-10-27 {
    description
      "added a new list for optmon powers.";
  }
  revision 2021-10-10 {
    description
      "Initial revision.";
  }

  container cienaRlsInventoryPwrmonsMIB {
    list rlsInventoryPwrmonsEntry {
      config false;
      key "rlsInventoryPwrmonsSlotName rlsInventoryPwrmonsName";
      description
        "";
      leaf rlsInventoryPwrmonsSlotName {
        type ciena-pro:DisplayString32;
        config false;
        description
          "The name of the slot.";
      }
      leaf rlsInventoryPwrmonsName {
        type ciena-pro:DisplayString128;
        config false;
        description
          "Pwrmon name.";
      }
      leaf rlsInventoryPwrmonsOSCCenterFreq {
        type ciena-pro:DisplayString128;
        config false;
        description
          "Center frequency of OSC pwrmon";
      }
    }
    config false;
    list rlsInventoryOptmonsEntry {
      config false;
      key "rlsInventoryOptmonsSlotName rlsInventoryOptmonsName";
      description
        "";
      leaf rlsInventoryOptmonsSlotName {
        type ciena-pro:DisplayString32;
        config false;
        description
          "The name of the slot.";
      }
      leaf rlsInventoryOptmonsName {
        type ciena-pro:DisplayString128;
        config false;
        description
          "Optmon name.";
      }
      leaf rlsInventoryPwrmonsOptmonInputPower {
        type ciena-pro:DisplayString32;
        config false;
        status deprecated;
        description
          "Optmon Input power";
      }
      leaf rlsInventoryPwrmonsOptmonOutputPower {
        type ciena-pro:DisplayString32;
        config false;
        status deprecated;
        description
          "Optmon Output power";
      }
      leaf rlsInventoryOptmonsPower {
        type ciena-pro:DisplayString32;
        config false;
        description
          "Optmon power";
      }
    }
  }
}
