module ciena-common-yang-async {
  namespace "urn:ciena:params:xml:ns:yang:ciena-common-yang-async";
  prefix async;

  import ciena-common-yang {
    prefix yang;
  }

  organization
    "Ciena Corporation";
  contact
    "Web URL: http://www.ciena.com/
     Postal:  7035 Ridge Road
     Hanover, Maryland 21076
     U.S.A.
     Phone:   +1 800-921-1144
     Fax:     +1 410-694-5750";
  description
    "Async mechanism, where an incoming server/client request behaves in a non-blocking manner";

  revision 2018-10-29 {
    description
      "Initial revision: Async rpc mechanisms to augment the ddf yang actions";
    reference
      "";
  }

  typedef correlation {
    type uint64;
    description
      "correlation tag used for mapping async request to response";
  }

  grouping async-request {
    container request {
      leaf async-req {
        type empty;
      }
      leaf notify {
        type string;
        description
          "name of the subscriber.  This is used in the
           notification to route the data to the correct destination";
      }
      leaf timeout {
        type uint32;
        units "ms";
        description
          "specified timeout for the async call";
      }
      anyxml data;
    }
  }

  grouping async-data {
    container async {
      leaf correlation-tag {
        type correlation;
        default "0";
      }
      anyxml data;
    }
  }

  augment "/yang:yang-del-object/yang:input" {
    uses async-request;
  }

  augment "/yang:yang-del-object/yang:output" {
    uses async-data;
  }

  augment "/yang:yang-get-object/yang:input" {
    uses async-request;
  }

  augment "/yang:yang-get-object/yang:output" {
    uses async-data;
  }

  augment "/yang:yang-set-object/yang:input" {
    uses async-request;
  }

  augment "/yang:yang-set-object/yang:output" {
    uses async-data;
  }

  augment "/yang:yang-val-object/yang:input" {
    uses async-request;
  }

  augment "/yang:yang-val-object/yang:output" {
    uses async-data;
  }

  augment "/yang:yang-stage-object/yang:input" {
    uses async-request;
  }

  augment "/yang:yang-stage-object/yang:output" {
    uses async-data;
  }
}
