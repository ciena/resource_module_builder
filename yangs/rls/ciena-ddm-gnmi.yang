module ciena-ddm-gnmi {
  namespace "urn:ciena:params:xml:ns:yang:ciena-ddm-gnmi";
  prefix ddm-gnmi;

  import ciena-ddy-msg {
    prefix ciena-ddy-msg;
  }

  organization
    "Ciena Corporation";
  contact
    "Web URL: http://www.ciena.com/
     Postal: 7035 Ridge Road
            Hanover, Maryland 21076
            U.S.A.
     Phone:   +1 800-921-1144
     Fax:     +1 410-694-5750";
  description
    "This module describes information about ddm-gnmi/grpc client server";

  revision 2019-06-13 {
    description
      "Initial revision";
  }

  identity gnmi {
    base ciena-ddy-msg:ddm-protocols;
    description
      "gNMI Client/Server";
  }

  augment "/ciena-ddy-msg:domains/ciena-ddy-msg:protocols" {
    when "ciena-ddy-msg:type = 'ciena-ddy-msg:gnmi'";
    container grpc-gnmi-options {
      leaf ipport {
        type string;
        description
          "IP and Port";
      }
    }
  }
}
