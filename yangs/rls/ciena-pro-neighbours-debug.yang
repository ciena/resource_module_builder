module ciena-pro-neighbours-debug {
  namespace "urn:ciena:params:xml:ns:yang:ciena-pro-neighbours-debug";
  prefix neighbours-debug;

  import ietf-inet-types {
    prefix ietf;
  }
  import ietf-yang-types {
    prefix ietf-yang;
  }
  import ciena-pro-neighbours {
    prefix neighbours;
  }
  import ciena-common-yang {
    prefix ciena-common-yang;
  }

  organization
    "Ciena Corporation";
  contact
    "Web URL: http://www.ciena.com/
     Postal:  7035 Ridge Road
              Hanover, Maryland 21076
              U.S.A.
     Phone:   +1 800-921-1144
     Fax:     +1 410-694-5750";
  description
    "This model captures debug RPCs for manipulating neighbours.";

  revision 2020-11-05 {
    description
      "Added IPV6 address RLS 2.2.";
  }
  revision 2018-10-16 {
    description
      "Initial Revision";
  }

  rpc debug-create-neighbour {
    input {
      leaf name {
        type string;
        description
          "The name of the neighbour";
      }
      leaf ip-address {
        type ietf:ip-address;
        description
          "The IP address of the neighbour";
      }
      leaf ipv6-address {
        type ietf:ipv6-address-no-zone;
        description
          "The IPv6 address of neighbour.";
      }
      leaf mac-address {
        type ietf-yang:mac-address;
        description
          "The MAC address of the neighbour";
      }
      leaf local-interface {
        type instance-identifier;
        description
          "Local interface where the neighbour was discovered";
      }
      leaf neighbour-interface {
        type string;
        description
          "Interface on the neighbouring node which is adjacent to the local interface above";
      }
      leaf source {
        type identityref {
          base neighbours:source-type;
        }
        description
          "The source for the neighbour entry";
      }
    }
    output {
      list return-code-list {
        uses ciena-common-yang:return-code;
      }
    }
  }

  rpc debug-delete-neighbour {
    input {
      leaf name {
        type string;
        description
          "The name of the neighbour";
      }
    }
    output {
      list return-code-list {
        uses ciena-common-yang:return-code;
      }
    }
  }
}
