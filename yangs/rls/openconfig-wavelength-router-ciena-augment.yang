module openconfig-wavelength-router-ciena-augment {
  yang-version 1.1;
  namespace "openconfig-wavelength-router-ciena:augment";
  prefix oc-wave-router-ciena;

  import openconfig-wavelength-router {
    prefix oc-wave-router;
  }

  organization
    "Ciena Corporation";
  contact
    "Web URL: http://www.ciena.com";
  description
    "This modules describes Ciena's openconfig-wavelength-router augmentation for the optical platforms";

  revision 2023-09-14 {
    description
      "Augmentation of the media channel config with the deadband-config grouping";
    reference
      "1.0.0";
  }

  grouping deadband-config {
    leaf lower-frequency-deadband {
      type uint64;
      units "MHz";
      default "6250";
      description
        "Account for filter deadband associated with lower-frequency roll off.";
    }
    leaf upper-frequency-deadband {
      type uint64;
      units "MHz";
      default "6250";
      description
        "Account for filter deadband associated with upper-frequency roll off.";
    }
  }

  augment "/oc-wave-router:wavelength-router/oc-wave-router:media-channels/oc-wave-router:channel/oc-wave-router:config" {
    uses deadband-config {
      when 'super-channel = true';
    }
  }
}
