module ciena-ddf {
  namespace "urn:ciena:params:xml:ns:yang:ciena-ddf";
  prefix ddf;

  organization
    "Ciena";
  contact
    "";
  description
    "UI";

  revision 2015-04-07 {
    description
      "";
    reference
      "";
  }

  extension ddf-struct-version {
    argument name;
    description
      "Mark the node with a DDF version (structs only). Versions affect the
       operation of the DDF parser. Generally only needed for augments.";
  }
}
