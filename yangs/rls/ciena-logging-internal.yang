module ciena-logging-internal {
  yang-version 1;
  namespace "urn:ciena:params:xml:ns:yang:ciena-logging-internal";
  prefix ciena-logging-internal;

  import ciena-common-version {
    prefix ciena-common-version;
  }
  import ciena-common-yang {
    prefix ciena-common-yang;
  }
  import ietf-yang-types {
    prefix yang;
  }

  organization
    "Ciena Corporation";
  contact
    "Web URL: http://www.ciena.com";
  description
    "This module describes Ciena's internal logging objects for the 6500r platform";

  revision 2023-11-21 {
    description
      "Initial revision for logging-mgr internal yang";
  }

  grouping set-ztp-log-servers-input {
    description
      "Input for setting ztp log servers with rpc";
    leaf server-num {
      type uint8 {
        range "4..6";
      }
      mandatory true;
      description
        "Number of the ztp remote log server (4 - 6). The default is 4.";
    }
    leaf host {
      type string;
      mandatory true;
      description
        "IP Address or hostname of the remote log server";
    }
  }

  grouping delete-ztp-log-servers-input {
    description
      "Input for deleting ztp log servers with rpc";
    leaf server-num {
      type uint8 {
        range "4..6";
      }
      mandatory true;
      description
        "Number of the ztp remote log server (4 - 6). The default is 4.";
    }
  }

  rpc set-ztp-log-servers {
    input {
      list ztp-log-servers {
        uses set-ztp-log-servers-input;
        description
          "Input data for configuring ztp logging servers";
      }
    }
    output {
      uses ciena-common-yang:rpc-result-common;
    }
  }

  rpc delete-ztp-log-servers {
    input {
      list ztp-log-servers {
        uses delete-ztp-log-servers-input;
        description
          "Input data for deleting ztp logging servers";
      }
    }
    output {
      uses ciena-common-yang:rpc-result-common;
    }
  }
}
