module ciena-common-service-broker-datastore {
  namespace "urn:ciena:params:xml:ns:yang:ciena-service-broker-datastore";
  prefix service-broker-datastore;

  import ciena-common-yang {
    prefix yang;
  }
  import ciena-common-version {
    prefix version;
  }
  import ciena-ddy-db {
    prefix ddy-db;
  }
  import ciena-common-service-broker {
    prefix service-broker;
  }

  organization
    "Ciena Corporation";
  contact
    "Web URL: http://www.ciena.com/
     Postal:  7035 Ridge Road
              Hanover, Maryland 21076
              U.S.A.
     Phone:   +1 800-921-1144
     Fax:     +1 410-694-5750";
  description
    "Service Level locking with Transactions.";

  revision 2021-02-11 {
    description
      "Add ddy-db datastore augment to the service broker
       yang-lock-object RPC.";
    version:version "version" {
      version:string "1.4.0";
    }
  }
  revision 2020-09-17 {
    description
      "Add ddy-db datastore augment to the service broker
       stage-transaction RPC.";
    version:version "version" {
      version:string "1.3.0";
    }
  }
  revision 2019-10-04 {
    description
      "Add ddy-db datastore augments to service broker RPCs and framework
       APIs.";
    version:version "version" {
      version:string "1.2.0";
    }
  }

  augment "/yang:yang-get-object/yang:input" {
    description
      "Adds datastore to the getObject API input.";
    uses ddy-db:datastore;
  }

  augment "/yang:yang-set-object/yang:input" {
    description
      "Adds datastore to the setObject API input.";
    uses ddy-db:datastore;
  }

  augment "/yang:yang-stage-object/yang:input" {
    description
      "Adds datastore to the stageObject API input.";
    uses ddy-db:datastore;
  }

  augment "/yang:yang-val-object/yang:input" {
    description
      "Adds datastore to the valObject API input.";
    uses ddy-db:datastore;
  }

  augment "/service-broker:validate-transaction/service-broker:input" {
    description
      "Adds datastore to the service broker validate transaction RPC input.";
    uses ddy-db:datastore;
  }

  augment "/service-broker:commit-transaction/service-broker:input" {
    description
      "Adds datastore to the service broker commit transaction RPC input.";
    uses ddy-db:datastore;
  }

  augment "/yang:yang-delivery" {
    description
      "Adds datastore to the delivery structure of the publish update API.";
    uses ddy-db:datastore;
  }

  augment "/service-broker:stage-transaction/service-broker:input" {
    description
      "Adds datastore to the service broker stage transaction RPC input.";
    uses ddy-db:datastore;
  }

  augment "/service-broker:yang-lock-object/service-broker:input" {
    description
      "Adds datastore to the service broker lock RPC input.";
    uses ddy-db:datastore;
  }
}
