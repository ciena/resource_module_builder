module ciena-pro-ztp-state {
  namespace "urn:ciena:params:xml:ns:yang:ciena-pro-ztp-state";
  prefix ciena-pro-ztp-state;

  import ciena-6500r-types {
    prefix ciena-6500r-types;
  }
  import ciena-common-version {
    prefix ciena-common-version;
  }

  organization
    "Ciena Corporation";
  contact
    "Web URL: http://www.ciena.com/";
  description
    "This module defines zero touch provisioning for Ciena's 6500r Platform.";

  revision 2020-05-11 {
    description
      "Add sw-upgrade-in-progress state";
    ciena-common-version:string "1.0.1";
  }
  revision 2018-09-04 {
    description
      "Initial version";
    ciena-common-version:string "1.0.0";
  }

  container ztp-state {
    description
      "ZTP state structure";
    leaf operation-state {
      type enumeration {
        enum init {
          description
            "The ZTP has been initialized";
        }
        enum started {
          description
            "The ZTP has started";
        }
        enum progress {
          description
            "The ZTP is in progress";
        }
        enum sw-upgrade-in-progress {
          description
            "ZTP's software upgrade is in progress";
        }
        enum done {
          description
            "The ZTP is done.";
        }
      }
      mandatory true;
    }
  }
}
