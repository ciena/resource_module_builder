module ciena-wavelogic-manager {
  namespace "urn:ciena:params:xml:ns:yang:ciena-wavelogic-manager";
  prefix wavelogic-manager;

  import ciena-common-version {
    prefix ciena-common-version;
  }

  organization
    "Ciena Corporation";
  contact
    "Web URL: http://www.ciena.com";
  description
    "Wavelogic Manager module";

  revision 2022-10-13 {
    description
      "Initial revision";
    ciena-common-version:string "1.0.0";
    reference
      "1.0.0";
  }

  container some-container {
    leaf some-value {
      type uint64;
    }
  }
}
