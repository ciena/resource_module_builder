module ciena-openconfig-routing-diag {
  yang-version 1.1;
  namespace "urn:ciena:params:xml:ns:yang:ciena-openconfig-routing-diag";
  prefix ciena-openconfig-routing-diag;

  import ciena-common-version {
    prefix ciena-common-version;
  }
  import openconfig-network-instance {
    prefix oc-ni;
  }
  import ciena-pro-routing-diag {
    prefix rtg-diag;
  }

  organization
    "Ciena Corporation";
  contact
    "Web URL: http://www.ciena.com/
     Postal:  7035 Ridge Road
             Hanover, Maryland 21076
             U.S.A.
     Phone:   +1 800-921-1144
     Fax:     +1 410-694-5750";
  description
    "This module augments the openconfig-bgp-global.yang
     with 2 actions for retrieving the BGP Network Layer Routing Information";

  revision 2022-07-12 {
    description
      "Added grouping for fib table display";
    ciena-common-version:string "1.0.1";
  }
  revision 2022-05-06 {
    description
      "Initial revision";
    ciena-common-version:string "1.0.0";
  }

  augment "/oc-ni:network-instances/oc-ni:network-instance/oc-ni:protocols/oc-ni:protocol/oc-ni:bgp/oc-ni:global" {
    description
      "BGP retrieve-rib-summary action";
    uses rtg-diag:bgp-rib-summary;
  }

  augment "/oc-ni:network-instances/oc-ni:network-instance/oc-ni:protocols/oc-ni:protocol/oc-ni:bgp/oc-ni:global" {
    description
      "BGP retrieve-rib-detail action";
    uses rtg-diag:bgp-rib-detail;
  }

  augment "/oc-ni:network-instances/oc-ni:network-instance" {
    description
      "Retrieve-routing-table action";
    uses rtg-diag:routing-table;
  }

  augment "/oc-ni:network-instances/oc-ni:network-instance/oc-ni:protocols/oc-ni:protocol/oc-ni:isis/oc-ni:global/oc-ni:config" {
    description
      "ISIS retrieve-area-address-list action";
    uses rtg-diag:isis-area-list;
  }
}
