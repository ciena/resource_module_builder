module ciena-ddy-msg-options {
  namespace "urn:ciena:params:xml:ns:yang:ciena-ddy-msg-options";
  prefix ddy-msg-options;

  import ciena-common-version {
    prefix version;
  }

  import ciena-common-yang {
    prefix yang;
  }

  organization
    "Ciena Corporation";
  contact
    "Web URL: http://www.ciena.com/
     Postal:  7035 Ridge Road
             Hanover, Maryland 21076
             U.S.A.
     Phone:   +1 800-921-1144
     Fax:     +1 410-694-5750";
  description
    "This is the model for the storing various ddy messaging options";

  revision 2020-03-11 {
    version:version "version" {
      version:string "0.1.0";
    }
    description
      "Initial revision";
  }

  grouping local-id {
    description
      "Contains various messaging options";
    leaf local-id {
      type string;
      description
        "An unique identifier to logically group a set of micro-services";
    }
  }

  container msg-options {
    description
      "Used by depo to define default messaging options";
    uses local-id;
  }
}
