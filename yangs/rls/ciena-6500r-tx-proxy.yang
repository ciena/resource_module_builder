module ciena-6500r-tx-proxy {
  yang-version 1.1;
  namespace "urn:ciena:params:xml:ns:yang:ciena-6500r-tx-proxy";
  prefix tx-proxy;

  import ciena-6500r-types {
    prefix ciena-6500r-types;
  }

  import ciena-common-version {
    prefix version;
  }

  import ciena-6500r-ports {
    prefix ports;
  }

  import ciena-pro-tx-proxy {
    prefix ciena-pro-tx-proxy;
  }

  organization
    "Ciena Corporation";
  contact
    "Web URL: http://www.ciena.com/
     Postal:  7035 Ridge Road
             Hanover, Maryland 21076
             U.S.A.
     Phone:   +1 800-921-1144
     Fax:     +1 410-694-5750";
  description
    "This module describes Ciena's transponder proxy data model for the RLS platform, first introduced in RLS 1.1";

  revision 2021-04-22 {
    version:version "version" {
      version:string "0.1.1";
    }
    description
      "Created tx-proxy-grouping";
  }
  revision 2020-09-08 {
    version:version "version" {
      version:string "0.2.0";
    }
    description
      "Use ciena-pro-tx-proxy";
  }
  revision 2020-08-17 {
    version:version "version" {
      version:string "0.1.0";
    }
    description
      "Added center-freq and source";
  }
  revision 2020-06-30 {
    version:version "version" {
      version:string "0.0.5";
    }
    description
      "Fix version formatting";
  }
  revision 2020-01-21 {
    version:version "version" {
      version:string "0.0.4";
    }
    description
      "Added target-psd parameter.";
  }
  revision 2019-11-12 {
    version:version "version" {
      version:string "0.0.3";
    }
    description
      "Added link-optimization-mode and tx-minimum-spectral-width params.";
  }
  revision 2019-11-05 {
    version:version "version" {
      version:string "0.0.2";
    }
    description
      "Updated state to common admin-state";
  }
  revision 2019-10-04 {
    version:version "version" {
      version:string "0.0.1";
    }
    description
      "Added path-chromatic-dispersion param.";
  }
  revision 2019-05-22 {
    description
      "Initial Revision.";
  }

  grouping tx-proxy-grouping {
    uses ciena-pro-tx-proxy:tx-proxy;

    leaf parent-port {
      type leafref {
        path "/ports:port/ports:name";
      }
      mandatory true;
      description
        "Transponder-proxy facility parent port.";
    }

    uses ciena-6500r-types:admin-state;
  }

  grouping ciena-6500r-tx-proxy-mount {
    list tx-proxy {
      key "name";
      uses tx-proxy-grouping;
    }
  }

  grouping ciena-6500r-tx-proxy-mount-actions;

  uses ciena-6500r-tx-proxy-mount;
}
