module ciena-pro-frequencies {
  yang-version 1.1;
  namespace "urn:ciena:params:xml:ns:yang:ciena-pro-frequencies";
  prefix frequencies;

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's P-series frequency module.";

  revision 2017-01-01 {
    description
      "Initial revision";
  }

  grouping ciena-pro-frequencies-mount {
    list freq-group {
      key "name";
      leaf name {
        type string {
          length "1..64";
        }
        description
          "Name for this frequency group";
      }

      list band {
        key "min";
        leaf min {
          type decimal64 {
            fraction-digits 4;
          }
          units "THz";
          description
            "Min frequency";
        }

        leaf max {
          type decimal64 {
            fraction-digits 4;
          }
          units "THz";
          description
            "Max frequency";
        }

        leaf width {
          type decimal64 {
            fraction-digits 3;
          }
          units "GHz";
          description
            "Frequency width";
        }
      }
    }
  }

  grouping ciena-pro-frequencies-mount-actions;

  uses ciena-pro-frequencies-mount;
}
