module ciena-pro-coherent-device-statistics-types {
  namespace "urn:ciena:ns:yang:coherent-device-statistics-types";
  prefix coherent-device-statistics-types;

  import ciena-common-version {
    prefix version;
  }
  import ietf-yang-types {
    prefix ietf-yang-types;
  }
  import ciena-pro-coherent-device-common-types {
    prefix coherent-device-common-types;
  }

  organization
    "Ciena Corporation";
  contact
    "Web URL: http://www.ciena.com/
     Postal:  7035 Ridge Road
              Hanover, Maryland 21076
              U.S.A.
     Phone:   +1 800-921-1144
     Fax:     +1 410-694-5750";
  description
    "Device statistics definitions for coherent devices.";

  revision 2024-01-01 {
    description
      "Initial version.";
    version:version "version" {
      version:string "1.0.0";
    }
    reference
      "1.0.0";
  }

  typedef stat-interval {
    type uint64;
    units "nanoseconds";
    description
      "A time interval that a statistic is computed over.";
  }

  typedef time-str {
    type ietf-yang-types:date-and-time;
    description
      "Timestamp in RFC 3339 string format.";
  }

  typedef time-ns {
    type uint64;
    units "nanoseconds";
    description
      "The amount of time modulo 2^64 in nanoseconds.";
  }

  grouping stat-interval-group {
    leaf interval {
      type stat-interval;
      description
        "The interval over which average, minimum, and maximum statistics
         are computed.";
    }
    description
      "Group for statistic bin interval.";
  }

  grouping stat-interval-validity-flag-group {
    leaf invalid {
      type boolean;
      description
        "When false indicates that the statistic data for this collection interval may
         be incomplete or otherwise untrustworthy due to anomalies during the interval.";
    }
    description
      "";
  }

  grouping stat-min-max-time-group {
    leaf min-time {
      type time-ns;
      description
        "The absolute time when the minimum value of a statistic occurred in nanoseconds.";
    }
    leaf max-time {
      type time-ns;
      description
        "The absolute time when the maximum value of a statistic occurred in nanoseconds.";
    }
    description
      "";
  }

  grouping stat-collection-time-group {
    leaf timestamp {
      type time-ns;
      description
        "Statistic collection time in nanoseconds.";
    }
    description
      "Representation of the time a statistic is collected.";
  }

  grouping stat-bin-timestamps-group {
    leaf start-time {
      type time-str;
      description
        "The start time for a statistic collection bin interval in RFC 3339 formatted timestamp string.";
    }
    leaf end-time {
      type time-str;
      description
        "The end time for a statistic collection bin interval in RFC 3339 formatted timestamp string.";
    }
    description
      "";
  }

  grouping stat-bin-details-group {
    container bin-details {
      uses stat-bin-timestamps-group;
      uses stat-interval-validity-flag-group;
      description
        "Details regarding the bin of each statistic. Bin collection is synchronized
         for all statistics and every bin coves the same period. Therefore the bin for
         every statistic has the same start and end-time and is affected by the same
         condition that drive the invalid data-flag.";
    }
    description
      "";
  }

  grouping instant-interval-stats-sci-notation-ber-group {
    leaf instant {
      type coherent-device-common-types:stat-sci-notation-ber-type;
      description
        "The instantaneous value of the statistic.";
    }
    uses stat-collection-time-group;
    container bin {
      uses stat-interval-group;
      leaf avg {
        type coherent-device-common-types:stat-sci-notation-ber-type;
        description
          "The mean value of the statistic over the bin interval.";
      }
      leaf min {
        type coherent-device-common-types:stat-sci-notation-ber-type;
        description
          "The minimum value of the statistic over the bin interval.";
      }
      leaf max {
        type coherent-device-common-types:stat-sci-notation-ber-type;
        description
          "The maximum value of the statistic over the bin interval.";
      }
      uses stat-min-max-time-group;
      description
        "";
    }
    description
      "Generic grouping for a statistic with units of dBm and 2 decimals of precision.";
  }

  grouping instant-interval-stats-precision2-dBm-group {
    leaf instant {
      type coherent-device-common-types:stat-precision2-dBm-type;
      description
        "The instantaneous value of the statistic.";
    }
    uses stat-collection-time-group;
    container bin {
      uses stat-interval-group;
      leaf avg {
        type coherent-device-common-types:stat-precision2-dBm-type;
        description
          "The mean value of the statistic over the bin interval.";
      }
      leaf min {
        type coherent-device-common-types:stat-precision2-dBm-type;
        description
          "The minimum value of the statistic over the bin interval.";
      }
      leaf max {
        type coherent-device-common-types:stat-precision2-dBm-type;
        description
          "The maximum value of the statistic over the bin interval.";
      }
      uses stat-min-max-time-group;
      description
        "";
    }
    description
      "Generic grouping for a statistic with units of dBm and 2 decimals of precision.";
  }

  grouping instant-interval-stats-precision3-ps-group {
    leaf instant {
      type coherent-device-common-types:stat-precision3-ps-type;
      description
        "The instantaneous value of the statistic.";
    }
    uses stat-collection-time-group;
    container bin {
      uses stat-interval-group;
      leaf avg {
        type coherent-device-common-types:stat-precision3-ps-type;
        description
          "The mean value of the statistic over the bin interval.";
      }
      leaf min {
        type coherent-device-common-types:stat-precision3-ps-type;
        description
          "The minimum value of the statistic over the bin interval.";
      }
      leaf max {
        type coherent-device-common-types:stat-precision3-ps-type;
        description
          "The maximum value of the statistic over the bin interval.";
      }
      uses stat-min-max-time-group;
      description
        "";
    }
    description
      "Generic grouping for a statistic with units of picoseconds and 3 decimals of precision.";
  }

  grouping instant-interval-stats-precision3-ps2-group {
    leaf instant {
      type coherent-device-common-types:stat-precision3-ps2-type;
      description
        "The instantaneous value of the statistic.";
    }
    uses stat-collection-time-group;
    container bin {
      uses stat-interval-group;
      leaf avg {
        type coherent-device-common-types:stat-precision3-ps2-type;
        description
          "The mean value of the statistic over the bin interval.";
      }
      leaf min {
        type coherent-device-common-types:stat-precision3-ps2-type;
        description
          "The minimum value of the statistic over the bin interval.";
      }
      leaf max {
        type coherent-device-common-types:stat-precision3-ps2-type;
        description
          "The maximum value of the statistic over the bin interval.";
      }
      uses stat-min-max-time-group;
      description
        "";
    }
    description
      "Generic grouping for a statistic with units of picoseconds squared and 3 decimals of precision.";
  }

  grouping instant-interval-stats-precision3-ps-nm-group {
    leaf instant {
      type coherent-device-common-types:stat-precision3-ps-nm-type;
      description
        "The instantaneous value of the statistic.";
    }
    uses stat-collection-time-group;
    container bin {
      uses stat-interval-group;
      leaf avg {
        type coherent-device-common-types:stat-precision3-ps-nm-type;
        description
          "The mean value of the statistic over the bin interval.";
      }
      leaf min {
        type coherent-device-common-types:stat-precision3-ps-nm-type;
        description
          "The minimum value of the statistic over the bin interval.";
      }
      leaf max {
        type coherent-device-common-types:stat-precision3-ps-nm-type;
        description
          "The maximum value of the statistic over the bin interval.";
      }
      uses stat-min-max-time-group;
      description
        "";
    }
    description
      "Generic grouping for a statistic with units of picosecond per nanometer
       and 3 decimals of precision.";
  }

  grouping instant-interval-stats-precision3-dB-group {
    leaf instant {
      type coherent-device-common-types:stat-precision3-dB-type;
      description
        "The instantaneous value of the statistic.";
    }
    uses stat-collection-time-group;
    container bin {
      uses stat-interval-group;
      leaf avg {
        type coherent-device-common-types:stat-precision3-dB-type;
        description
          "The mean value of the statistic over the bin interval.";
      }
      leaf min {
        type coherent-device-common-types:stat-precision3-dB-type;
        description
          "The minimum value of the statistic over the bin interval.";
      }
      leaf max {
        type coherent-device-common-types:stat-precision3-dB-type;
        description
          "The maximum value of the statistic over the bin interval.";
      }
      uses stat-min-max-time-group;
      description
        "";
    }
    description
      "Generic grouping for a statistic with units of decibel
       and 3 decimals of precision.";
  }

  grouping interval-stat-std-dev-precision3-dB-group {
    leaf standard-deviation {
      type coherent-device-common-types:stat-precision3-dB-type;
      description
        "Generic grouping for a standard deviation statistic with
         units of decibel and 3 decimals of precision.";
    }
    description
      "";
  }

  grouping instant-interval-stats-precision1-mhz-group {
    leaf instant {
      type coherent-device-common-types:stat-precision1-mhz-type;
      description
        "The instantaneous value of the statistic.";
    }
    uses stat-collection-time-group;
    container bin {
      uses stat-interval-group;
      leaf avg {
        type coherent-device-common-types:stat-precision1-mhz-type;
        description
          "The mean value of the statistic over the bin interval.";
      }
      leaf min {
        type coherent-device-common-types:stat-precision1-mhz-type;
        description
          "The minimum value of the statistic over the bin interval.";
      }
      leaf max {
        type coherent-device-common-types:stat-precision1-mhz-type;
        description
          "The maximum value of the statistic over the bin interval.";
      }
      uses stat-min-max-time-group;
      description
        "";
    }
    description
      "Generic grouping for a statistic with units of Megahertz
       and 3 decimals of precision.";
  }

  grouping instant-interval-stats-precision2-percent-group {
    leaf instant {
      type coherent-device-common-types:stat-precision2-percent-type;
      description
        "The instantaneous value of the statistic.";
    }
    uses stat-collection-time-group;
    container bin {
      uses stat-interval-group;
      leaf avg {
        type coherent-device-common-types:stat-precision2-percent-type;
        description
          "The mean value of the statistic over the bin interval.";
      }
      leaf min {
        type coherent-device-common-types:stat-precision2-percent-type;
        description
          "The minimum value of the statistic over the bin interval.";
      }
      leaf max {
        type coherent-device-common-types:stat-precision2-percent-type;
        description
          "The maximum value of the statistic over the bin interval.";
      }
      uses stat-min-max-time-group;
      description
        "";
    }
    description
      "Generic grouping for a statistic with units as percentage
       and 2 decimals of precision.";
  }

  grouping instant-interval-stats-precision1-krads-group {
    leaf instant {
      type coherent-device-common-types:stat-precision1-krads-type;
      description
        "The instantaneous value of the statistic.";
    }
    uses stat-collection-time-group;
    container bin {
      uses stat-interval-group;
      leaf avg {
        type coherent-device-common-types:stat-precision1-krads-type;
        description
          "The mean value of the statistic over the bin interval.";
      }
      leaf min {
        type coherent-device-common-types:stat-precision1-krads-type;
        description
          "The minimum value of the statistic over the bin interval.";
      }
      leaf max {
        type coherent-device-common-types:stat-precision1-krads-type;
        description
          "The maximum value of the statistic over the bin interval.";
      }
      uses stat-min-max-time-group;
      description
        "";
    }
    description
      "Generic grouping for a statistic with units as kiloradians per second
       and 1 decimals of precision.";
  }

  grouping instant-interval-stats-precision1-degree-c-group {
    leaf instant {
      type coherent-device-common-types:stat-precision1-degree-c-type;
      description
        "The instantaneous value of the statistic.";
    }
    uses stat-collection-time-group;
    container bin {
      uses stat-interval-group;
      leaf avg {
        type coherent-device-common-types:stat-precision1-degree-c-type;
        description
          "The mean value of the statistic over the bin interval.";
      }
      leaf min {
        type coherent-device-common-types:stat-precision1-degree-c-type;
        description
          "The minimum value of the statistic over the bin interval.";
      }
      leaf max {
        type coherent-device-common-types:stat-precision1-degree-c-type;
        description
          "The maximum value of the statistic over the bin interval.";
      }
      uses stat-min-max-time-group;
      description
        "";
    }
    description
      "Generic grouping for a statistic with units as degree Celsius
       and 1 decimal of precision.";
  }

  grouping instant-interval-stats-precision1-volts-group {
    leaf instant {
      type coherent-device-common-types:stat-precision2-volts-type;
      description
        "The instantaneous value of the statistic.";
    }
    uses stat-collection-time-group;
    container bin {
      uses stat-interval-group;
      leaf avg {
        type coherent-device-common-types:stat-precision2-volts-type;
        description
          "The mean value of the statistic over the bin interval.";
      }
      leaf min {
        type coherent-device-common-types:stat-precision2-volts-type;
        description
          "The minimum value of the statistic over the bin interval.";
      }
      leaf max {
        type coherent-device-common-types:stat-precision2-volts-type;
        description
          "The maximum value of the statistic over the bin interval.";
      }
      uses stat-min-max-time-group;
      description
        "";
    }
    description
      "Generic grouping for a statistic with units as Volts
       and 2 decimals of precision.";
  }

  grouping instant-interval-stats-precision2-milliamps-group {
    leaf instant {
      type coherent-device-common-types:stat-precision2-milliamps-type;
      description
        "The instantaneous value of the statistic.";
    }
    uses stat-collection-time-group;
    container bin {
      uses stat-interval-group;
      leaf avg {
        type coherent-device-common-types:stat-precision2-milliamps-type;
        description
          "The mean value of the statistic over the bin interval.";
      }
      leaf min {
        type coherent-device-common-types:stat-precision2-milliamps-type;
        description
          "The minimum value of the statistic over the bin interval.";
      }
      leaf max {
        type coherent-device-common-types:stat-precision2-milliamps-type;
        description
          "The maximum value of the statistic over the bin interval.";
      }
      uses stat-min-max-time-group;
      description
        "";
    }
    description
      "Generic grouping for a statistic with units as milliamps
       and 2 decimals of precision.";
  }

  grouping instant-total-stats-seconds-count-group {
    leaf instant {
      type coherent-device-common-types:stat-seconds-counter8-type;
      description
        "The instantaneous value of the statistic.";
    }
    uses stat-collection-time-group;
    container bin {
      uses stat-interval-group;
      leaf total {
        type coherent-device-common-types:stat-seconds-counter8-type;
        description
          "The mean value of the statistic over the bin interval.";
      }
      description
        "";
    }
    description
      "Generic grouping for a statistic that is a counter requiring 32-bits.";
  }

  grouping instant-interval-total-stats-counter32-group {
    leaf instant {
      type uint32;
      description
        "The instantaneous value of the statistic.";
    }
    uses stat-collection-time-group;
    container bin {
      uses stat-interval-group;
      leaf total {
        type uint64;
        description
          "The total value of the statistic over the bin interval.";
      }
      leaf avg {
        type uint32;
        description
          "The mean value of the statistic over the bin interval.";
      }
      leaf min {
        type uint32;
        description
          "The minimum value of the statistic over the bin interval.";
      }
      leaf max {
        type uint32;
        description
          "The maximum value of the statistic over the bin interval.";
      }
      uses stat-min-max-time-group;
      description
        "";
    }
    description
      "Generic grouping for a statistic that is a counter requiring 32-bits.";
  }

  grouping instant-interval-total-stats-counter64-group {
    leaf instant {
      type uint64;
      description
        "The instantaneous value of the statistic.";
    }
    uses stat-collection-time-group;
    container bin {
      uses stat-interval-group;
      leaf total {
        type uint64;
        description
          "The total value of the statistic over the bin interval.";
      }
      leaf avg {
        type uint64;
        description
          "The mean value of the statistic over the bin interval.";
      }
      leaf min {
        type uint64;
        description
          "The minimum value of the statistic over the bin interval.";
      }
      leaf max {
        type uint64;
        description
          "The maximum value of the statistic over the bin interval.";
      }
      uses stat-min-max-time-group;
      description
        "";
    }
    description
      "Generic grouping for a statistic that is a counter requiring 64-bits.";
  }

  grouping instant-total-stats-bits-count-group {
    leaf instant {
      type coherent-device-common-types:stat-bits-counter64-type;
      description
        "The instantaneous value of the statistic.";
    }
    uses stat-collection-time-group;
    container bin {
      uses stat-interval-group;
      leaf total {
        type coherent-device-common-types:stat-bits-counter64-type;
        description
          "The mean value of the statistic over the bin interval.";
      }
      description
        "";
    }
    description
      "Generic grouping for a statistic that is a counter requiring 32-bits.";
  }

  grouping instant-total-stats-frame-count-group {
    leaf instant {
      type coherent-device-common-types:stat-frame-counter64-type;
      description
        "The instantaneous value of the statistic.";
    }
    uses stat-collection-time-group;
    container bin {
      uses stat-interval-group;
      leaf total {
        type coherent-device-common-types:stat-frame-counter64-type;
        description
          "The mean value of the statistic over the bin interval.";
      }
      description
        "";
    }
    description
      "Generic grouping for a statistic that is a counter requiring 32-bits.";
  }

  grouping instant-interval-stats-kilometer-group {
    leaf instant {
      type coherent-device-common-types:stat-kilometer-type;
      description
        "The instantaneous value of the statistic.";
    }
    uses stat-collection-time-group;
    container bin {
      uses stat-interval-group;
      leaf avg {
        type coherent-device-common-types:stat-kilometer-type;
        description
          "The mean value of the statistic over the bin interval.";
      }
      leaf min {
        type coherent-device-common-types:stat-kilometer-type;
        description
          "The minimum value of the statistic over the bin interval.";
      }
      leaf max {
        type coherent-device-common-types:stat-kilometer-type;
        description
          "The maximum value of the statistic over the bin interval.";
      }
      uses stat-min-max-time-group;
      description
        "";
    }
    description
      "Generic grouping for a statistic with units in kilometers.";
  }

  grouping instant-interval-stats-microseconds-group {
    leaf instant {
      type coherent-device-common-types:stat-microseconds-type;
      description
        "The instantaneous value of the statistic.";
    }
    uses stat-collection-time-group;
    container bin {
      uses stat-interval-group;
      leaf avg {
        type coherent-device-common-types:stat-microseconds-type;
        description
          "The mean value of the statistic over the bin interval.";
      }
      leaf min {
        type coherent-device-common-types:stat-microseconds-type;
        description
          "The minimum value of the statistic over the bin interval.";
      }
      leaf max {
        type coherent-device-common-types:stat-microseconds-type;
        description
          "The maximum value of the statistic over the bin interval.";
      }
      uses stat-min-max-time-group;
      description
        "";
    }
    description
      "Generic grouping for a statistic with units in microseconds.";
  }

  grouping instant-interval-stats-counter64-group {
    leaf instant {
      type coherent-device-common-types:stat-counter64-type;
      description
        "The instantaneous value of the statistic.";
    }
    uses stat-collection-time-group;
    container bin {
      uses stat-interval-group;
      leaf total {
        type coherent-device-common-types:stat-counter64-type;
        description
          "The total count of the statistic over the bin interval.";
      }
      leaf avg {
        type coherent-device-common-types:stat-counter64-type;
        description
          "The mean value of the statistic over the bin interval.";
      }
      leaf min {
        type coherent-device-common-types:stat-counter64-type;
        description
          "The minimum value of the statistic over the bin interval.";
      }
      leaf max {
        type coherent-device-common-types:stat-counter64-type;
        description
          "The maximum value of the statistic over the bin interval.";
      }
      uses stat-min-max-time-group;
      description
        "";
    }
    description
      "Generic grouping for a 64-bit statistic counter.";
  }

  grouping coherent-device-statistics-cmis-modulator-bias-group {
    container modulator-bias-xi {
      uses coherent-device-statistics-types:instant-interval-stats-precision2-percent-group;
      description
        "";
      reference
        "IA OIF-C-CMIS-01.1 Table 7";
    }
    container modulator-bias-xq {
      uses coherent-device-statistics-types:instant-interval-stats-precision2-percent-group;
      description
        "";
      reference
        "IA OIF-C-CMIS-01.1 Table 7";
    }
    container modulator-bias-yi {
      uses coherent-device-statistics-types:instant-interval-stats-precision2-percent-group;
      description
        "";
      reference
        "IA OIF-C-CMIS-01.1 Table 7";
    }
    container modulator-bias-yq {
      uses coherent-device-statistics-types:instant-interval-stats-precision2-percent-group;
      description
        "";
      reference
        "IA OIF-C-CMIS-01.1 Table 7";
    }
    container modulator-bias-x-phase {
      uses coherent-device-statistics-types:instant-interval-stats-precision2-percent-group;
      description
        "";
      reference
        "IA OIF-C-CMIS-01.1 Table 7";
    }
    container modulator-bias-y-phase {
      uses coherent-device-statistics-types:instant-interval-stats-precision2-percent-group;
      description
        "";
      reference
        "IA OIF-C-CMIS-01.1 Table 7";
    }
    description
      "";
  }

  grouping device-statistics-group {
    container statistics {
      uses coherent-device-statistics-types:stat-bin-details-group;
      container temperature {
        uses coherent-device-statistics-types:instant-interval-stats-precision1-degree-c-group;
        description
          "The module temperature.";
      }
      container voltage {
        uses coherent-device-statistics-types:instant-interval-stats-precision1-volts-group;
        description
          "The module voltage monitor value.";
      }
      list lane {
        key "lane-index";
        leaf lane-index {
          type uint8 {
            range "1..max";
          }
          description
            "";
        }
        container laser-bias {
          uses coherent-device-statistics-types:instant-interval-stats-precision2-milliamps-group;
          description
            "The module voltage monitor value.";
        }
        container laser-temperature {
          uses coherent-device-statistics-types:instant-interval-stats-precision1-degree-c-group;
          description
            "The module voltage monitor value.";
        }
        uses coherent-device-statistics-cmis-modulator-bias-group;
        description
          "";
      }
      description
        "";
    }
    description
      "";
  }
}
