module ciena-pro-cluster-options {
  yang-version 1.1;
  namespace "urn:ciena:params:xml:ns:yang:ciena-pro-cluster-options";
  prefix cluster-mgmt;

  import ciena-common-version {
    prefix ciena-common-version;
  }
  import ciena-common-yang {
    prefix ciena-common-yang;
  }

  organization
    "Ciena Corporation";
  contact
    "Web URL: http://www.ciena.com/
     Postal:  7035 Ridge Road
             Hanover, Maryland 21076
             U.S.A.
     Phone:   +1 800-921-1144
     Fax:     +1 410-694-5750";
  description
    "This YANG module defines internal options used to configure the
     per-deployment behaviour of the cluster service";

  revision 2023-01-15 {
    description
      "Initial draft of pro-cluster-options yang";
    ciena-common-version:string "1.0.0";
  }

  container cluster-options {
    leaf db-supported {
      type boolean;
      default "true";
      description
        "Indicates that provisioned cluster members should be saved to a
         database.";
    }
    leaf db-name {
      type string {
        ciena-common-yang:stringptr "true";
      }
      default "cc-db";
      description
        "Indicates the name of the cluster database if it is supported.
         This is ignored if the db is not supported";
    }
  }
}
