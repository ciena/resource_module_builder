module ciena-common-test-augment {
  namespace "urn:ciena:params:xml:ns:yang:ciena-common-test-augment";
  prefix test-augment;

  import ciena-common-exceptions {
    prefix ciena-common-exceptions;
  }
  import ciena-common-test {
    prefix test;
  }
  import ciena-common-test-list {
    prefix testlist;
  }
  import ciena-common-yang {
    prefix ciena-common-yang;
  }

  organization
    "Ciena Corporation";
  contact
    "Web URL: http://www.ciena.com";
  description
    "Test module";

  revision 2022-12-21 {
    description
      "Add a multiply-augmented augmented container (the augment augments the augment).";
  }
  revision 2018-01-01 {
    description
      "Initial revision";
  }

  augment "/test:root-container" {
    container augment-container {
      leaf test {
        type uint16;
      }
    }
  }

  augment "/test:root-container/test:list-test/test:leaf-test" {
    leaf int8-test {
      type int8;
    }
  }

  augment "/test:root-container/test:list-test" {
    container leaf-test {
      leaf int8-test {
        type int8;
      }
    }
  }

  augment "/test:i_love_instance_id_for_keys/test:some_list" {
    ciena-common-yang:augment-name "augment-list";
    list augmented-list {
      key "id";
      leaf id {
        type int8;
      }
      leaf value {
        type string;
      }
    }
  }

  augment "/testlist:common-test-list/testlist:simple-string-key-augmented" {
    container augmented {
      leaf augmented {
        type uint8;
      }
    }
  }

  augment "/testlist:common-test-list/testlist:simple-string-key-augmented-list" {
    list augmented {
      key "key";
      leaf key {
        type string;
      }
      leaf augmented {
        type uint8;
      }
    }
  }

  augment "/test:multi-augment" {
    container augmented-container {
      leaf first-augment {
        type uint8;
      }
    }
  }

  augment "/test:multi-augment/test-augment:augmented-container" {
    leaf second-augment {
      type uint8;
    }
  }

  augment "/test:multi-augment/test-augment:augmented-container" {
    leaf third-augment {
      type uint8;
    }
  }

  augment "/test:root-container/test:list-test/test:action-test/test:input" {
    leaf int8-test-with-input {
      type int8;
    }
  }

  augment "/test:root-container/test:list-test/test:no-inout-action-test/test:input" {
    leaf int8-test-without-input {
      type int8;
    }
  }

  augment "/test:root-container/test:list-test/test:no-inout-action-test/test:output" {
    leaf int8-test-without-output {
      type int8;
    }
  }

  augment "/test:to-pointer-test" {
    container augmented-container {
      leaf int-leaf {
        type uint8;
      }
      leaf string-leaf {
        type string;
      }
    }
  }

  augment "/test:to-pointer-test" {
    leaf augmented-string {
      type string;
    }
  }

  augment "/test:multi-augment/test-augment:augmented-container" {
    container fourth-augment {
      leaf leaf {
        type uint8;
      }
    }
  }

  augment "/test:multi-augment/test-augment:augmented-container" {
    container fifth-augment {
      leaf leaf {
        type uint8;
      }
    }
  }
}
