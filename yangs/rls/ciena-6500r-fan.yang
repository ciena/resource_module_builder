module ciena-6500r-fan {
  yang-version 1.1;
  namespace "urn:ciena:params:xml:ns:yang:ciena-6500r-fan";
  prefix fan;

  import ciena-6500r-types {
    prefix ciena-6500r-types;
  }

  import ciena-common-version {
    prefix version;
  }

  import ciena-pro-fan {
    prefix ciena-pro-fan;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's fan object";

  revision 2021-03-25 {
    version:version "version" {
      version:string "1.0.0";
    }
    description
      "Initial version";
  }

  grouping ciena-6500r-fan-mount {
    container fans {
      list fan {
        key "name";
        uses ciena-pro-fan:fan;

        uses ciena-6500r-types:admin-state;
      }
    }
  }

  grouping ciena-6500r-fan-mount-actions;

  uses ciena-6500r-fan-mount;
}
