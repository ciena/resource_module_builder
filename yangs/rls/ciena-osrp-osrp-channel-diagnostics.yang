module ciena-osrp-osrp-channel-diagnostics {
  yang-version 1.1;
  namespace "urn:ciena:params:xml:ns:yang:ciena-osrp-osrp-channel-diagnostics";
  prefix ciena-osrp-osrp-channel-diagnostics;

  import ciena-common-yang {
    prefix ciena-common-yang;
  }
  import ciena-osrp-common-channel-diagnostics {
    prefix common-channel-diagnostics;
  }
  import ciena-common-version {
    prefix ciena-common-version;
  }

  organization
    "Ciena Corporation";
  contact
    "Web URL: http://www.ciena.com
     Postal: Ciena India Pvt. Ltd.
     Sector 32, Plot 14,
     Gurgaon 122001,
     Haryana, India";
  description
    "This module describes Ciena's OSRP end-to-end channel diagnostics data.";

  revision 2021-10-14 {
    description
      "Channel-diagnostics made config false.";
    ciena-common-version:string "1.0.1";
  }
  revision 2021-08-05 {
    description
      "Initial revision.";
    ciena-common-version:string "1.0.0";
  }

  grouping ciena-osrp-osrp-channel-diagnostics-mount-data {
    container channel-diagnostics {
      uses common-channel-diagnostics:ccs-instance-common;
      config false;
    }
  }

  grouping ciena-osrp-osrp-channel-diagnostics-mount-actions-notifs;

  grouping ciena-osrp-osrp-channel-diagnostics-mount-actions-notifs-as-cont;

  grouping ciena-osrp-osrp-channel-diagnostics-mount-data-actions-notifs-as-cont {
    container channel-diagnostics {
      uses common-channel-diagnostics:ccs-instance-common;
      config false;
    }
  }

  uses ciena-osrp-osrp-channel-diagnostics-mount-data;
}
