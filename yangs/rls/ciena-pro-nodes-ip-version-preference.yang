module ciena-pro-nodes-ip-version-preference {
  namespace "urn:ciena:params:xml:ns:yang:ciena-pro-nodes-ip-version-preference";
  prefix nodes-ip-version-preference;

  import ciena-common-version {
    prefix ciena-common-version;
  }

  organization
    "Ciena Corporation";
  contact
    "Web URL: http://www.ciena.com/
     Postal:  7035 Ridge Road
              Hanover, Maryland 21076
              U.S.A.
     Phone:   +1 800-921-1144
     Fax:     +1 410-694-5750";
  description
    "This model is used to provide options to configure
     system in IPv4 or IPv6 in dual-stack configuration.";

  revision 2023-01-13 {
    description
      "Initial revision added for RLS 3.1.";
    ciena-common-version:version "version" {
      ciena-common-version:string "1.0.0";
    }
  }

  identity version-type {
    description
      "This identity describes IP version for nodes.";
  }

  identity ipv4 {
    base version-type;
    description
      "IPv4 protocol";
  }

  identity ipv6 {
    base version-type;
    description
      "IPv6 protocol";
  }

  container node-ip-version-preference {
    description
      "Element used for specifying IPv4, or IPv6 version as preferred protocol in dual stack configuration.
       It should be configured in local as well as in remote node.";
    leaf ip-version {
      type identityref {
        base version-type;
      }
      default "ipv4";
      description
        "This identity describes IP version for neighbours.
         Default is IPv4.";
    }
  }
}
