module ciena-pro-system-health-data-driver {
  namespace "urn:ciena:params:xml:ns:yang:ciena-pro-system-health-data-driver";
  prefix health-data-driver;

  import ciena-common-version {
    prefix version;
  }

  organization
    "Ciena Corporation";
  contact
    "Web URL: http://www.ciena.com/
     Postal:  7035 Ridge Road
              Hanover, Maryland 21076
              U.S.A.
     Phone:   +1 800-921-1144
     Fax:     +1 410-694-5750";
  description
    "This module defines the system's health data driver YANG structures";

  revision 2022-05-16 {
    description
      "Initial Creation of health-data-driver yang";
    version:version "version" {
      version:string "1.0.0";
    }
  }

  grouping interface-name-map {
    description
      "Used to map external to internal interface names";
    leaf external-name {
      type string;
      description
        "External interface name";
    }
    leaf internal-name {
      type string;
      description
        "Internal interface name";
    }
  }

  rpc get-openconfig-interfaces {
    description
      "Retrieves all the provisioned openconfig-interfaces & will return a mapping of external to internal interface names";
    output {
      list interface-name-maps {
        container interface-name-map {
          description
            "External to internal interface name map entry";
          uses interface-name-map;
        }
      }
    }
  }
}
