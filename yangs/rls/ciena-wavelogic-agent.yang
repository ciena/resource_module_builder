module ciena-wavelogic-agent {
  namespace "urn:ciena:params:xml:ns:yang:ciena-wavelogic-agent";
  prefix wavelogic-agent;

  import ciena-common-version {
    prefix ciena-common-version;
  }

  organization
    "Ciena Corporation";
  contact
    "Web URL: http://www.ciena.com";
  description
    "Wavelogic Agent module";

  revision 2022-09-09 {
    description
      "Initial revision";
    ciena-common-version:string "1.0.0";
    reference
      "1.0.0";
  }

  container some-container {
    leaf some-value {
      type uint64;
    }
  }
}
