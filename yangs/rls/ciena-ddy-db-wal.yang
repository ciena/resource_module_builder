module ciena-ddy-db-wal {
  yang-version 1.1;
  namespace "urn:ciena:params:xml:ns:yang:ciena-ddy-db-wal";
  prefix db-wal;

  import ciena-common-version {
    prefix ciena-common-version;
  }
  import ciena-common-yang {
    prefix ciena-common-yang;
  }

  organization
    "Ciena Corporation";
  contact
    "Web URL: http://www.ciena.com/
     Postal:  7035 Ridge Road
             Hanover, Maryland 21076
             U.S.A.
     Phone:   +1 800-921-1144
     Fax:     +1 410-694-5750";
  description
    "Ciena Database Write Ahead Log(WAL) Yang Definitions.

     Write Ahead Log stores information about db operations in
     a file to enable features such as db recovery and rollbacks.";

  revision 2021-11-10 {
    description
      "Removed grouping for tid and used ciena-common-yang transaction-id.
       Renamed prefix for ciena-common-yang";
    ciena-common-version:string "1.2.0";
  }
  revision 2021-11-04 {
    description
      "Added grouping for transaction-id.
       Added leaf done for transaction completion";
    ciena-common-version:string "1.1.0";
  }
  revision 2021-10-06 {
    description
      "Add wal-records list";
    ciena-common-version:string "1.0.0";
  }

  grouping ddy-db-wal-group {
    list wal-records {
      description
        "WAL record is used to store the relevent data of each db operations";
      key "index";
      leaf index {
        type uint64;
      }
      list patches {
        description
          "Used to store list of diff patches that the current wal records represent";
        key "action path";
        uses ciena-common-yang:patch;
      }
      leaf done {
        description
          "flag is set to true on transaction completion";
        type boolean;
      }
      uses ciena-common-yang:transaction-id;
    }
  }
}
