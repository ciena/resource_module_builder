module ciena-pro-file-debug {
  namespace "urn:ciena:params:xml:ns:yang:ciena-pro-file-debug";
  prefix file-debug;

  import ciena-common-yang {
    prefix ciena-common-yang;
  }

  organization
    "Ciena Corporation";
  contact
    "Web URL: http://www.ciena.com/
     Postal:  7035 Ridge Road
              Hanover, Maryland 21076
              U.S.A.
     Phone:   +1 800-921-1144
     Fax:     +1 410-694-5750";
  description
    "This model captures debug RPCs for manipulating file operations.";

  revision 2023-01-20 {
    description
      "Initial Revision";
  }

  rpc pro-file-debug {
    input {
      leaf enable-xftp-verbose-logs {
        type boolean;
        description
          "Enable verbose logs for XFTP file transfer operations.";
      }
      leaf enable-unsecure-https {
        type boolean;
        description
          "Enable unscured version of HTTPS.";
      }
    }
    output {
      list return-code-list {
        uses ciena-common-yang:return-code;
      }
    }
  }
}
