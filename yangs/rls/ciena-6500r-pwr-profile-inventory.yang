module ciena-6500r-pwr-profile-inventory {
  namespace "urn:ciena:params:xml:ns:yang:ciena-6500r-pwr-profile-inventory";
  prefix pwr-profile-inventory;

  import ciena-6500r-pwr-profile {
    prefix pwr-profile;
  }
  import ciena-common-version {
    prefix version;
  }
  import ciena-6500r-types {
    prefix ciena-6500r-types;
  }

  organization
    "Ciena Corporation";
  contact
    "Web URL: http://www.ciena.com/
      Postal:  7035 Ridge Road
              Hanover, Maryland 21076
              U.S.A.
      Phone:   +1 800-921-1144
      Fax:     +1 410-694-5750";

  revision 2021-06-04 {
    description
      "6500r-series Release 2.4
       Initial revision";
    version:version "version" {
      version:string "1.0.0";
    }
  }

  list diagnostic-inventory {
    key "name";
    leaf name {
      type string;
      description
        "Name of the Profile Tracking Entry";
    }
    list pwr-profile {
      key "parent-port name";
      uses pwr-profile:pwr-profile-grouping;
    }
  }
}
