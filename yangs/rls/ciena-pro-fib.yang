module ciena-pro-fib {
  namespace "urn:ciena:params:xml:ns:yang:ciena-pro-fib";
  prefix ciena-pro-fib;

  import ciena-common-version {
    prefix ciena-common-version;
  }

  import openconfig-inet-types {
    prefix oc-inet;
  }

  import openconfig-network-instance {
    prefix oc-ni;
  }

  include "ciena-pro-fib-common";

  organization
    "Ciena Corporation";
  contact
    "Web URL: http://www.ciena.com/";
  description
    "Ciena forwarding information base";

  revision 2019-09-17 {
    ciena-common-version:string "1.0.0";
    description
      "Initial version";
  }

  grouping fib-ipv4-unicast-structural {
    description
      "Structural grouping defining the schema for the IPv4 unicast
       forwarding table.";
    list ipv4-entry {
      key "prefix";
      config false;
      description
        "List of the IPv4 unicast entries within the
         forwarding table. This list is keyed by the destination IPv4
         prefix.";
      leaf prefix {
        type leafref {
          path "../state/prefix";
        }
        config false;
        description
          "Reference to the IPv4 unicast destination prefix which
           must be matched to utilise the FIB entry.";
      }

      container state {
        config false;
        description
          "Operational state parameters for the IPv4 unicast FIB
           entry.";
        leaf prefix {
          type oc-inet:ipv4-prefix;
          description
            "The IPv4 destination prefix that should be matched to
             utilise the FIB entry.";
        }

        uses fib-common-entry-state;
      }
    }
  }

  grouping fib-ipv6-unicast-structural {
    description
      "Structural grouping defining the schema for the IPv6 unicast
       forwarding table.";
    list ipv6-entry {
      key "prefix";
      config false;
      description
        "List of the IPv6 unicast entries within the
         forwarding table. This list is keyed by the destination IPv6
         prefix.";
      leaf prefix {
        type leafref {
          path "../state/prefix";
        }
        config false;
        description
          "Reference to the IPv6 unicast destination prefix which
           must be matched to utilise the FIB entry.";
      }

      container state {
        config false;
        description
          "Operational state parameters for the IPv6 unicast FIB
           entry.";
        leaf prefix {
          type oc-inet:ipv6-prefix;
          description
            "The IPv6 destination prefix that should be matched to
             utilise the FIB entry.";
        }

        uses fib-common-entry-state;
      }
    }
  }

  grouping fib-top {
    description
      "Top-level grouping allowing per-protocol instantiation of the
       FIB.";
    container fibs {
      config false;
      description
        "The forwarding information base (FIBs) that are associated
         with the network instance. An FIB is instantiated per-protocol
         running within the network-instance - such that one exists for
         IPv4 Unicast, IPv6 Unicast, MPLS, L2 forwarding entries, etc.
         A forwarding entry within the FIB has a set of next-hops,
         which may be a reference to an entry within another table -
         e.g., where a Layer 3 next-hop has an associated Layer 2
         forwarding entry.";
      container ipv4-unicast {
        config false;
        description
          "The abstract forwarding table for IPv4 unicast. Entries
           within this table are uniquely keyed on the IPv4 unicast
           destination prefix which is matched by ingress packets.

           The data set represented by the IPv4 Unicast FIB is the set
           of entries from the IPv4 unicast RIB that have been selected
           for installation into the FIB of the device exporting the
           data structure.";
        uses fib-ipv4-unicast-structural;
      }

      container ipv6-unicast {
        config false;
        description
          "The abstract forwarding table for IPv6 unicast. Entries
           within this table are uniquely keyed on the IPv6 unicast
           destination prefix which is matched by ingress packets.

           The data set represented by the IPv6 Unicast FIB is the set
           of entries within the IPv6 RIB that ";
        uses fib-ipv6-unicast-structural;
      }

      uses fib-next-hop-groups-structural;

      uses fib-nhop-structural;
    }
  }

  augment "/oc-ni:network-instances/oc-ni:network-instance" {
    description
      "Add FIB to each network instance.";
    uses fib-top;
  }
}
