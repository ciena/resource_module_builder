module ciena-6500r-cv-results {
  namespace "urn:ciena:params:xml:ns:yang:ciena-6500r-cv-results";
  prefix cv;

  import ciena-6500r-types {
    prefix ciena-6500r-types;
  }

  import ciena-common-version {
    prefix version;
  }

  import ietf-yang-types {
    prefix yang;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's 6500r platform connection validation service consolidated results";

  revision 2021-06-18 {
    version:version "version" {
      version:string "1.2.0";
    }
    description
      "Marking cv-results as config false";
  }
  revision 2020-12-01 {
    version:version "version" {
      version:string "1.1.0";
    }
    description
      "Adding expected/actual-system-name in cv-results";
  }
  revision 2020-07-21 {
    version:version "version" {
      version:string "1.0.0";
    }
    description
      "Initial revision";
  }

  container cv-results {
    config false;
    list cv-rx-ports {
      key "slot port";
      leaf slot {
        type ciena-6500r-types:object-name;
        description
          "The name of the slot.";
      }

      leaf port {
        type ciena-6500r-types:object-name;
        description
          "The name of the port.";
      }

      leaf status {
        type enumeration {
          enum "scanning" {
            description
              "Connection validation is scanning the given port";
          }
          enum "pass" {
            description
              "Connection Validation has passed on the given port.";
          }
          enum "fail" {
            description
              "Connection Validation has failed on the given port.";
          }
          enum "not-in-use" {
            description
              "The given port is not in use by Connection validation";
          }
        }
        description
          "Status of Connection Validation on the given port.";
      }

      leaf reason {
        type string;
        description
          "Reason for the status obtained. It may contain one or more conditions.
           All of the applicable ones will be displayed.  These reasons are:
           CV Data Missing, CV Data Mismatch, High Fiber Loss, Fiber Break Suspected.";
      }

      leaf last-validated {
        type yang:date-and-time;
        description
          "The last time CV status validated.";
      }

      leaf last-status-changed {
        type yang:date-and-time;
        description
          "The last time CV status changed.";
      }

      leaf expected-port-id {
        type string;
        description
          "Expected port id from the far-end tx port.";
      }

      leaf actual-port-id {
        type string;
        description
          "Actual port id from the far-end tx port.";
      }

      leaf link-identifier {
        type string;
        description
          "The link that has given cv rx port as To port.";
      }

      leaf expected-physical-loss {
        type ciena-6500r-types:loss-dB-1-precision;
        description
          "overall expected loss of the given link.";
      }

      leaf measured-physical-loss {
        type ciena-6500r-types:loss-dB-1-precision;
        description
          "The physical loss of the given link derived from power measurement";
      }

      leaf expected-system-name {
        type string;
        description
          "Expected system name from the far-end tx port.";
      }

      leaf actual-system-name {
        type string;
        description
          "Actual system name from the far-end tx port.";
      }
    }
  }
}
