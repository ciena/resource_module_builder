module ciena-common-test-list {
  yang-version 1.1;
  namespace "urn:ciena:params:xml:ns:yang:ciena-common-test-list";
  prefix tl;

  import ciena-common-yang {
    prefix ciena-common-yang;
  }

  organization
    "Ciena Corporation";
  contact
    "Web URL: http://www.ciena.com";
  description
    "A module to test variations on lists for DDF. These lists are intended to
     be used to test features of the generator, serializer and other parts of
     the framework";

  revision 2023-12-22 {
    description
      "Adding bool-test and string-test leaf in simple-keyless list";
  }
  revision 2021-10-28 {
    description
      "Adding list with bits as key and bits typedef";
  }
  revision 2019-10-25 {
    description
      "Initial revision";
  }

  identity base-key {
    description
      "A base identity, currently used for key testing";
  }

  identity derived-key-1 {
    base base-key;
  }

  grouping ciena-common-test-list-mount-data {
    container common-test-list {
      description
        "Container to group all of the test list variations.";
      list simple-string-key {
        key "name";
        description
          "The simplest of lists; with a string key.";
        leaf name {
          type string;
        }
      }
      list simple-string-key-augmented {
        key "name";
        description
          "The simplest of lists; now augmented with a container
           (see ciena-common-test-augment.yang)";
        leaf name {
          type string;
        }
      }
      list simple-string-key-augmented-list {
        key "name";
        description
          "The simplest of lists; now augmented with a container
           (see ciena-common-test-augment.yang)";
        leaf name {
          type string;
        }
      }
      list simple-int-key {
        key "index";
        description
          "The simplest of lists; with an integer key.";
        leaf index {
          type int32;
        }
      }
      typedef test-bits {
        type bits {
          bit BIT0 {
            position 0;
          }
          bit BIT1 {
            position 1;
          }
          bit BIT2 {
            position 2;
          }
          bit BIT3 {
            position 3;
          }
          bit TOTAL {
            position 4;
          }
        }
      }

      list simple-bits-key {
        key "bits-test";
        leaf bits-test {
          type test-bits;
          description
            "A simple list that has a bits field as a key.";
        }
      }
      list simple-keyless {
        config false;
        description
          "The simplest of lists; with no keys.";
        leaf not-a-key {
          type int32;
        }
        leaf bool-test {
          type boolean;
        }
        leaf string-test {
          type string;
        }
      }
      list simple-multi-key {
        key "name index";
        description
          "The simplest of lists; with 2 keys of mixed type.";
        leaf name {
          type string;
        }
        leaf index {
          type uint64;
        }
      }
      list simple-instance-id-key {
        key "instance";
        description
          "The simplest of lists; with an instance-identifier as a key.";
        leaf instance {
          type instance-identifier;
        }
      }
      list compound-instance-id-key {
        key "instance";
        description
          "A nested list with an outer instance-id key";
        leaf instance {
          type instance-identifier;
        }
        list inner {
          key "integer";
          leaf integer {
            type int32;
          }
        }
      }
      list simple-identityref-key {
        key "key";
        description
          "A simple list with an identityref as a key.";
        leaf key {
          type identityref {
            base base-key;
          }
        }
        leaf value {
          type uint32;
        }
      }
      list compound {
        key "name";
        description
          "A compound list that represents a 'typical' list in YANG: one that
           has a key, some top-level leafs and some containers with further
           leafs in them.
          ";
        leaf name {
          type string;
        }
        leaf label {
          type string;
        }
        leaf priority {
          type int64;
        }
        container topic-1 {
          leaf details {
            type string;
          }
        }
        container topic-2 {
          leaf details {
            type string;
          }
        }
      }
      list nested {
        key "name";
        description
          "A nested compound list that contains some leaves and a 'compound'
           list. Not using groupings to avoid testing too many features at once.";
        leaf name {
          type string;
        }
        leaf priority {
          type uint64;
        }
        list compound {
          key "name";
          description
            "A compound list that represents a 'typical' list in YANG: one that
             has a key, some top-level leafs and some containers with further
             leafs in them.
            ";
          leaf name {
            type string;
          }
          leaf label {
            type string;
          }
          leaf priority {
            type int64;
          }
          container topic-1 {
            leaf details {
              type string;
            }
          }
          container topic-2 {
            leaf details {
              type string;
            }
          }
        }
      }
    }
  }

  grouping ciena-common-test-list-mount-actions-notifs;

  grouping ciena-common-test-list-mount-actions-notifs-as-cont;

  grouping ciena-common-test-list-mount-data-actions-notifs-as-cont {
    container common-test-list {
      description
        "Container to group all of the test list variations.";
      list simple-string-key {
        key "name";
        description
          "The simplest of lists; with a string key.";
        leaf name {
          type string;
        }
      }
      list simple-string-key-augmented {
        key "name";
        description
          "The simplest of lists; now augmented with a container
           (see ciena-common-test-augment.yang)";
        leaf name {
          type string;
        }
      }
      list simple-string-key-augmented-list {
        key "name";
        description
          "The simplest of lists; now augmented with a container
           (see ciena-common-test-augment.yang)";
        leaf name {
          type string;
        }
      }
      list simple-int-key {
        key "index";
        description
          "The simplest of lists; with an integer key.";
        leaf index {
          type int32;
        }
      }
      typedef test-bits {
        type bits {
          bit BIT0 {
            position 0;
          }
          bit BIT1 {
            position 1;
          }
          bit BIT2 {
            position 2;
          }
          bit BIT3 {
            position 3;
          }
          bit TOTAL {
            position 4;
          }
        }
      }

      list simple-bits-key {
        key "bits-test";
        leaf bits-test {
          type test-bits;
          description
            "A simple list that has a bits field as a key.";
        }
      }
      list simple-keyless {
        config false;
        description
          "The simplest of lists; with no keys.";
        leaf not-a-key {
          type int32;
        }
        leaf bool-test {
          type boolean;
        }
        leaf string-test {
          type string;
        }
      }
      list simple-multi-key {
        key "name index";
        description
          "The simplest of lists; with 2 keys of mixed type.";
        leaf name {
          type string;
        }
        leaf index {
          type uint64;
        }
      }
      list simple-instance-id-key {
        key "instance";
        description
          "The simplest of lists; with an instance-identifier as a key.";
        leaf instance {
          type instance-identifier;
        }
      }
      list compound-instance-id-key {
        key "instance";
        description
          "A nested list with an outer instance-id key";
        leaf instance {
          type instance-identifier;
        }
        list inner {
          key "integer";
          leaf integer {
            type int32;
          }
        }
      }
      list simple-identityref-key {
        key "key";
        description
          "A simple list with an identityref as a key.";
        leaf key {
          type identityref {
            base base-key;
          }
        }
        leaf value {
          type uint32;
        }
      }
      list compound {
        key "name";
        description
          "A compound list that represents a 'typical' list in YANG: one that
           has a key, some top-level leafs and some containers with further
           leafs in them.
          ";
        leaf name {
          type string;
        }
        leaf label {
          type string;
        }
        leaf priority {
          type int64;
        }
        container topic-1 {
          leaf details {
            type string;
          }
        }
        container topic-2 {
          leaf details {
            type string;
          }
        }
      }
      list nested {
        key "name";
        description
          "A nested compound list that contains some leaves and a 'compound'
           list. Not using groupings to avoid testing too many features at once.";
        leaf name {
          type string;
        }
        leaf priority {
          type uint64;
        }
        list compound {
          key "name";
          description
            "A compound list that represents a 'typical' list in YANG: one that
             has a key, some top-level leafs and some containers with further
             leafs in them.
            ";
          leaf name {
            type string;
          }
          leaf label {
            type string;
          }
          leaf priority {
            type int64;
          }
          container topic-1 {
            leaf details {
              type string;
            }
          }
          container topic-2 {
            leaf details {
              type string;
            }
          }
        }
      }
    }
  }

  uses ciena-common-test-list-mount-data;
}
