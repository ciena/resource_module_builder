module ciena-pro-grpc-system-options {
  namespace "urn:ciena:params:xml:ns:yang:ciena-pro-grpc-system-options";
  prefix ciena-pro-grpc-system-options;

  import ciena-common-version {
    prefix version;
  }
  import ciena-pro-grpc {
    prefix grpc;
  }

  organization
    "Ciena Corporation";
  contact
    "Web URL: http://www.ciena.com/
     Postal:  7035 Ridge Road
             Hanover, Maryland 21076
             U.S.A.
     Phone:   +1 800-921-1144
     Fax:     +1 410-694-5750";
  description
    "This module describes gNMI/gRPC deployment wide options.";

  revision 2023-10-23 {
    description
      "Add feature support flags.
       Adding leaf for maximum streaming telemetry sessions.";
    version:version "version" {
      version:string "1.3.0";
    }
  }
  revision 2023-03-07 {
    description
      "Added dialout options as container";
    version:version "version" {
      version:string "1.2.0";
    }
  }
  revision 2023-01-20 {
    description
      "Add device & ca certificate path leafs..";
    version:version "version" {
      version:string "1.1.0";
    }
  }
  revision 2022-08-17 {
    description
      "initial version.";
    version:version "version" {
      version:string "1.0.0";
    }
  }

  container grpc-system-options {
    leaf async-thread-count {
      type uint8;
      description
        "total number of threads for async request.";
      default "3";
      config true;
    }
    leaf device-certificate-path {
      type string;
      description
        "Location of device certificates. security-options value
         takes priority if present.";
      default "/var/opt/ssl/dev/";
    }
    leaf ca-certificate-path {
      type string;
      description
        "Location of ca certificates. security-options value
         takes priority if present.";
      default "/var/opt/ssl/ca/";
    }
    leaf gnoi-state {
      type grpc:status-type;
      description
        "Flag to enable/disable gNOI feature support.";
      default "enable";
    }
    leaf sonic-dialout-state {
      type grpc:status-type;
      description
        "Flag to enable/disable dialout feature support.";
      default "enable";
    }
    leaf mutualauth-state {
      type grpc:status-type;
      description
        "Flag to enable/disable mutual authentication feature support.";
      default "enable";
    }
    leaf grpc-max-streaming-sessions {
      type uint8;
      description
        "Maximum gRPC streaming network telemetry sessions allowed";
      default "10";
    }
    container grpc-dialout-options {
      leaf authentication-type {
        type enumeration {
          enum insecure;
          enum one-way-auth;
          enum mutual-auth;
        }
        description
          "dialout client needs to connect in insecure/secure one way authentication/mutual authentication mode";
        default "mutual-auth";
      }
      leaf keepalive-time {
        type uint32;
        description
          "controls the period (in milliseconds) after which a keepalive ping is sent.";
      }
      leaf keepalive-timeout {
        type uint32;
        description
          "controls the amount of time (in milliseconds) the sender of the keepalive ping waits for an acknowledgement.";
      }
    }
  }
}
