module ciena-pro-demoMgr {
  namespace "urn:ciena:params:xml:ns:yang:ciena-pro-demoMgr";
  prefix demoMgr;

  import ciena-common-version {
    prefix ciena-common-version;
  }

  organization
    "Ciena Corporation";
  contact
    "Web URL: http://www.ciena.com";
  description
    "Training module";

  revision 2020-01-20 {
    description
      "Add RPC to get diag data";
    ciena-common-version:string "1.1.0";
  }
  revision 2018-01-01 {
    description
      "Initial revision";
    ciena-common-version:string "1.0.0";
  }

  typedef card-type {
    type enumeration {
      enum RLA;
      enum TPS;
      enum DLM;
    }
  }

  typedef form-factor-type {
    type enumeration {
      enum 1x;
      enum 2x;
      enum 3x;
    }
  }

  container demo-shelf {
    config true;
    leaf name {
      type string;
    }
    list slots {
      key "slot-no";
      leaf slot-no {
        type uint32;
      }
      leaf type {
        type card-type;
      }
      leaf PEC {
        type string;
      }
      leaf form-factor {
        type form-factor-type;
      }
      list ports {
        key "port-no";
        leaf port-no {
          type uint32;
        }
        leaf PEC {
          type string;
        }
        leaf pkt-tx {
          type uint64;
          description
            "Number of tx packets";
        }
        leaf pkt-rx {
          type uint64;
          description
            "Number of rx packets";
        }
      }
    }
  }
}
