module ciena-common-debug-lorem-ipsum {
  namespace "urn:ciena:params:xml:ns:yang:ciena-common-debug-lorem-ipsum";
  prefix lorem-ipsum;

  import ciena-common-version {
    prefix version;
  }

  organization
    "Ciena Corporation";
  contact
    "Web URL: http://www.ciena.com/
     Postal:  7035 Ridge Road
             Hanover, Maryland 21076
             U.S.A.
     Phone:   +1 800-921-1144
     Fax:     +1 410-694-5750";
  description
    "Service to provide random sample data for yang models.";

  revision 2020-09-07 {
    description
      "Initial revision.";
    version:version "version" {
      version:string "1.0.0";
    }
  }

  list lorem-ipsum {
    description
      "A self generated tree of sample data.  This is non-standard yang since the
       tree is generated based on the input parameters only and cannot
       be queried from above the 'data' node.  This is useful for getting test
       data from nodes in a tree and is organized as an 'anyxml' node
       so that the yang-get-object semantics like filtering and paging
       can be applied easily.";
    config false;
    key "size fill seed";
    leaf size {
      type uint16;
      description
        "Specifies the average size of the list elements in the generated tree.
         The sizes of the lists are randomly generated from a poisson
         distribution around this mean.  Default is 10.";
    }
    leaf fill {
      type uint8 {
        range "1..100";
      }
      description
        "Specifies the fill percentage of the generated tree.  Default is 50.";
    }
    leaf seed {
      type uint64;
      description
        "Specifies the seed to use for randomness to allow for tree
         cloning.  Default is the time.";
    }
    anyxml data;
  }
}
