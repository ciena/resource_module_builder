module ciena-6500r-rx-proxy {
  yang-version 1.1;
  namespace "urn:ciena:params:xml:ns:yang:ciena-6500r-rx-proxy";
  prefix rx-proxy;

  import ciena-6500r-types {
    prefix ciena-6500r-types;
  }

  import ciena-common-version {
    prefix version;
  }

  import ciena-6500r-ports {
    prefix ports;
  }

  import ciena-pro-rx-proxy {
    prefix ciena-pro-rx-proxy;
  }

  organization
    "Ciena Corporation";
  contact
    "Web URL: http://www.ciena.com/
     Postal:  7035 Ridge Road
             Hanover, Maryland 21076
             U.S.A.
     Phone:   +1 800-921-1144
     Fax:     +1 410-694-5750";
  description
    "This module describes Ciena's receiver proxy data model for the RLS platform, first introduced in RLS 2.0";

  revision 2021-04-22 {
    version:version "version" {
      version:string "0.0.5";
    }
    description
      "Create rx-proxy-grouping";
  }
  revision 2020-09-08 {
    version:version "version" {
      version:string "0.0.4";
    }
    description
      "Use ciena-pro-rx-proxy";
  }
  revision 2020-06-30 {
    version:version "version" {
      version:string "0.0.3";
    }
    description
      "Fix version formating";
  }
  revision 2020-01-22 {
    version:version "version" {
      version:string "0.0.2";
    }
    description
      "Added target-psd parameter.";
  }
  revision 2019-11-27 {
    version:version "version" {
      version:string "0.0.1";
    }
    description
      "Initial Revision.";
  }

  grouping rx-proxy-grouping {
    uses ciena-pro-rx-proxy:rx-proxy;

    leaf parent-port {
      type leafref {
        path "/ports:port/ports:name";
      }
      mandatory true;
      description
        "Receiver proxy facility parent port.";
    }
  }

  grouping ciena-6500r-rx-proxy-mount {
    list rx-proxy {
      key "name";
      uses rx-proxy-grouping;
    }
  }

  grouping ciena-6500r-rx-proxy-mount-actions;

  uses ciena-6500r-rx-proxy-mount;
}
