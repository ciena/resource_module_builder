module ciena-pro-pm-internal-interface {
  namespace "urn:ciena:params:xml:ns:yang:ciena-pro-pm-internal-interface";
  prefix pm-driver-interface;

  import ciena-common-version {
    prefix ciena-common-version;
  }
  import ciena-pro-pm-types {
    prefix pm-types;
  }

  organization
    "Ciena Corporation";
  contact
    "Web URL: http://www.ciena.com";
  description
    "This module describes Ciena's pm runtime objects for the Bifrost platform";

  revision 2023-01-23 {
    description
      "Add invoke-custom-read-roll RPC";
    ciena-common-version:string "1.1.1";
  }
  revision 2023-01-23 {
    description
      "Add Reset RPC for reset PM function";
    ciena-common-version:string "1.1.0";
  }
  revision 2022-10-07 {
    description
      "Add test otn instance init";
    ciena-common-version:string "1.0.0";
  }
  revision 2022-02-27 {
    description
      "Initial revision";
  }

  rpc update-template-data {
    input {
      leaf name {
        type string;
      }
      anyxml data {
        description
          "This data tree represents updated template data.";
      }
    }
    output {
      anyxml data {
        description
          "This data tree represents updated template data.";
      }
    }
  }

  rpc test-otn-instance-init {
    input {
      leaf flag {
        type uint32;
      }
    }
  }

  rpc reset-pm-counters {
    input {
      leaf pm-resource-instance {
        type instance-identifier;
      }
      leaf interval {
        type pm-types:current-interval;
      }
      leaf reset-all-instances {
        type boolean;
        description
          "reset all seconds count instances";
      }
    }
  }

  rpc invoke-custom-read-roll {
    output {
      leaf return_code {
        type uint32;
        description
          "success or failure";
      }
    }
    description
      "Invoke read and roll custom PM before end of interval";
  }
}
