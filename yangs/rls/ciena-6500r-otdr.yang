module ciena-6500r-otdr {
  yang-version 1.1;
  namespace "urn:ciena:params:xml:ns:yang:ciena-6500r-otdr";
  prefix otdr;

  import ciena-6500r-types {
    prefix ciena-6500r-types;
  }

  import ciena-6500r-ports {
    prefix ports;
  }

  import ciena-pro-fiber-types {
    prefix fiber-types;
  }

  import ietf-yang-types {
    prefix yang;
  }

  import ciena-common-version {
    prefix version;
  }

  import ciena-6500r-local-fault {
    prefix ciena-6500r-local-fault;
  }

  organization
    "Ciena Corporation";
  contact
    "Web URL: http://www.ciena.com/
     Postal:  7035 Ridge Road
             Hanover, Maryland 21076
             U.S.A.
     Phone:   +1 800-921-1144
     Fax:     +1 410-694-5750";
  description
    "This module describes Ciena's otdr object for the 6500 RLS platform";

  revision 2021-05-17 {
    version:version "version" {
      version:string "1.12.0";
    }
    description
      "Modified otdr-instance with latest MIB changes";
  }
  revision 2021-05-13 {
    version:version "version" {
      version:string "1.11.0";
    }
    description
      "Add otdr-instance for FLM mirror configuration and inventory querying";
  }
  revision 2021-04-22 {
    version:version "version" {
      version:string "1.10.0";
    }
    description
      "FLM trace handshaking enhancements";
  }
  revision 2021-03-31 {
    version:version "version" {
      version:string "1.9.0";
    }
    description
      "Added rpc results: missing-traces-for-override, remote-port-communication-error.
       Added force option to set-baseline-otdr-trace.
       Added reason option to override-nogo.";
  }
  revision 2021-02-25 {
    version:version "version" {
      version:string "1.8.0";
    }
    description
      "New enum values for FLM traces: card-if-trace-type_t, request-trace-type_t, trace-type_t";
  }
  revision 2020-11-25 {
    version:version "version" {
      version:string "1.7.0";
    }
    description
      "New gonogo_t enum values to match snmp mib OtdrGoNogoStatus.";
  }
  revision 2020-11-13 {
    version:version "version" {
      version:string "1.6.0";
    }
    description
      "New handshaking state no-remote-otdr.
       No migration escape required.";
  }
  revision 2020-11-12 {
    version:version "version" {
      version:string "1.5.0";
    }
    description
      "Add event-status. Remove defaults for loss-threshold-single,
       loss-threshold-all, reflection-threshold-single, reflection-threshold-all.
       No migration escapes are required. New values will migrate without a checklist.";
  }
  revision 2020-09-22 {
    version:version "version" {
      version:string "1.4.0";
    }
    description
      "Adding trace event comment to show effective loss.";
  }
  revision 2020-07-17 {
    version:version "version" {
      version:string "1.3.0";
    }
    description
      "Adding sor-file to trace-response-group.
       No migration escape required, otdr-svc code will auto-populate data";
  }
  revision 2020-07-15 {
    version:version "version" {
      version:string "1.2.2";
    }
    description
      "Adding automatic long/short/office traces to card-if-trace-type_t.";
  }
  revision 2020-06-30 {
    version:version "version" {
      version:string "1.2.1";
    }
    description
      "Fix config false parameters. Fix version numbering.";
  }
  revision 2020-06-10 {
    version:version "version" {
      version:string "1.2.0";
    }
    description
      "Removed config false for parameters that should be saved in datastore.";
  }
  revision 2020-06-08 {
    version:version "version" {
      version:string "1.1.0";
    }
    description
      "Update typedef event-type_t to add the new enum values";
  }
  revision 2020-03-18 {
    version:version "version" {
      version:string "1.0.11";
    }
    description
      "OTDR raman information";
  }
  revision 2020-02-22 {
    version:version "version" {
      version:string "1.0.10";
    }
    description
      "Added OTDR diagnostic warnings and monitored diag points";
  }
  revision 2020-02-08 {
    version:version "version" {
      version:string "1.0.9";
    }
    description
      "Intro of rpc override-nogo";
  }
  revision 2020-01-29 {
    version:version "version" {
      version:string "1.0.8";
    }
    description
      "Intro of event type saturated";
  }
  revision 2020-01-24 {
    version:version "version" {
      version:string "1.0.7";
    }
    description
      "Circuit pack mismatch response.
       Changed session-name to pfg-name.";
  }
  revision 2020-01-20 {
    version:version "version" {
      version:string "1.0.6";
    }
    description
      "Extra OTDR handshaking diagnostics";
  }
  revision 2020-01-20 {
    version:version "version" {
      version:string "1.0.5";
    }
    description
      "Intro of nogo-leadin-office";
  }
  revision 2020-01-06 {
    version:version "version" {
      version:string "1.0.4";
    }
    description
      "Support OTDR handshaking and improve OTDR diagnostics";
  }
  revision 2019-12-09 {
    version:version "version" {
      version:string "1.0.3";
    }
    description
      "Align gonogo_t with the mib OtdrGoNogoStatus";
  }
  revision 2019-11-28 {
    version:version "version" {
      version:string "1.0.2";
    }
    description
      "OTDR trace type and card interface trace type restructuring";
  }
  revision 2019-09-19 {
    version:version "version" {
      version:string "1.0.1";
    }
    description
      "Manual Go/No-Go support";
  }
  revision 2019-09-09 {
    version:version "version" {
      version:string "1.0.1";
    }
    description
      "Added loss-threshold-single, loss-threshold-all,
       reflection-threshold-single and reflection-threshold-all.";
  }
  revision 2019-05-10 {
    version:version "version" {
      version:string "1.0.0";
    }
    description
      "Added additional info for alarms";
  }
  revision 2018-01-01 {
    description
      "RLS Release 1.0";
  }

  typedef card-if-trace-type_t {
    type enumeration {
      enum "unknown" {
        value 0;
        description
          "To align with snmp mib";
      }
      enum "long" {
        value 1;
        description
          "Manual long trace";
      }
      enum "short" {
        value 2;
        description
          "Manual short trace";
      }
      enum "office" {
        value 3;
        description
          "Manual office trace";
      }
      enum "gonogo" {
        value 4;
        description
          "gonogo trace. Not used";
      }
      enum "gonogo-long" {
        value 5;
        description
          "Long gonogo trace. Used for both manual and automatic go/nogo traces.";
      }
      enum "gonogo-short" {
        value 6;
        description
          "Short gonogo trace. Used for both manual and automatic go/nogo traces.";
      }
      enum "gonogo-office" {
        value 7;
        description
          "Office gonogo trace. Used for both manual and automatic go/nogo traces.";
      }
      enum "auto-long" {
        value 8;
        description
          "Long automatic trace";
      }
      enum "auto-short" {
        value 9;
        description
          "Short automatic trace";
      }
      enum "auto-office" {
        value 10;
        description
          "Office automatic trace";
      }
      enum "flm-with-mirror" {
        value 11;
        description
          "FLM trace measurement with mirror";
      }
      enum "flm-no-mirror" {
        value 12;
        description
          "FLM trace measurement without mirror";
      }
    }
    description
      "The type of trace to be measured";
  }

  typedef request-trace-type_t {
    type enumeration {
      enum "long" {
        description
          "Long trace";
      }
      enum "short" {
        description
          "Short trace";
      }
      enum "office" {
        description
          "Office trace";
      }
      enum "all" {
        description
          "Long, short and Office traces";
      }
      enum "go-nogo" {
        description
          "Long, short and office traces with Go/No Go evaluation.
           On a start trace, this will enable the Raman pump when
           the long, short and office traces are a Go.
           On a stop trace, it has the same behavior as stopping long, short and office traces.
           'go-nogo' is only valid on Rx ports.";
      }
      enum "flm" {
        description
          "OTDR Fiber Length Measurement (FLM) request, this will execute an OTDR trace with
           the remote mirror turned on and a subsequent trace with the remote mirror turned off.
           Both traces will be processed together to calculate the measured fiber length.";
      }
    }
    description
      "The type of traces being requested";
  }

  typedef trace-type_t {
    type enumeration {
      enum "long" {
        value 1;
        description
          "Long trace";
      }
      enum "short" {
        value 2;
        description
          "Short trace";
      }
      enum "office" {
        value 3;
        description
          "Office trace";
      }
      enum "flm-with-mirror" {
        value 4;
        description
          "Fiber Length Measurement (FLM) trace with the remote mirror turned on";
      }
      enum "flm-no-mirror" {
        value 5;
        description
          "Fiber Length Measurement (FLM) trace with the remote mirror turned off";
      }
    }
    description
      "The type of trace measured";
  }

  typedef requestor_t {
    type enumeration {
      enum "raman-go-nogo" {
        value 0;
        description
          "Raman card go-nogo trace condition detected.
           This includes a raman slot cold restart detection or
           a raman slot warm restart with a previous trace result of no-go";
      }
      enum "olf-clear" {
        value 1;
        description
          "OLF has been cleared";
      }
      enum "rdi-clear" {
        value 2;
        description
          "RDI has been cleared";
      }
      enum "olf-set" {
        value 3;
        description
          "OLF has been set";
      }
      enum "rdi-set" {
        value 4;
        description
          "RDI has been set";
      }
      enum "user-request" {
        value 5;
        description
          "Manual user requested trace";
      }
      enum "no-baseline" {
        value 6;
        description
          "No OTDR baseline or current trace detected";
      }
      enum "none" {
        value 7;
        description
          "No OTDR trace has been requested";
      }
    }
    description
      "What triggered the OTDR trace request.
       If multiple requestors requested the same trace,
       then the requestor with the highest trace priority is selected";
  }

  typedef handshaking-state_t {
    type enumeration {
      enum "discovery" {
        description
          "Initial handshaking.
           Remote handshaking data has not been received.";
      }
      enum "trace-running-no-peer" {
        description
          "Initial handshaking is not complete and a local
           trace is running without handshake.";
      }
      enum "discovered" {
        description
          "Received initial handshaking data.";
      }
      enum "discovered-acked" {
        description
          "Received initial handshaking data.
           Peer already discovered the local OTDR.";
      }
      enum "idle" {
        description
          "Initial handshaking discovery complete, no trace or trace requests in progress.";
      }
      enum "trace-request" {
        description
          "Local OTDR service is requesting to execute a trace to the remote OTDR";
      }
      enum "trace-running" {
        description
          "Local OTDR service is running a trace";
      }
      enum "trace-running-no-handshake" {
        description
          "Local OTDR service is running a trace without handshake";
      }
      enum "trace-done" {
        description
          "Local OTDR service completed running a trace.
           Waiting for acknowledgement from remote end.";
      }
      enum "peer-tracing" {
        description
          "Remote OTDR service is running a trace.";
      }
      enum "simultaneous-tracing" {
        description
          "Local and remote OTDR service is currently running a trace.";
      }
      enum "no-remote-otdr" {
        description
          "The remote OTDR port does not have any OTDR facility.";
      }
      enum "trace-with-mirror-request" {
        description
          "Local OTDR service is requesting to execute a trace with mirror to the remote OTDR";
      }
      enum "trace-with-mirror-running" {
        description
          "Local OTDR service is executing a trace with the mirror set at the remote OTDR";
      }
      enum "remote-tracing-with-mirror-requested" {
        description
          "Remote OTDR service has requested to execute a trace with the local mirror.
           The local OTDR service has not yet configured the mirror towards this port.";
      }
      enum "remote-tracing-with-mirror" {
        description
          "Remote OTDR service is executing a trace with the local mirror configured towards this port.";
      }
    }
    description
      "OTDR handshaking states.";
  }

  typedef resp-trace-status_t {
    type enumeration {
      enum "unknown" {
        description
          "n/a, To align with snmp mib";
      }
      enum "reflection" {
        description
          "Reflection (?)";
      }
      enum "hi-loss" {
        description
          "High loss";
      }
      enum "sw-fail" {
        description
          "Software failed";
      }
      enum "no-osc" {
        description
          "no osc";
      }
      enum "fw-fail" {
        description
          "fw failed";
      }
      enum "file-fail" {
        description
          "file failed";
      }
      enum "rm-otdr-trc" {
        description
          "Remote otdr trace (I don't know what it means!)";
      }
      enum "stop-auto-trace" {
        description
          "Auto trace stopped";
      }
      enum "success" {
        description
          "Good trace available";
      }
      enum "resource-unavailable" {
        description
          "Some resources were not available";
      }
      enum "retry" {
        description
          "Under retry (I guess)";
      }
    }
    description
      "The type of trace to be measured";
  }

  typedef launch-power_t {
    type enumeration {
      enum "auto" {
        description
          "Auto";
      }
      enum "low" {
        description
          "Low power";
      }
      enum "med" {
        description
          "Medium power";
      }
      enum "high" {
        description
          "High power";
      }
    }
    description
      "Type of launch power. Note: for now this type has to match the one in otdr snmp mib.";
  }

  typedef event-type_t {
    type enumeration {
      enum "unknown" {
        value 0;
        description
          "The event where the OTDR error could not be determined.";
      }
      enum "loss" {
        value 1;
        description
          "The event where the level of reflected light suddenly decreases.";
      }
      enum "reflection" {
        value 2;
        description
          "The event where a pulse of light reflected back to the OTDR.";
      }
      enum "saturated" {
        value 3;
        description
          "The event is a saturation.";
      }
      enum "nogo" {
        value 4;
        description
          "The event is a nogo.";
      }
    }
    description
      "Type of OTDR events.";
  }

  typedef trace-tag_t {
    type enumeration {
      enum "baseline" {
        description
          "OTDR trace tagged as baseline";
      }
      enum "current" {
        description
          "Current OTDR trace";
      }
    }
    description
      "Baseline or the current OTDR trace";
  }

  typedef gonogo_t {
    type enumeration {
      enum "nogo-refl-short" {
        value 1;
        description
          "No go, reflection short distance";
      }
      enum "nogo-loss-short" {
        value 2;
        description
          "No go, loss short distance";
      }
      enum "go" {
        value 3;
        description
          "It's a go: the raman pump can be turned on";
      }
      enum "nogo-refl-office" {
        value 4;
        description
          "No go, reflection office distance (super short distance)";
      }
      enum "nogo-loss-office" {
        value 5;
        description
          "No go, loss office distance (super short distance)";
      }
      enum "nogo-refl-long" {
        value 6;
        description
          "No go, reflection long distance";
      }
      enum "nogo-leadin-office" {
        value 7;
        description
          "No go, lead-in error";
      }
      enum "nogo-unknown" {
        value 8;
        description
          "Not a go-nogo trace. The go-nogo status was not evaluated by the card.";
      }
      enum "nogo-high-gain-office" {
        value 9;
        description
          "No go, a high gain event has been encountered on the office trace";
      }
      enum "nogo-high-gain-short" {
        value 10;
        description
          "No go, a high gain event has been encountered on the short trace";
      }
      enum "nogo-unsolvable-office" {
        value 11;
        description
          "No go, an unsolvable event has been encountered on the office trace";
      }
      enum "nogo-unsolvable-short" {
        value 12;
        description
          "No go, an unsolvable event has been encountered on the short trace";
      }
    }
    description
      "Enum of go nogo indicator for raman.";
  }

  typedef event-status_t {
    type enumeration {
      enum "single-reflection" {
        description
          "Single reflection event.";
      }
      enum "total-reflection" {
        description
          "Total reflection event.";
      }
      enum "single-loss" {
        description
          "Single loss event.";
      }
      enum "total-loss" {
        description
          "Total loss event.";
      }
    }
    description
      "Trace event statuses.";
  }

  typedef otdr-trace-state_t {
    type enumeration {
      enum "unknown" {
        description
          "The state is currently unknown.";
      }
      enum "idle" {
        description
          "OTDR trace is currently not running and no request pending either";
      }
      enum "running" {
        description
          "OTDR trace is currently running";
      }
      enum "pending" {
        description
          "OTDR trace is pending, i.e. the trace will start once the required resources become available";
      }
    }
    description
      "Enum indicating the state of a given otdr port trace type.";
  }

  typedef last-trace-state_t {
    type enumeration {
      enum "na" {
        description
          "Not applicable.";
      }
      enum "success" {
        description
          "OTDR trace is good";
      }
      enum "failure" {
        description
          "OTDR trace failed";
      }
    }
    description
      "Enum indicating the state of a last trace.";
  }

  typedef file-transfer-state_t {
    type enumeration {
      enum "na" {
        description
          "Not applicable.";
      }
      enum "success" {
        description
          "OTDR file transfer succeeded";
      }
      enum "failure" {
        description
          "OTDR file transfer failed";
      }
    }
    description
      "Enum indicating the state of the SOR file from card.";
  }

  typedef otdr-rpc_state_t {
    type enumeration {
      enum "unknown" {
        description
          "The state is currently unknown.";
      }
      enum "success" {
        description
          "Request successfully completed";
      }
      enum "pending" {
        description
          "Start trace request accepted and has been queued up for execution";
      }
      enum "missing-otdr-name" {
        description
          "Request rejected: Missing mandatory OTDR 'name' parameter";
      }
      enum "missing-otdr-trace-type" {
        description
          "Request rejected: Missing mandatory OTDR 'trace-type' parameter";
      }
      enum "missing-otdr-trace-tag" {
        description
          "Request rejected: Missing mandatory OTDR 'trace-tag' parameter";
      }
      enum "missing-otdr-raman-name" {
        description
          "Request rejected: Missing mandatory OTDR 'raman-name' parameter";
      }
      enum "invalid-otdr-name" {
        description
          "Request rejected: OTDR name format is expected to be 'slot-{slotName}-port-{portName}'.";
      }
      enum "invalid-otdr-raman-name" {
        description
          "Request rejected: OTDR Raman name format is expected to be 'slot-{slotName}-port-{portName}'.";
      }
      enum "invalid-slot-name" {
        description
          "Request rejected: slot name is invalid or does not have any OTDR facility.";
      }
      enum "slot-is-not-present" {
        description
          "Request rejected: card in slot not present.";
      }
      enum "circuit-pack-mismatch" {
        description
          "Request rejected: Slot has a circuit pack mismatch";
      }
      enum "invalid-port-name" {
        description
          "Request rejected: port name is invalid or does not have any OTDR facility.";
      }
      enum "invalid-raman-port" {
        description
          "Request rejected: The specified 'slot-{slotName}-port-{portName}' is an invalid raman port";
      }
      enum "raman-slot-is-not-present" {
        description
          "Request rejected: Raman slot name has no presence.";
      }
      enum "raman-circuit-pack-mismatch" {
        description
          "Request rejected: Raman slot has a circuit pack mismatch.";
      }
      enum "feature-disabled" {
        description
          "Request rejected: the OTDR feature is disabled.";
      }
      enum "trace-response-not-found" {
        description
          "Trace response not found";
      }
      enum "trace-events-not-found" {
        description
          "Trace events not found";
      }
      enum "sor-file-not-found" {
        description
          "SOR file not found";
      }
      enum "software-error" {
        description
          "Request rejected: Encountered an internal software error, please try again.";
      }
      enum "nogo-override-error" {
        description
          "Error with nogo override request. The additional info will provide more detail as to what failed: password missing, wrong
           passport, valid GO trace missing, or current trace missing";
      }
      enum "baseline-not-supported" {
        description
          "Request rejected: The requested 'trace-type' does not support any baseline.";
      }
      enum "missing-traces-for-override" {
        description
          "Request rejected: Current go-nogo trace responses are required to override go-nogo";
      }
      enum "remote-port-communication-error" {
        description
          "Request rejected: communication with remote OTDR port is unsuccessful";
      }
      enum "remote-port-does-not-support-flm" {
        description
          "Request rejected: Remote port does not support Fiber Length Measurement (FLM)";
      }
    }
    description
      "Enum indicating the result of a request.";
  }

  typedef distance_t {
    type int32;
    units "m";
    description
      "distance in meters";
  }

  typedef reflection_t {
    type decimal64 {
      fraction-digits 2;
    }
    units "dB";
    description
      "Reflection in dB";
  }

  typedef pulse_t {
    type uint16;
    units "ns";
    description
      "pulse width in ns";
  }

  typedef otdr-diag-name_t {
    type enumeration {
      enum "pre-amp-olf" {
        description
          "pre-amplifier optical line failed";
      }
      enum "raman-olf" {
        description
          "Raman amplifier optical line failed";
      }
      enum "osc-rdi" {
        description
          "Optical service channel remote defect indicator";
      }
      enum "telemetry-rdi" {
        description
          "Telemetry remote defect indicator";
      }
    }
    description
      "OTDR diagnostic name for a monitored diag point";
  }

  grouping otdr-rpc-response-group {
    leaf result {
      type otdr-rpc_state_t;
      default "unknown";
      config false;
      description
        "The state of the request.";
    }

    leaf result-str {
      type string;
      config false;
      description
        "Result detailed description";
    }
  }

  grouping response-group {
    list trace-response {
      key "trace-type trace-tag";
      description
        "List of trace responses.";
      leaf trace-type {
        type trace-type_t;
        description
          "Type of trace.";
      }

      leaf trace-tag {
        type trace-tag_t;
        description
          "Baseline or the current OTDR trace";
      }

      leaf sor-file {
        type string {
          length "0..256";
        }
        description
          "The SOR file name with directory path that can be used with sftp.";
      }

      leaf file-size {
        type uint32;
        units "byte";
        description
          "Size of the SOR file";
      }

      leaf discovered-fiber-type {
        type leafref {
          path "/fiber-types:fiber-type/fiber-types:fiber-type";
        }
        description
          "Discovered fiber type. TODO: need a translation between yang and SNMP...";
      }

      leaf average-loss {
        type ciena-6500r-types:loss;
        units "dB/km";
        description
          "Average Fiber loss for OTDR Trace (dB/km)";
      }

      leaf num-event {
        type uint32;
        config false;
        description
          "Number of event reported by the card for this trace";
      }

      leaf trace-status {
        type resp-trace-status_t;
        description
          "Status of the trace.";
      }

      leaf file-time-stamp {
        type yang:date-and-time;
        description
          "File time stamp";
      }

      leaf total-loss {
        type ciena-6500r-types:loss;
        units "dB";
        description
          "Total loss";
      }

      leaf total-reflection {
        type reflection_t;
        units "dB";
        description
          "Total reflection";
      }

      leaf go-nogo-status {
        type gonogo_t;
        description
          "Go Nogo status indicator";
      }

      leaf-list event-status {
        type event-status_t;
        description
          "Reported event statuses.";
      }

      leaf fiber-length-valid {
        type boolean;
        description
          "The Fiber Length Measurement (FLM) calculation validity.";
      }

      leaf fiber-length {
        type int32;
        units "m";
        description
          "The calculated Fiber Length Measurement (FLM)";
      }
    }
  }

  grouping event-group {
    list trace-event {
      key "trace-type trace-tag";
      description
        "List of trace events list.";
      leaf trace-type {
        type trace-type_t;
        description
          "Type of trace.";
      }

      leaf trace-tag {
        type trace-tag_t;
        description
          "Baseline or the current OTDR trace";
      }

      leaf trace-date-time {
        type yang:date-and-time;
        description
          "The date and time of the OTDR trace";
      }

      leaf num-event {
        type uint32;
        description
          "Number of event reported by the card for this trace";
      }

      list events {
        key "event-num";
        leaf event-num {
          type uint8;
          description
            "Id of the event";
        }

        leaf event-type {
          type event-type_t;
          description
            "Type of event in the trace.";
        }

        leaf event-distance {
          type distance_t;
          description
            "Distance (m) of the event.";
        }

        leaf event-reflection {
          type reflection_t;
          description
            "Reflection value (dB) of the event.";
        }

        leaf event-loss {
          type ciena-6500r-types:loss;
          description
            "Loss value (dB) of the event.";
        }

        leaf event-comment {
          type string {
            length "1..51";
          }
          description
            "Event comment.";
        }
      }
    }
  }

  grouping ciena-6500r-otdr-mount {
    list otdr-instance {
      key "name";
      description
        "An OTDR instance can only run one OTDR trace at a time within a group of OTDR facilities";
      leaf name {
        type ciena-6500r-types:object-name;
        description
          "Otdr instance name";
      }

      leaf mirror-active {
        type boolean;
        description
          "If true, the mirror is active.";
      }

      leaf port-selector-config {
        type instance-identifier;
        description
          "Indicates the OTDR port that the mirror is directed towards.";
      }

      leaf port-selector-state {
        type instance-identifier;
        config false;
        description
          "The current hardware OTDR port selection state.  This is a common port selection state shared
           by the OTDR mirror and OTDR traces.";
      }
    }

    list otdr {
      key "name";
      leaf name {
        type string;
        description
          "Otdr Facility name";
      }

      leaf parent-port {
        type leafref {
          path "/ports:port/ports:name";
        }
        mandatory true;
        description
          "Otdr facility parent.";
      }

      container config {
        leaf measure-time {
          type uint32;
          units "seconds";
          default "60";
          description
            "Acquisition Time for the OTDR Trace (s)";
        }

        leaf event-range {
          type uint32 {
            range "0..128000";
          }
          units "m";
          default "0";
          description
            "OTDR Event Range (m)";
        }

        container office {
          leaf pulse-office {
            type pulse_t;
            default "100";
            description
              "Pulse width for Office Distance OTDR Trace (ns), supported values are 10, 30 and 100 (ns)";
          }

          leaf distance-office {
            type distance_t;
            default "8000";
            description
              "Span Length for Office Distance for OTDR Trace, supported value is 8000 (m) only";
          }
        }

        container short {
          leaf pulse-short {
            type pulse_t;
            default "1000";
            description
              "Pulse width for Short Distance OTDR Trace, supported value is 1000 (ns) only";
          }

          leaf distance-short {
            type distance_t;
            default "20000";
            description
              "Span Length for Short Distance OTDR Trace, supported values is 8000, 16000, 20000 and 32000 (m) ";
          }
        }

        container long {
          leaf pulse-long {
            type pulse_t;
            default "40000";
            description
              "Pulse width for Long Distance OTDR Trace, supported values are 3000, 10000, and 40000 (ns)";
          }

          leaf distance-long {
            type distance_t;
            default "128000";
            description
              "Span Length for Long Distance for OTDR Trace, supported values are 64000 and 128000 (m)";
          }
        }

        leaf loss-threshold-single {
          type decimal64 {
            fraction-digits 1;
          }
          units "dB";
          description
            "Loss threshold per event for go/nogo decision for OTDR trace.";
        }

        container loss-threshold-single-ranges {
          leaf min {
            type decimal64 {
              fraction-digits 1;
            }
            units "dB";
          }

          leaf max {
            type decimal64 {
              fraction-digits 1;
            }
            units "dB";
          }
        }

        leaf loss-threshold-all {
          type decimal64 {
            fraction-digits 1;
          }
          units "dB";
          description
            "Loss threshold for all events for go/nogo decision for OTDR trace.";
        }

        container loss-threshold-all-ranges {
          leaf min {
            type decimal64 {
              fraction-digits 1;
            }
            units "dB";
          }

          leaf max {
            type decimal64 {
              fraction-digits 1;
            }
            units "dB";
          }
        }

        leaf reflection-threshold-single {
          type decimal64 {
            fraction-digits 1;
          }
          units "dB";
          description
            "Reflection threshold for a single event for go/nogo decision for OTDR trace.";
        }

        container reflection-threshold-single-ranges {
          leaf min {
            type decimal64 {
              fraction-digits 1;
            }
            units "dB";
          }

          leaf max {
            type decimal64 {
              fraction-digits 1;
            }
            units "dB";
          }
        }

        leaf reflection-threshold-all {
          type decimal64 {
            fraction-digits 1;
          }
          units "dB";
          description
            "Reflection threshold for all events for go/nogo decision for OTDR trace.";
        }

        container reflection-threshold-all-ranges {
          leaf min {
            type decimal64 {
              fraction-digits 1;
            }
            units "dB";
          }

          leaf max {
            type decimal64 {
              fraction-digits 1;
            }
            units "dB";
          }
        }

        leaf wavelength {
          type decimal64 {
            fraction-digits 2;
            range "1527..1625";
          }
          units "nm";
          description
            "OTDR Wavelength";
        }

        leaf provisioned-fiber-type {
          type leafref {
            path "/fiber-types:fiber-type/fiber-types:fiber-type";
          }
          description
            "Fiber Type";
        }
      }

      container diagnostic {
        config false;
        description
          "Section containing info related to state of the ODTR port";
        leaf local-otdr-in-progress {
          type boolean;
          config false;
          description
            "Local OTDR trace is in progress";
        }

        list notes {
          key "index";
          config false;
          leaf index {
            type uint32;
          }

          leaf note {
            type string;
            description
              "Configuration or operational observation associated to this OTDR port";
          }
        }

        leaf handshaking-state {
          type handshaking-state_t;
          config false;
          description
            "Handshaking state.";
        }

        leaf pfg-name {
          type string;
          config false;
          description
            "The name of the PFG associated to this OTDR facility.";
        }

        leaf local-line-port {
          type instance-identifier;
          config false;
          description
            "The PFG line in or out port associated to this OTDR facility";
        }

        leaf remote-line-port {
          type instance-identifier;
          config false;
          description
            "The remote PFG line in or out port associated to this OTDR facility";
        }

        list trace-types {
          key "trace-type";
          config false;
          leaf trace-type {
            type trace-type_t;
            config false;
            description
              "Type of trace.";
          }

          leaf state {
            type otdr-trace-state_t;
            default "idle";
            config false;
            description
              "OTDR trace state";
          }

          leaf requestor {
            type requestor_t;
            config false;
            description
              "What triggered a request for an OTDR trace";
          }

          leaf is-handshake-requested {
            type boolean;
            config false;
            description
              "Is a Go/No-Go trace requested?";
          }

          leaf is-go-nogo-requested {
            type boolean;
            config false;
            description
              "Is a Go/No-Go trace requested?";
          }

          leaf trace-result {
            type last-trace-state_t;
            config false;
            description
              "Trace result from the last executed trace";
          }

          leaf trace-result-details {
            type string;
            config false;
            description
              "Extra diagnostic information from the last executed trace";
          }

          leaf trace-response-status {
            type resp-trace-status_t;
            config false;
            description
              "Status of the trace from the card";
          }

          leaf trace-go-nogo-status {
            type gonogo_t;
            config false;
            description
              "Go/No-Go status from the card";
          }

          leaf-list trace-event-status {
            type event-status_t;
            config false;
            description
              "Reported event statuses.";
          }

          leaf trace-time-stamp {
            type yang:date-and-time;
            config false;
            description
              "File time stamp from the card";
          }
        }

        list monitored-diag-points {
          key "name";
          config false;
          description
            "List of diagnostic points monitored by this OTDR port.";
          leaf name {
            type otdr-diag-name_t;
            config false;
            description
              "OTDR diagnostic name for the monitored diag point";
          }

          uses ciena-6500r-local-fault:diag-point-id;
        }

        leaf parent-failed {
          type boolean;
          config false;
          description
            "Parent port failed.";
        }
      }

      container raman {
        config false;
        description
          "OTDR raman information";
        leaf slot-name {
          type string;
          config false;
          description
            "Raman slot name";
        }

        leaf instance {
          type string;
          config false;
          description
            "Raman facility instance";
        }

        leaf cold-restart-epoch-time {
          type int64;
          config false;
          description
            "The Unix epoch time of the last slot cold restart.
             The Unix epoch is the number of seconds that have elapsed since
             00:00:00 UTC on 1 January 1970, minus leap seconds.
             This field has a low precision and can be off by multiple seconds.";
        }

        leaf go-nogo-status {
          type enumeration {
            enum "nogo" {
              value 1;
              description
                "OTDR measurements are a No Go.";
            }
            enum "go" {
              value 2;
              description
                "OTDR measurements are a Go";
            }
            enum "unknown" {
              value 3;
              description
                "No go-nogo OTDR measurements have been done on this port.
                 It's the default value on configuration and when a cold restart is detected.";
            }
          }
          config false;
          description
            "The last OTDR Go/No-Go measurement aggregate results for all 3 trace types.
             Used to update the raman card when a warm restart is detected.
             This value is not impacted when running traces on the port without go-nogo.";
        }
      }

      leaf alarm-additional-info {
        type string {
          length "1..80";
        }
        config false;
        description
          "Additional info associated to a raised alarm.";
      }

      container opr {
        config false;
        description
          "Structure of the interface to start/stop a trace.";
        leaf start {
          type boolean;
          config false;
          description
            "True to start a trace, false to cancel(stop) a trace.";
        }

        leaf trace-type {
          type card-if-trace-type_t;
          config false;
          description
            "Type of trace.";
        }
      }

      uses response-group;

      uses event-group;
    }
  }

  grouping ciena-6500r-otdr-mount-actions {
    action start-otdr-trace {
      description
        "Operate OTDR Measurement: Instructs a network element to start OTDR Measurement";
      input {
        leaf name {
          type string;
          description
            "Otdr Facility name";
        }

        leaf trace-type {
          type request-trace-type_t;
          default "long";
          description
            "The type of trace to be measured";
        }

        leaf handshake {
          type boolean;
          default "true";
          description
            "Handshake state (for trace collision management).";
        }

        leaf raman-name {
          type string;
          description
            "Raman Facility name when using a 'trace-type' of 'Go-nogo'.
             This field is only required when the OTDR port is not associated to a PFG,
             but the OTDR port is connected to a raman facility.";
        }
      }

      output {
        list output {
          uses otdr-rpc-response-group;
        }
      }
    }

    action stop-otdr-trace {
      description
        "Stop the ongoing OTDR Measurement";
      input {
        leaf name {
          type string;
          description
            "Otdr Facility name";
        }

        leaf trace-type {
          type request-trace-type_t;
          default "long";
          description
            "The type of trace to stop";
        }

        leaf raman-name {
          type string;
          description
            "Raman Facility name when using a 'trace-type' of 'Go-nogo'";
        }
      }

      output {
        list output {
          uses otdr-rpc-response-group;
        }
      }
    }

    action set-baseline-otdr-trace {
      description
        "Instructs a network element to tag the current trace (SOR file, response, events) specified with the TRACE TYPE as BASELINE";
      input {
        leaf name {
          type string;
          description
            "Otdr Facility name";
        }

        leaf trace-type {
          type trace-type_t;
          default "long";
          description
            "The type of trace to be measured";
        }

        leaf force {
          type boolean;
          default "false";
          description
            "Set current trace as baseline regardless of go-nogo status, only if no existing baseline.";
        }
      }

      output {
        list output {
          uses otdr-rpc-response-group;
        }
      }
    }

    action get-otdr-sor-file {
      description
        "Retrieve the SOR (Standard OTDR Record) path and file name specified by the tracetype and tracetag.
         This file is accessible through port 22022 using sftp";
      input {
        leaf name {
          type string;
          description
            "Otdr Facility name";
        }

        leaf trace-type {
          type trace-type_t;
          description
            "The type of trace to be measured";
        }

        leaf trace-tag {
          type trace-tag_t;
          description
            "Baseline or the current SOR file";
        }
      }

      output {
        list output {
          uses otdr-rpc-response-group;

          leaf url {
            type string {
              length "0..256";
            }
            description
              "The file path is: /directory-path.";
          }
        }
      }
    }

    action show-otdr-response {
      description
        "Response of a given OTDR Trace";
      input {
        leaf name {
          type string;
          description
            "Otdr Facility name";
        }

        leaf trace-type {
          type trace-type_t;
          description
            "The type of trace to be measured";
        }

        leaf trace-tag {
          type trace-tag_t;
          description
            "Baseline or the current OTDR trace";
        }
      }

      output {
        list output {
          uses otdr-rpc-response-group;

          leaf name {
            type string;
            description
              "Otdr Facility name";
          }

          uses response-group;
        }
      }
    }

    action show-otdr-events {
      description
        "List all the events corresponding to the given OTDR Trace";
      input {
        leaf name {
          type string;
          description
            "Otdr Facility name";
        }

        leaf trace-type {
          type trace-type_t;
          description
            "The type of trace to be measured";
        }

        leaf trace-tag {
          type trace-tag_t;
          description
            "Baseline or the current OTDR trace";
        }
      }

      output {
        list output {
          uses otdr-rpc-response-group;

          leaf name {
            type string;
            description
              "Otdr Facility name";
          }

          uses event-group;
        }
      }
    }

    action override-nogo {
      description
        "Override a nogo status to go. This is possible only if a go was obtained in a previous run. Password required";
      input {
        leaf name {
          type string;
          description
            "Otdr Facility name";
        }

        leaf password {
          type string;
          mandatory true;
          description
            "A password is required to override nogo.";
        }

        leaf reason {
          type string;
          description
            "Cause or reasoning for OTDR go-nogo-status override request.";
        }
      }

      output {
        list output {
          uses otdr-rpc-response-group;
        }
      }
    }
  }

  uses ciena-6500r-otdr-mount;

  rpc start-otdr-trace {
    description
      "Operate OTDR Measurement: Instructs a network element to start OTDR Measurement";
    input {
      leaf name {
        type string;
        description
          "Otdr Facility name";
      }

      leaf trace-type {
        type request-trace-type_t;
        default "long";
        description
          "The type of trace to be measured";
      }

      leaf handshake {
        type boolean;
        default "true";
        description
          "Handshake state (for trace collision management).";
      }

      leaf raman-name {
        type string;
        description
          "Raman Facility name when using a 'trace-type' of 'Go-nogo'.
           This field is only required when the OTDR port is not associated to a PFG,
           but the OTDR port is connected to a raman facility.";
      }
    }

    output {
      list output {
        uses otdr-rpc-response-group;
      }
    }
  }

  rpc stop-otdr-trace {
    description
      "Stop the ongoing OTDR Measurement";
    input {
      leaf name {
        type string;
        description
          "Otdr Facility name";
      }

      leaf trace-type {
        type request-trace-type_t;
        default "long";
        description
          "The type of trace to stop";
      }

      leaf raman-name {
        type string;
        description
          "Raman Facility name when using a 'trace-type' of 'Go-nogo'";
      }
    }

    output {
      list output {
        uses otdr-rpc-response-group;
      }
    }
  }

  rpc set-baseline-otdr-trace {
    description
      "Instructs a network element to tag the current trace (SOR file, response, events) specified with the TRACE TYPE as BASELINE";
    input {
      leaf name {
        type string;
        description
          "Otdr Facility name";
      }

      leaf trace-type {
        type trace-type_t;
        default "long";
        description
          "The type of trace to be measured";
      }

      leaf force {
        type boolean;
        default "false";
        description
          "Set current trace as baseline regardless of go-nogo status, only if no existing baseline.";
      }
    }

    output {
      list output {
        uses otdr-rpc-response-group;
      }
    }
  }

  rpc get-otdr-sor-file {
    description
      "Retrieve the SOR (Standard OTDR Record) path and file name specified by the tracetype and tracetag.
       This file is accessible through port 22022 using sftp";
    input {
      leaf name {
        type string;
        description
          "Otdr Facility name";
      }

      leaf trace-type {
        type trace-type_t;
        description
          "The type of trace to be measured";
      }

      leaf trace-tag {
        type trace-tag_t;
        description
          "Baseline or the current SOR file";
      }
    }

    output {
      list output {
        uses otdr-rpc-response-group;

        leaf url {
          type string {
            length "0..256";
          }
          description
            "The file path is: /directory-path.";
        }
      }
    }
  }

  rpc show-otdr-response {
    description
      "Response of a given OTDR Trace";
    input {
      leaf name {
        type string;
        description
          "Otdr Facility name";
      }

      leaf trace-type {
        type trace-type_t;
        description
          "The type of trace to be measured";
      }

      leaf trace-tag {
        type trace-tag_t;
        description
          "Baseline or the current OTDR trace";
      }
    }

    output {
      list output {
        uses otdr-rpc-response-group;

        leaf name {
          type string;
          description
            "Otdr Facility name";
        }

        uses response-group;
      }
    }
  }

  rpc show-otdr-events {
    description
      "List all the events corresponding to the given OTDR Trace";
    input {
      leaf name {
        type string;
        description
          "Otdr Facility name";
      }

      leaf trace-type {
        type trace-type_t;
        description
          "The type of trace to be measured";
      }

      leaf trace-tag {
        type trace-tag_t;
        description
          "Baseline or the current OTDR trace";
      }
    }

    output {
      list output {
        uses otdr-rpc-response-group;

        leaf name {
          type string;
          description
            "Otdr Facility name";
        }

        uses event-group;
      }
    }
  }

  rpc override-nogo {
    description
      "Override a nogo status to go. This is possible only if a go was obtained in a previous run. Password required";
    input {
      leaf name {
        type string;
        description
          "Otdr Facility name";
      }

      leaf password {
        type string;
        mandatory true;
        description
          "A password is required to override nogo.";
      }

      leaf reason {
        type string;
        description
          "Cause or reasoning for OTDR go-nogo-status override request.";
      }
    }

    output {
      list output {
        uses otdr-rpc-response-group;
      }
    }
  }
}
