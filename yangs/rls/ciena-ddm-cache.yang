module ciena-ddm-cache {
  namespace "urn:ciena:params:xml:ns:yang:ciena-ddm-cache";
  prefix ddm-cache;

  import ciena-ddy-msg {
    prefix ciena-ddy-msg;
  }

  organization
    "Ciena Corporation";
  contact
    "Web URL: http://www.ciena.com/
     Postal:  7035 Ridge Road
             Hanover, Maryland 21076
             U.S.A.
     Phone:   +1 800-921-1144
     Fax:     +1 410-694-5750";
  description
    "This is the model for the cache based messaging component of the
     Bifrost framework.  This allows a service to use a cache or a
     database as a messaging endpoint.  Any get/set requests that
     would have gone to a remote service will instead be redirected
     to a local cache or database.  This allows deployments in which
     remote services can be simulated by cached static data.
     Notifications are not emitted and all RPCs return true with no
     content";

  revision 2020-02-18 {
    description
      "Initial revision";
  }

  identity cache {
    base ciena-ddy-msg:ddm-protocols;
    description
      "cache based messaging";
  }

  augment "/ciena-ddy-msg:domains/ciena-ddy-msg:protocols" {
    when "ciena-ddy-msg:type = 'ciena-ddy-msg:cache'";
    container cache-options {
      leaf name {
        type string;
        description
          "Name of the cache.";
      }
      leaf type {
        type enumeration {
          enum ddy-cache;
          enum ddy-db;
        }
        default "ddy-cache";
        description
          "Type of cache.";
      }
    }
  }
}
