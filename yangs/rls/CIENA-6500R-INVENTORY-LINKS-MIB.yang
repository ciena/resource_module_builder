module CIENA-6500R-INVENTORY-LINKS-MIB {
  namespace "urn:ietf:params:xml:ns:yang:smiv2:CIENA-6500R-INVENTORY-LINKS-MIB";
  prefix ciena-6500r-inventory;

  import CIENA-6500R-INVENTORY-MIB {
    prefix ciena-6500r;
  }
  import CIENA-6500R-TYPES-MIB {
    prefix ciena-6500r-types;
  }
  import CIENA-PRO-TYPES-MIB {
    prefix ciena-pro;
  }

  organization
    "Ciena Corporation";
  contact
    "Web URL: http://www.ciena.com/
     Postal:  7035 Ridge Road
     Hanover, Maryland 21076
     U.S.A.
     Phone:   +1 800-921-1144
     Fax:    Inventory +1 410-694-5750";
  description
    "This modules describes Ciena's photonic Links object.";

  revision 2021-10-22 {
    description
      "Initial revision.";
  }

  container cienaRlsInventoryLinksMIB {
    list rlsInventoryLinksEntry {
      config false;
      key "rlsInventoryLinksName";
      description
        "";
      leaf rlsInventoryLinksName {
        type ciena-pro:DisplayString128;
        config false;
        description
          "Links name.";
      }
      leaf rlsInventoryLinksLinkType {
        type enumeration {
          enum unknown {
            value 1;
          }
          enum fiber {
            value 2;
          }
          enum mpo-cable {
            value 3;
          }
          enum logical {
            value 4;
          }
          enum line-fiber {
            value 5;
          }
          enum logical-line-fiber {
            value 6;
          }
          enum loopback {
            value 7;
          }
        }
        config false;
        description
          "Links link type.";
      }
      leaf rlsInventoryLinksFarEndAddress {
        type ciena-pro:DisplayString128;
        config false;
        description
          "Links Far End address.";
      }
      leaf rlsInventoryLinksNearEndAddress {
        type ciena-pro:DisplayString128;
        config false;
        description
          "Links Near End address.";
      }
      leaf rlsInventoryLinksSpanLossMargin {
        type ciena-pro:DisplayString32;
        config false;
        description
          "Links Span loss Margin in dB.";
      }
      leaf rlsInventoryLinksTargetSpanLoss {
        type ciena-pro:DisplayString32;
        config false;
        description
          "Links Target Span loss in dB.";
      }
    }
    config false;
    list rlsInventoryLinksLossEntry {
      config false;
      key "rlsInventoryLinksLossName
           rlsInventoryLinksLossSpectralType
           rlsInventoryLinksLossType";
      description
        "";
      leaf rlsInventoryLinksLossName {
        type ciena-pro:DisplayString128;
        config false;
        description
          "Links name.";
      }
      leaf rlsInventoryLinksLossSpectralType {
        type ciena-6500r-types:BandOccupancy;
        config false;
        description
          "Links Spectral Type.";
      }
      leaf rlsInventoryLinksLossType {
        type enumeration {
          enum measured {
            value 0;
          }
          enum calculated {
            value 1;
          }
        }
        config false;
        description
          "Links loss type.";
      }
      leaf rlsInventoryLinksOscSpanLoss {
        type ciena-pro:DisplayString32;
        config false;
        description
          "Links OSC span loss value in dB.";
      }
      leaf rlsInventoryLinksTelemetrySpanLoss {
        type ciena-pro:DisplayString32;
        config false;
        description
          "Links Raman/Telemetry span loss value in dB.";
      }
    }
  }
}
