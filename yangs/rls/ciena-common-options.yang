module ciena-common-options {
  namespace "urn:ciena:params:xml:ns:yang:ciena-common-options";
  prefix options;

  import ciena-common-version {
    prefix version;
  }
  import ciena-common-yang {
    prefix yang;
  }

  organization
    "Ciena Corporation";
  contact
    "Web URL: http://www.ciena.com/
     Postal:  7035 Ridge Road
             Hanover, Maryland 21076
             U.S.A.
     Phone:   +1 800-921-1144
     Fax:     +1 410-694-5750";
  description
    "Options to drive behaviour of framework.  Used internally and
     driven by deployment specific inputs.";

  revision 2024-02-15 {
    description
      "Adding yang option context-validation.";
    version:version "version" {
      version:string "1.23.0";
    }
  }
  revision 2024-01-03 {
    description
      "Adding yang option max-get-initial-cache-count.";
    version:version "version" {
      version:string "1.22.0";
    }
  }
  revision 2023-12-05 {
    description
      "Changed packed option to be boolean.";
    version:version "version" {
      version:string "1.21.0";
    }
  }
  revision 2023-11-17 {
    description
      "Adding yang options path-skip-wildcarding and path-ignore-partial-key.";
    version:version "version" {
      version:string "1.20.0";
    }
  }
  revision 2023-10-26 {
    description
      "Updated pointer-paths option to allow exclusion of unions.";
    version:version "version" {
      version:string "1.19.0";
    }
  }
  revision 2023-10-23 {
    description
      "Add option to prefer a module during parsing so that
       object paths resolve to the preferred module.";
    version:version "version" {
      version:string "1.18.0";
    }
  }
  revision 2023-09-05 {
    description
      "Added new way to specify whether the strings or containers
       should be converted to pointers and deprecated the old way.";
    version:version "version" {
      version:string "1.17.0";
    }
  }
  revision 2023-08-11 {
    description
      "Add an option for targeted publishing of get-initial's.";
    version:version "version" {
      version:string "1.16.0";
    }
  }
  revision 2023-05-01 {
    description
      "Added failed-cipher-check option";
    version:version "version" {
      version:string "1.15.0";
    }
  }
  revision 2023-05-01 {
    description
      "Added option to list-size-change.";
    version:version "version" {
      version:string "1.14.0";
    }
  }
  revision 2023-04-18 {
    description
      "Added option to omit namespace prefixes from xml serialization for
       instance identifier for backwards compatibility.";
    version:version "version" {
      version:string "1.13.0";
    }
  }
  revision 2023-03-09 {
    description
      "Added path-fields-bug-compatiblity";
    version:version "version" {
      version:string "1.12.0";
    }
  }
  revision 2023-03-09 {
    description
      "Added to-pointer-paths option";
    version:version "version" {
      version:string "1.11.0";
    }
  }
  revision 2022-11-25 {
    description
      "Added encryption yang option";
    version:version "version" {
      version:string "1.10.0";
    }
  }
  revision 2022-11-01 {
    description
      "Added option to disable quotes in \"int64\", \"uint64\" numbers from
       json serialization for backwards compatibility.";
    version:version "version" {
      version:string "1.9.0";
    }
  }
  revision 2022-09-28 {
    description
      "Added option to omit namespaces from json serialization for
       backwards compatibility.";
    version:version "version" {
      version:string "1.8.0";
    }
  }
  revision 2022-09-27 {
    description
      "Added packing option for generated structures.";
    version:version "version" {
      version:string "1.7.0";
    }
  }
  revision 2022-06-16 {
    description
      "Added list session-data to register session data ";
    version:version "version" {
      version:string "1.6.0";
    }
  }
  revision 2022-05-25 {
    description
      "Add a option to allow path parsing to generate errors on
       failures";
    version:version "version" {
      version:string "1.5.0";
    }
  }
  revision 2022-04-12 {
    description
      "Add a container for legacy-autoload library list";
    version:version "version" {
      version:string "1.4.0";
    }
  }
  revision 2022-02-23 {
    description
      "Added yang-validate to automatically test parameters against
       YANG restrictions.";
    version:version "version" {
      version:string "1.3.0";
    }
  }
  revision 2021-01-08 {
    description
      "Added option for publicaton of empty updates";
    version:version "version" {
      version:string "1.2.0";
    }
  }
  revision 2020-10-05 {
    description
      "Added option for set-object validation";
    version:version "version" {
      version:string "1.1.0";
    }
  }
  revision 2020-08-18 {
    description
      "Initial revision.";
    reference
      "";
    version:version "version" {
      version:string "1.0.0";
    }
  }

  typedef yang-options-context-validation {
    type enumeration {
      enum none {
        description
          "No validation is done";
      }
      enum logged {
        description
          "Validation is done and invalid data is logged";
      }
      enum blocked {
        description
          "Validation is done and invalid data is rejected";
      }
    }
  }

  container yang-options {
    description
      "Container that holds options to drive framework behaviour when
       changes would not be backwards compatible.  Flags are added here
       with the new functionality and the default is the same as the
       previous release.  If an when a deployment chooses to use the
       feature it can be enabled via a deployment file.";
    leaf last-element-delete {
      type boolean;
      default "false";
      description
        "Flag that indicates that the 'delete-element' action is
         supported.  This action indicates that an entire element is to
         be deleted, as opposed to all of its contents.  Without this
         flag, the only way to tell if the full element is being
         deleted is to query the destination database (if service broker
         is supported).

         If this flag is false, the diff function will not generate
         delete-element actions, even though the action will still be
         available for clients to use.";
    }
    leaf json-allow-missing-namespace {
      type boolean;
      default "false";
      description
        "Flag that indicates that the JSON parser permits omitted
         namespaces when traversing an augmentation or anyxml boundary.

         RFC 7951 dictates that namespaces (module names) must always
         be provided in these cases and the default behaviour is to
         fail parsing for those fields.  If this flag is true, the
         module name does not need to be provided.";
    }
    leaf set-object-validation {
      type yang-options-context-validation;
      default "none";
      description
        "Flag that indicates the amount of validation the framework
          performs on set-object calls.

          Internal calls may invoke set-object with incorrect contexts,
          and missing or invalid context data.  Legacy behaviour is to
          pass this onto the handlers for validation, but the framework
          can also validate and log or reject these cases to help find
          invalid usage.";
    }
    leaf get-object-validation {
      type yang-options-context-validation;
      default "none";
      description
        "Flag that indicates the amount of validation the framework
          performs on get-object calls.

          Internal calls may invoke get-object with incorrect contexts,
          and missing or invalid context data.  Legacy behaviour is to
          pass this onto the handlers for validation, but the framework
          can also validate and log or reject these cases to help find
          invalid usage.";
    }
    leaf action-handler-validation {
      type yang-options-context-validation;
      default "none";
      description
        "Flag that indicates the amount of validation the framework
          performs on action-handler calls.

          Internal calls may invoke action-handler with incorrect contexts,
          and missing or invalid context data.  Legacy behaviour is to
          pass this onto the handlers for validation, but the framework
          can also validate and log or reject these cases to help find
          invalid usage.";
    }
    leaf publish-empty-updates {
      type boolean;
      default "false";
      description
        "Flag that indicates that the get-initial, poller based, and
         refresh notifications should publish empty notifications if
         the resource does not exist.

         This is useful to know that publications are working, and
         can let clients work through state transitions, but can
         cause problems in update handlers when empty data or
         incomplete contexts cannot be resolved properly";
    }
    leaf decimal64-include-all-precision-digits {
      type boolean;
      default "true";
      description
        "Flag that indicates whether to trim trailing (non-significant)
         zeros from serialized decimal64 leaves.

         When set to 'false', this forces string representation to conform
         to RFC 6020 and RFC 7950 decimal64 digit specifications.";
    }
    leaf yang-validate {
      type boolean;
      default "false";
      description
        "Flag that indicates that rpcs, actions and edits should automatically
         test for YANG compliance.  This was not available
         before 1.2.0 so may break backwards compatibility if the tests
         were not manually performed before.  This validation can be
         accessed for a complete data node or by
         a patch for create/delete actions by calling the
         'yang-validate' service manually.";
    }
    leaf path-errors {
      type boolean;
      default "false";
      description
        "Flag that indicates that path parsing and generations should
         generate error codes when there is a problem in parsing or
         generation.  This is disabled by default for backward
         compatibility.";
    }
    leaf get-skip-wildcarding {
      type boolean;
      default "false";
      description
        "Flag that indicates that enhanced wildcarding support should be skipped. More
         specifically, setting this flag will cause path parsing to stop at the first
         wildcard.";
    }
    leaf get-skip-selection {
      type boolean;
      default "false";
      description
        "Flag that indicates that instance selection based on wildcarding should not be
         performed on the data returned by the service.";
    }
    list session-data {
      key "name";
      description
        "This list contains details of session data to be registered on all services by depo.
         Session data that is registered to be transferred to and from the virtual stack and messages.
         Each entry corresponds to a container that is present in a message and has a path that maps
         to data that can be present on the stack. Every message that is sent or received is processed
         to encode or decode stack data based on the list of registered session data. This ensures that
         data on the stack in one domain is present in downstream or upstream domains via messaging";
      leaf name {
        type string;
        description
          "Some unique name for tracking.";
      }
      leaf attribute {
        type string;
        description
          "Name of the attribute to register the session data for";
      }
      leaf path {
        type string;
        description
          "Path of the session data to register the session data for.";
      }
    }
    leaf packed {
      type boolean;
      default "true";
      description
        "This flag indicates the setting for C structure packing for ddf-parser.

         When structures are packed (true / default), it is good for saving space,
         but affects processing time.

         When C structures are unpacked (false), it allows for better CPU optimization,
         but the generated structures are larger. Fields are not reordered, so
         it could result in more wasted space between fields.";
    }
    leaf omit-xml-ns-instance-id {
      type boolean;
      default "false";
      description
        "Flag that indicates that the XML serializer should omit
         namespace prefixes for instance identifier.

         RFC 6020 dictates that all node names in an instance-identifier
         value MUST be qualified with explicit namespace prefixes, and
         these prefixes MUST be declared in the XML namespace scope in
         the instance-identifier's XML element.
         This option is available for backwards compatibility with products
         which did not encode namespace prefixes. To disable strict namespace
         prefixes, set to true.";
    }
    leaf json-disable-quotes-int64 {
      type boolean;
      default "false";
      description
        "Flag that indicates that the JSON serializer should disable
         quotes in \"int64\", \"uint64\" numbers.

         RFC 7951 dictates that a value of the \"int64\", \"uint64\"  type is
         represented as a JSON string and the default behaviour is to be compliant.
         This option is available for backwards compatibility with products
         which represents these as a JSON number. To disable strict compliance, set
         to true.";
    }
    leaf json-omit-namespaces {
      type boolean;
      default "false";
      description
        "Flag that indicates that the JSON serializer should omit
         namespaces.

         RFC 7951 dictates that namespaces (module names) must always
         be provided and the default behaviour is to be compliant.
         This option is available for backwards compatibility with products
         which did not encode namespaces. To disable strict namespaces, set
         to true.";
    }
    leaf encryption {
      type boolean;
      default "false";
      description
        "Flag that indicates whether encryption should be done to data.";
    }
    leaf-list to-pointer-paths {
      status deprecated;
      type string;
      description
        "List of paths to containers/strings that should be changed to pointers representations in
         generated structs. If module is given in the list, all containers/strings are changed to
         pointer representations.";
    }
    list pointer-paths {
      description
        "List of paths to containers/strings/unions that should be changed to pointers representations in
         generated structs. If module is given in the list, all containers/strings/unions are changed to
         pointer representations.";
      key "path";
      leaf path {
        type string;
      }
      leaf exclude {
        description
          "By default, all containers, strings and unions are converted to pointers when defined in
           pointer-paths. This option defines which conversions you wish to exclude.";
        type bits {
          bit string;
          bit container;
          bit union;
        }
      }
    }
    leaf path-fields-bug-compatiblity {
      type boolean;
      default "true";
      description
        "Path generation previously had a bug where filters are handled
         inconsistently.  If there is only one element in the top level
         of the filter, it should be separated from the path by a slash.
         With this bug, if keys are present in the top level of the
         filter, it will be wrapped in brackets instead, and this breaks
         parsing of those paths when the leaves are
         instance-identifiers.

         Since existing code may rely on this buggy behaviour, it is in
         control of the user to move away from a bug compatible mode
         when all expectations of the old behaviour have been removed.";
    }
    leaf list-size-change {
      type boolean;
      default "false";
      description
        "If enabled, lists are preserved when list size changed during diff and get patches as
         an edit of the list where the list contents are not present, only the keys. This allows
         validation functions to quickly determine the effect of list size changes without querying
         the database for this data. ";
    }
    leaf failed-cipher-check {
      type enumeration {
        enum assert;
        enum log;
        enum ignore;
      }
      default "assert";
      description
        "Define the behaviour when trying to encrypt but no cipher is provided";
    }
    leaf target-get-initial {
      description
        "If true/enabled, get-initial will target only the specific domain/service in question.";
      type boolean;
      default "false";
    }
    leaf-list preferred-modules {
      description
        "This option re-orders the modules defined here to the top of YANG root
         during parsing / struct generation. This is so object names resolve
         to the preferred module in the event there are conflicting object names
         across modules and you would prefer one to be always used over the other.

         The order of the modules defined here will directly reflect how they appear
         at the top of the generated YANG root.";
      type string;
    }
    leaf max-get-initial-cache-count {
      type uint64;
      description
        "number of messages we want to cache during get initial before we give up";
    }
  }
  container legacy-autoload {
    list library-list {
      key "name";
      ordered-by user;
      description
        "This table contains a list of plugin files that need to be loaded by services that need
         legacy-autoload feature";
      leaf name {
        type string;
        description
          "Some unique name to identify the library";
      }
      leaf file-name {
        type string;
        description
          "Plugin library file name";
      }
    }
  }
}
