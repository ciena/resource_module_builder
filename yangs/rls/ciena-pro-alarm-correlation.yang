module ciena-pro-alarm-correlation {
  yang-version 1.1;
  namespace "urn:ciena:params:xml:ns:yang:ciena-pro-alarm-correlation";
  prefix alarm-correlation;

  import ciena-common-version {
    prefix version;
  }

  organization
    "Ciena Corporation";
  contact
    "Web URL: http://www.ciena.com/
     Postal:  7035 Ridge Road
            Hanover, Maryland 21076
            U.S.A.
     Phone:   +1 800-921-1144
     Fax:     +1 410-694-5750";
  description
    "This modules describes Ciena's alarm correlation module for 6500 RLS platform";

  revision 2020-08-12 {
    version:version "version" {
      version:string "1.1.0";
    }
    description
      "Converting alarm-correlation module to grouping under container.";
  }
  revision 2020-07-31 {
    version:version "version" {
      version:string "1.0.0";
    }
    description
      "Introduction Of Alarm Correlation Module.";
  }

  grouping upstream-fault-masking-group {
    leaf upstream-fault-masking {
      type enumeration {
        enum "Enabled" {
          value 0;
        }
        enum "Disabled" {
          value 1;
        }
        enum "Enabled-locked" {
          value 2;
        }
        enum "Disabled-locked" {
          value 3;
        }
      }
      default "Enabled";
      description
        "The upstream-fault-masking leaf will have four states. This container can be used to configure alarm correlation behavior at different levels of hierarchy.
         Please Note the state with **-locked** means that the value can't be overwritten by shelf level value of the same leaf.";
    }
  }

  grouping ciena-pro-alarm-correlation-mount {
    container alarm-correlation {
      uses upstream-fault-masking-group;
    }
  }

  grouping ciena-pro-alarm-correlation-mount-actions;

  uses ciena-pro-alarm-correlation-mount;
}
