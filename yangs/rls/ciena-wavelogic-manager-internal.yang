module ciena-wavelogic-manager-internal {
  namespace "urn:ciena:params:xml:ns:yang:ciena-wavelogic-manager-internal";
  prefix wavelogic-manager-internal;

  import ciena-common-version {
    prefix ciena-common-version;
  }

  organization
    "Ciena Corporation";
  contact
    "Web URL: http://www.ciena.com";
  description
    "Wavelogic Manager internal module";

  revision 2022-10-13 {
    description
      "Initial revision";
    ciena-common-version:string "1.0.0";
    reference
      "1.0.0";
  }

  container settings {
    leaf some-relevant-internal-setting {
      type uint16;
    }
  }
}
