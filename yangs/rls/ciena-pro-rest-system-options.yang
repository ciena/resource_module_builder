module ciena-pro-rest-system-options {
  namespace "urn:ciena:params:xml:ns:yang:ciena-pro-rest-system-options";
  prefix ciena-pro-rest-system-options;

  import ciena-common-version {
    prefix version;
  }

  organization
    "Ciena Corporation";
  contact
    "Web URL: http://www.ciena.com/
     Postal:  7035 Ridge Road
             Hanover, Maryland 21076
             U.S.A.
     Phone:   +1 800-921-1144
     Fax:     +1 410-694-5750";
  description
    "This module describes rest deployment wide options.";

  revision 2022-09-06 {
    description
      "Added a list to block notifications for modules.";
    version:version "version" {
      version:string "1.3.0";
    }
  }
  revision 2021-06-02 {
    description
      "Added leaf for xsrf-token-support.";
    version:version "version" {
      version:string "1.2.0";
    }
  }
  revision 2021-04-15 {
    description
      "Make new leaf for certificate path";
    version:version "version" {
      version:string "1.1.0";
    }
  }
  revision 2020-09-30 {
    description
      "Initial revision.";
    version:version "version" {
      version:string "1.0.0";
    }
  }

  container rest-system-options {
    leaf options-configurable {
      type boolean;
      default "true";
      description
        "Flag to control creation of rest DB";
    }
    leaf certificate-path {
      type string;
      description
        "Path to certificate for secure access";
    }
    leaf xsrf-token-support {
      type boolean;
      default "false";
      description
        "XSRF Token support has been deprecated. If required for
         backward compatibilty, it could be enabled by using this
         flag.";
    }
    list block-notifications {
      leaf name {
        type string;
        description
          "Name of module that will be filtered out while publishing
           websocket notifications";
      }
    }
    leaf return-keys {
      type boolean;
      default "false";
      description
        "flag to return the leaf and not the keys in the list element
          when doing a GET on a leaf in a list element";
    }
    config false;
  }
}
