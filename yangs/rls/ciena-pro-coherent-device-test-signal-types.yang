module ciena-pro-coherent-device-test-signal-types {
  namespace "urn:ciena:ns:yang:coherent-device-test-signal-types";
  prefix coherent-device-test-signal-types;

  import ciena-common-version {
    prefix version;
  }
  import ciena-pro-coherent-device-types {
    prefix coherent-device-types;
  }
  import ciena-pro-coherent-device-statistics-types {
    prefix coherent-device-statistics-types;
  }

  organization
    "Ciena Corporation";
  contact
    "Web URL: http://www.ciena.com/
     Postal:  7035 Ridge Road
              Hanover, Maryland 21076
              U.S.A.
     Phone:   +1 800-921-1144
     Fax:     +1 410-694-5750";
  description
    "Test-signal definitions for coherent devices.";

  revision 2024-01-01 {
    description
      "Initial version.";
    version:version "version" {
      version:string "1.0.0";
    }
    reference
      "1.0.0";
  }

  typedef coherent-device-test-signal-pattern-enum {
    type enumeration {
      enum none {
        description
          "Not provisioned.";
      }
      enum PRBS31 {
        description
          "Pseudo random Binary Sequence of length 31.";
      }
    }
    description
      "Type for the pseudo random binary sequence pattern";
  }

  typedef coherent-device-test-signal-monitor-operational-state-enum {
    type enumeration {
      enum idle {
        description
          "Monitor is disabled.";
      }
      enum up {
        description
          "test-signal detected and not failed.";
      }
      enum down {
        description
          "loss-of-test-signal is active.";
      }
      enum degrade {
        description
          "excessive-ber is active.";
      }
    }
    description
      "Type for the test-signal operational-state.";
  }

  typedef coherent-device-test-signal-ber-threshold-enum {
    type enumeration {
      enum -5 {
        description
          "A test-signal BER threshold of 1E-5.";
      }
      enum -6 {
        description
          "A test-signal BER threshold of 1E-6.";
      }
      enum -7 {
        description
          "A test-signal BER threshold of 1E-7.";
      }
      enum -8 {
        description
          "A test-signal BER threshold of 1E-8.";
      }
      enum -9 {
        description
          "A test-signal BER threshold of 1E-9.";
      }
      enum -10 {
        description
          "A test-signal BER threshold of 1E-10.";
      }
      enum -11 {
        description
          "A test-signal BER threshold of 1E-11.";
      }
      enum -12 {
        description
          "A test-signal BER threshold of 1E-12.";
      }
      enum -13 {
        description
          "A test-signal BER threshold of 1E-13.";
      }
      enum -14 {
        description
          "A test-signal BER threshold of 1E-14.";
      }
      enum -15 {
        description
          "A test-signal BER threshold of 1E-15.";
      }
      enum -16 {
        description
          "A test-signal BER threshold of 1E-16.";
      }
    }
    description
      "Type for the test-signal ber-threshold.";
  }

  grouping coherent-device-test-signal-monitor-admin-state-group {
    leaf admin-state {
      type coherent-device-types:admin-state-enum;
      description
        "The administrative state of the entity.";
    }
    description
      "Grouping for the coherent-device test-signal admin-state.";
  }

  grouping coherent-device-test-signal-generator-config-group {
    container generator {
      uses coherent-device-test-signal-monitor-admin-state-group;
      leaf pattern {
        type coherent-device-test-signal-pattern-enum;
        description
          "The configured pseudo random binary sequence pattern of the entity.";
      }
      description
        "Container for the coherent-device test-signal generator configuration.";
    }
    description
      "Grouping for the coherent-device test-signal generator configuration.";
  }

  grouping coherent-device-test-signal-monitor-config-group {
    container monitor {
      uses coherent-device-test-signal-monitor-admin-state-group;
      leaf pattern {
        type coherent-device-test-signal-pattern-enum;
        description
          "The configured pseudo random binary sequence pattern of the entity.";
      }
      description
        "Container for the coherent-device test-signal monitor configuration.";
    }
    description
      "Grouping for the coherent-device test-signal monitor configuration.";
  }

  grouping coherent-device-test-signal-monitor-state-group {
    container monitor {
      uses coherent-device-test-signal-monitor-admin-state-group;
      leaf operational-state {
        type coherent-device-test-signal-monitor-operational-state-enum;
        description
          "The operational-state of the entity.";
      }
      leaf pattern {
        type coherent-device-test-signal-pattern-enum;
        description
          "The configured pseudo random binary sequence pattern of the entity.";
      }
      description
        "Container for the coherent-device test-signal monitor state.";
    }
    description
      "Grouping for the coherent-device test-signal monitor state.";
  }

  grouping coherent-device-test-signal-statistics-group {
    uses coherent-device-statistics-types:stat-bin-details-group;
    container bit-error-rate {
      uses coherent-device-statistics-types:instant-interval-stats-sci-notation-ber-group;
      description
        "Container for the bit-error-rate statistics.";
    }
    container error-count {
      uses coherent-device-statistics-types:instant-interval-stats-counter64-group;
      description
        "Container for the error-count statistics.";
    }
    description
      "Grouping for the coherent-device test-signal statistics.";
  }

  grouping coherent-device-test-signal-diagnostics-group {
    leaf loss-of-test-signal {
      type boolean;
      description
        "Leaf indicates loss-of-test-signal if true.";
    }
    description
      "Grouping for coherent-device test-signal diagnostics.";
  }
}
