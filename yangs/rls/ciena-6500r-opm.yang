module ciena-6500r-opm {
  yang-version 1.1;
  namespace "urn:ciena:params:xml:ns:yang:ciena-6500r-opm";
  prefix opm;

  import ciena-6500r-types {
    prefix types;
  }

  import ciena-6500r-ports {
    prefix ports;
  }

  import ciena-pro-opm {
    prefix ciena-pro-opm;
  }

  import ciena-common-version {
    prefix version;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's OPM object for the 6500r platform";

  revision 2020-09-08 {
    version:version "version" {
      version:string "0.0.4";
    }
    description
      "Use ciena-pro-opm";
  }
  revision 2020-06-30 {
    version:version "version" {
      version:string "0.0.3";
    }
    description
      "Fix version formating";
  }
  revision 2020-02-22 {
    version:version "version" {
      version:string "0.0.2";
    }
    description
      "Added leaf for signal-type";
  }
  revision 2018-01-01 {
    version:version "version" {
      version:string "0.0.1";
    }
    description
      "6500r Release 1.0";
  }

  grouping ciena-6500r-opm-mount {
    list opm {
      key "name";
      uses ciena-pro-opm:opm;

      leaf parent-port {
        type leafref {
          path "/ports:port/ports:name";
        }
        mandatory true;
        description
          "OPM facility parent port.";
      }
    }
  }

  grouping ciena-6500r-opm-mount-actions;

  uses ciena-6500r-opm-mount;
}
