module ciena-6500r-msg-relay {
  namespace "urn:ciena:params:xml:ns:yang:ciena-6500r-msg-relay";
  prefix msg-relay;

  import ciena-common-version {
    prefix ciena-common-version;
  }

  organization
    "Ciena Corporation";
  contact
    "Web URL: http://www.ciena.com
     Postal: Ciena India Pvt. Ltd.
     Sector 32, Plot 14,
     Gurgaon 122001,
     Haryana, India";
  description
    "This module describes OSC interface information required for message-relay purpose";

  revision 2020-10-24 {
    ciena-common-version:string "1.1.0";
    description
      "Added FIB in YANG. Removed interface-mapping.";
  }
  revision 2020-09-22 {
    ciena-common-version:string "1.0.0";
    description
      "Initial revision.";
  }

  list msg-relay-forwarding-table {
    key "osc-interface-tag peer-osc-interface-tag";
    description
      "Message forwarding information base (FIB).";
    leaf osc-interface-tag {
      type string;
      mandatory true;
      description
        "OSC Interface tag.";
    }

    leaf peer-osc-interface-tag {
      type string;
      mandatory true;
      description
        "Peer OSC Interface tag.";
    }
  }

  rpc msg-relay-assistant {
    description
      "msg-relay internal data lookup. Options: msg-fwd-table, stats.";
    input {
      leaf operation {
        type enumeration {
          enum "msg-fwd-table";
          enum "stats";
        }
      }
    }
  }
}
