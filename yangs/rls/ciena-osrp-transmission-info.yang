module ciena-osrp-transmission-info {
  namespace "urn:ciena:params:xml:ns:yang:ciena-osrp-transmission-info";
  prefix transmission-info;

  import ciena-osrp-types {
    prefix ciena-osrp-types;
  }
  import ciena-common-version {
    prefix ciena-common-version;
  }

  organization
    "Ciena Corporation";
  contact
    "Web URL: http://www.ciena.com
     Postal: Ciena India Pvt. Ltd.
     Sector 32, Plot 14,
     Gurgaon 122001,
     Haryana, India";
  description
    "This module describes Ciena's OSRP DTL transmission Info
     object model for the 6500r platform.";

  revision 2020-04-19 {
    description
      "6500r-series Release 2.0
       Initial revision.";
    ciena-common-version:string "1.0.0";
  }

  list transmission-info {
    key "transmission-mode";
    leaf transmission-mode {
      type ciena-osrp-types:transmission-mode;
      description
        "Name of Transmission Mode";
      mandatory true;
    }
    leaf identifier {
      type uint16 {
        range "1..65535";
      }
      description
        "Specifies the Identifier for the entry.";
      mandatory true;
    }
    leaf-list modem-type {
      type ciena-osrp-types:modem-type;
      description
        "Specifies the Modem Type";
    }
    leaf tx-minimum-spectral-width {
      type ciena-osrp-types:frequency;
      description
        "Specifies the minimum spectral width for the corresponding transmission-mode(in GHz).";
    }
  }
}
