module ciena-6500r-osrp-rls-ra-osrp-comms-link {
  yang-version 1.1;
  namespace "urn:ciena:params:xml:ns:yang:ciena-6500r-osrp-rls-ra-osrp-comms-link";
  prefix osrp-comms-link;

  import ciena-6500r-osrp-rls-ra-types {
    prefix osrp-rls-ra-types;
  }

  import ciena-common-version {
    prefix ciena-common-version;
  }

  import ietf-inet-types {
    prefix ietf;
  }

  organization
    "Ciena Corporation";
  contact
    "Web URL: http://www.ciena.com
     Postal: Ciena India Pvt. Ltd.
     Sector 32, Plot 14,
     Gurgaon 122001,
     Haryana, India";
  description
    "This module describes Ciena's osrp-rls-ra - osrp-comms-link data for osrp-rls-ra to provision Comms.";

  revision 2021-02-01 {
    ciena-common-version:string "1.2.0";
    description
      "Added new field 'inventory-version'.";
  }
  revision 2021-01-09 {
    ciena-common-version:string "1.1.0";
    description
      "Node-id length extended.";
  }
  revision 2020-08-26 {
    ciena-common-version:string "1.0.0";
    description
      "Initial revision.";
  }

  grouping ciena-6500r-osrp-rls-ra-osrp-comms-link-mount {
    list osrp-comms-link {
      key "port-name system-name";
      leaf port-name {
        type osrp-rls-ra-types:osrp-port-identifier;
        description
          "Comms-link Port Name.";
      }

      leaf system-name {
        type string {
          length "0..255";
        }
        description
          "LLDP system-name of the shelf to which the port belongs to.";
      }

      leaf inventory-version {
        type string;
        description
          "Inventory version of the service.";
      }

      leaf ip-address {
        type ietf:ip-address;
        description
          "Shelf IP address";
      }

      leaf osrp-comms-port {
        type uint16;
        description
          "Comms port of assciated OSRP to which the port belongs to.";
      }

      leaf osrp-node-id {
        type osrp-rls-ra-types:node-id-hex-type;
        description
          "Node id of associated OSRP to which the port belongs to.";
      }

      leaf osrp-node-name {
        type string;
        description
          "OSRP node name of associated OSRP to which the port belongs to.";
      }

      leaf remote-system-name {
        type string {
          length "0..255";
        }
        description
          "LLDP system-name of the remote shelf to which the port is connected to.";
      }

      leaf remote-port-name {
        type osrp-rls-ra-types:osrp-port-identifier;
        description
          "Comms-link Port Name on remote shelf to which the port is connected to.";
      }
    }
  }

  grouping ciena-6500r-osrp-rls-ra-osrp-comms-link-mount-actions;

  uses ciena-6500r-osrp-rls-ra-osrp-comms-link-mount;
}
