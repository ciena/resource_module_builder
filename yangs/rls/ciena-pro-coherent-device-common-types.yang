module ciena-pro-coherent-device-common-types {
  namespace "urn:ciena:ns:yang:coherent-device-common-types";
  prefix coherent-device-common-types;

  import ciena-common-version {
    prefix version;
  }

  organization
    "Ciena Corporation";
  contact
    "Web URL: http://www.ciena.com/
     Postal:  7035 Ridge Road
              Hanover, Maryland 21076
              U.S.A.
     Phone:   +1 800-921-1144
     Fax:     +1 410-694-5750";
  description
    "Common definitions for coherent devices.";

  revision 2024-01-01 {
    description
      "Initial version.";
    version:version "version" {
      version:string "1.0.0";
    }
    reference
      "1.0.0";
  }

  typedef string12 {
    type string {
      length "0..12";
    }
    description
      "String of up to 12 characters.";
  }

  typedef string16 {
    type string {
      length "0..16";
    }
    description
      "String of up to 16 characters.";
  }

  typedef string32 {
    type string {
      length "0..32";
    }
    description
      "String of up to 32 characters.";
  }

  typedef string64 {
    type string {
      length "0..64";
    }
    description
      "String of up to 64 characters.";
  }

  typedef string128 {
    type string {
      length "0..128";
    }
    description
      "String of up to 128 characters.";
  }

  typedef string255 {
    type string {
      length "0..255";
    }
    description
      "String of up to 255 characters.";
  }

  typedef decimal-1-dig {
    type decimal64 {
      fraction-digits 1;
    }
    description
      "Decimal value up to 1 digit precision.";
  }

  typedef decimal-2-dig {
    type decimal64 {
      fraction-digits 2;
    }
    description
      "Decimal value up to 2 digits precision.";
  }

  typedef decimal-3-dig {
    type decimal64 {
      fraction-digits 3;
    }
    description
      "Decimal value up to 3 digits precision.";
  }

  typedef decimal-scientific-notation {
    type string {
      length "0..32";
      pattern '[-+]?[0-9](\.[0-9]+)?([eE][-+]?[0-9]+)?';
    }
    description
      "Decimal represented as a string in scientific notation.";
  }

  typedef frequency-100MHz {
    type decimal64 {
      fraction-digits 1;
      range "0.0 .. max";
    }
    units "GHz";
    description
      "Frequency in GHz with 0.1 GHz precision. Value of 0.0 indicates unprovisioned (default) value. L-Band
       range is 186087.5 - 190956.2 GHz, and C-Band range is 191250.0 - 196125.0 GHz.
       Some devices may support values outside of these ranges. Range checks are
       enforced dynamically based on device capabilities.";
  }

  typedef wavelength-nm {
    type uint32;
    units "nm";
    description
      "Wavelength value in nanometers (nm).";
  }

  typedef optical-power-dBm {
    type decimal-2-dig;
    units "dBm";
    description
      "Generic type to define optical-power readings in dBm with 2 significant digits.";
  }

  typedef direction-enum {
    type enumeration {
      enum rx {
        value 1;
        description
          "Rx direction.";
      }
      enum tx {
        value 2;
        description
          "Tx direction.";
      }
    }
    description
      "Direction enum";
  }

  typedef laser-tuning-status-enum {
    type enumeration {
      enum tuned {
        value 1;
        description
          "Laser tuning complete.";
      }
      enum tuning {
        value 2;
        description
          "Laser tuning in progress.";
      }
      enum not-tuned {
        value 3;
        description
          "Laser tuning not started or laser not tuned.";
      }
      enum unavailable {
        value 4;
        description
          "Equipment present but laser tuning state cannot be determined.";
      }
      enum unknown {
        value 5;
        description
          "Cannot determine laser tuning state because equipment not available or not present.";
      }
    }
    description
      "Typedef laser tuning status.";
  }

  typedef coherent-device-statistic-interval-enum {
    type enumeration {
      enum 1-second {
        description
          "10 second";
      }
      enum 10-second {
        description
          "10 second";
      }
    }
    description
      "Type to define the intervals for which statistic reporting covers.";
  }

  typedef mac-address-string {
    type string {
      length "1..20";
    }
    description
      "MAC address string.";
  }

  typedef ip-address-with-subnet {
    type union {
      type ipv4-with-subnet;
      type ipv6-with-subnet;
      type string {
        pattern 'Unresolved';
      }
    }
    description
      "An IP prefix type that supports both IPv4 and IPv6 formats.";
  }

  typedef ip-address {
    type union {
      type ipv4-address;
      type ipv6-address;
      type string {
        pattern 'Unresolved';
      }
    }
    description
      "An IP address type that supports both IPv4 and IPv6 formats.";
  }

  typedef ipv4-address {
    type string {
      length "0..16";
      pattern '(([0-9]|[1-9][0-9]|1[0-9][0-9]|2[0-4][0-9]|25[0-5])\.){3}([0-9]|[1-9][0-9]|1[0-9][0-9]|2[0-4][0-9]|25[0-5])';
    }
    description
      "An IPv4 address represented in dotted decimal notation.";
  }

  typedef ipv4-with-subnet {
    type string {
      length "0..20";
      pattern '(([0-9]|[1-9][0-9]|1[0-9][0-9]|2[0-4][0-9]|25[0-5])\.){3}([0-9]|[1-9][0-9]|1[0-9][0-9]|2[0-4][0-9]|25[0-5])/(([0-9])|([1-2][0-9])|(3[0-2]))';
    }
    description
      "An IPv4 address and prefix represented in dotted decimal notation
       followed by a slash and a prefix length, e.g. '192.168.1.2/24'.";
  }

  typedef ipv6-address {
    type string {
      pattern '[0-9a-fA-F:\.]*';
    }
    description
      "An IPv6 address format.";
    reference
      "RFC 4291: IP Version 6 Addressing Architecture
       RFC 4007: IPv6 Scoped Address Architecture
       RFC 5952: A Recommendation for IPv6 Address Text Representation";
  }

  typedef ipv6-with-subnet {
    type string {
      pattern '((:|[0-9a-fA-F]{0,4}):)([0-9a-fA-F]{0,4}:){0,5}((([0-9a-fA-F]{0,4}:)?(:|[0-9a-fA-F]{0,4}))|(((25[0-5]|2[0-4][0-9]|[01]?[0-9]?[0-9])\.){3}(25[0-5]|2[0-4][0-9]|[01]?[0-9]?[0-9])))(/(([0-9])|([0-9]{2})|(1[0-1][0-9])|(12[0-8])))';
    }
    description
      "The ipv6-prefix type represents an IPv6 address prefix.
       The prefix length is given by the number following the
       slash character and must be less than or equal to 128.

       A prefix length value of n corresponds to an IP address
       mask that has n contiguous 1-bits from the most
       significant bit (MSB) and all other bits set to 0.

       The IPv6 address should have all bits that do not belong
       to the prefix set to zero.

       The canonical format of an IPv6 prefix has all bits of
       the IPv6 address set to zero that are not part of the
       IPv6 prefix.  Furthermore, the IPv6 address is represented
       as defined in Section 4 of RFC 5952.";
    reference
      "RFC 5952: A Recommendation for IPv6 Address Text Representation";
  }

  typedef ip-port {
    type uint16;
    description
      "An IP port number.";
  }

  typedef username-string {
    type string {
      length "0..128";
    }
    description
      "Type to represent a username string.";
  }

  typedef password-string {
    type string {
      length "0..128";
    }
    description
      "Type to represent a password string.";
  }

  typedef filename-string {
    type string {
      length "1..128";
    }
    description
      "Type to specify the path and filename to a file.";
  }

  typedef stat-precision2-dBm-type {
    type decimal64 {
      fraction-digits 2;
    }
    units "dBm";
    description
      "Statistic type for dBm units with 2 decimal precision.";
  }

  typedef stat-precision3-ps-type {
    type decimal64 {
      fraction-digits 3;
    }
    units "ps";
    description
      "Statistic type for ps units with 3 decimal precision.";
  }

  typedef stat-precision3-ps2-type {
    type decimal64 {
      fraction-digits 3;
    }
    units "ps^2";
    description
      "Statistic type for ps^2 units with 3 decimal precision.";
  }

  typedef stat-precision3-ps-nm-type {
    type decimal64 {
      fraction-digits 3;
    }
    units "ps-nm";
    description
      "Statistic type for ps/nm units with 3 decimal precision.";
  }

  typedef stat-precision3-dB-type {
    type decimal64 {
      fraction-digits 3;
    }
    units "dB";
    description
      "Statistic type for decibel units with 3 decimal precision.";
  }

  typedef stat-sci-notation-ber-type {
    type coherent-device-common-types:decimal-scientific-notation;
    units "bit-errors-per-second";
    description
      "Statistic type for a decimal64 represented in scientific notation string";
  }

  typedef stat-precision1-mhz-type {
    type decimal64 {
      fraction-digits 1;
    }
    units "MHz";
    description
      "Statistic type for Megahertz units with 1 decimal precision.";
  }

  typedef stat-precision2-percent-type {
    type decimal64 {
      fraction-digits 2;
    }
    units "percentage";
    description
      "Statistic type for percentage units with 2 decimal precision.";
  }

  typedef stat-precision1-krads-type {
    type decimal64 {
      fraction-digits 1;
    }
    units "krads/s";
    description
      "Statistic type for kiloradian per second (krad/s) units with 1 decimal precisions.";
  }

  typedef stat-precision1-degree-c-type {
    type decimal64 {
      fraction-digits 1;
    }
    units "degC";
    description
      "Statistic type for degree Celsius units with 1 decimal precision.";
  }

  typedef stat-precision2-volts-type {
    type decimal64 {
      fraction-digits 2;
    }
    units "volts";
    description
      "Statistic type for volts units with 2 decimal precision.";
  }

  typedef stat-precision2-milliamps-type {
    type decimal64 {
      fraction-digits 2;
    }
    units "mA";
    description
      "Statistic type for milliamps units with 2 decimal precision.";
  }

  typedef stat-seconds-counter8-type {
    type uint8;
    units "seconds";
    description
      "Statistic type for a seconds counter requiring an 8-bit integer.";
  }

  typedef stat-counter32-type {
    type uint32;
    description
      "Statistic type for a generic counter requiring a 32-bit integer.";
  }

  typedef stat-counter64-type {
    type uint64;
    description
      "Statistic type for a generic counter requiring a 64-bit integer.";
  }

  typedef stat-bits-counter64-type {
    type uint64;
    units "bits";
    description
      "Statistic type for a bits counter requiring a 64-bit integer.";
  }

  typedef stat-frame-counter64-type {
    type uint64;
    units "frames";
    description
      "Statistic type for a frame counter requiring a 64-bit integer.";
  }

  typedef stat-kilometer-type {
    type uint32;
    units "km";
    description
      "Distance in kilometers.";
  }

  typedef stat-microseconds-type {
    type uint32;
    units "us";
    description
      "Latency in microseconds.";
  }

  identity error-code {
    description
      "The base identity to represent error codes";
  }

  identity error-unknown {
    base error-code;
    description
      "Error was generated for unknown reason.";
  }

  identity success {
    base error-code;
    description
      "Success.";
  }

  identity info {
    base error-code;
    description
      "Extra information.";
  }

  identity warning {
    base error-code;
    description
      "Warning.";
  }

  identity error-internal {
    base error-code;
    description
      "Error was generated by an internal failure.";
  }

  identity error-does-not-exist {
    base error-code;
    description
      "Error was generated because the instance does not exist.";
  }

  identity error-already-exist {
    base error-code;
    description
      "Error was generated because the instance already exists.";
  }

  identity error-not-configurable {
    base error-code;
    description
      "Element is not configurable.";
  }

  identity error-mandatory {
    base error-code;
    description
      "Mandatory element is missing or is being deleted.";
  }

  identity error-out-of-range {
    base error-code;
    description
      "Element is out of range.";
  }

  identity error-invalid-request {
    base error-code;
    description
      "Request is not permitted on this element.";
  }

  identity error-not-supported {
    base error-code;
    description
      "Element is out of range.";
  }

  grouping return-code {
    leaf result {
      type identityref {
        base error-code;
      }
      description
        "A result code identifier.";
    }
    leaf result-str {
      type string;
      description
        "A string description of the result code.";
    }
    description
      "";
  }
}
