module ciena-6500r-transponder-proxies {
  namespace "urn:ciena:parms:xml:ns:yang:ciena-6500r-transponder-proxies";
  prefix tx-proxies;

  import ciena-6500r-tx-proxy {
    prefix ciena-6500r-tx-proxy;
  }

  import ciena-6500r-rx-proxy {
    prefix ciena-6500r-rx-proxy;
  }

  import ciena-pro-spli-common-types {
    prefix ciena-pro-spli-types;
  }

  organization
    "Ciena Corporation";
  contact
    "Web URL: http://www.ciena.com";
  description
    "This module describes Ciena's RLS discovered transponder parameter data model ";

  revision 2021-04-22 {
    description
      "Initial revision.";
  }

  container transponders {
    description
      "Top level spli-rls-ra container describing spli state information";
    list hosts {
      key "host-name";
      description
        "Information about connection states for each transponder host connected to RLS shelf";
      leaf host-name {
        type instance-identifier;
        description
          "The name of the neighbour in neighbour object";
      }

      leaf connection-state {
        type ciena-pro-spli-types:shelf-status-enum;
        description
          "The connection state with the transponder host";
      }
    }

    list tx {
      key "tx-proxy-name";
      description
        "Discovered information about transponders";
      leaf tx-proxy-name {
        type instance-identifier;
        description
          "Name of the tx-proxy object";
      }

      leaf far-end-label {
        type string;
        description
          "Opaque string containing remote far end address of the transponder. Example: nodeName-shelf-sl-port ";
      }

      container inventory {
        uses ciena-6500r-tx-proxy:tx-proxy-grouping;
      }
    }

    list rx {
      key "rx-proxy-name";
      description
        "Discovered information about receivers";
      leaf rx-proxy-name {
        type instance-identifier;
        description
          "Name of the rx-proxy object";
      }

      leaf far-end-label {
        type string;
        description
          "Opaque string containing remote far end address of the receiver. Example: nodeName-shelf-port ";
      }

      container inventory {
        uses ciena-6500r-rx-proxy:rx-proxy-grouping;
      }
    }
  }
}
