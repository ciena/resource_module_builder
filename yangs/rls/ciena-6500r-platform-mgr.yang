module ciena-6500r-platform-mgr {
  yang-version 1.1;
  namespace "urn:ciena:params:xml:ns:yang:ciena-6500r-platform-mgr";
  prefix debug;

  import ciena-common-version {
    prefix ciena-common-version;
  }

  organization
    "Ciena Corporation";
  contact
    "Web URL: http://www.ciena.com";
  description
    "This module is a placeholder for the platform-mgr";

  revision 2020-06-11 {
    description
      "Default empty file to serve as a placeholder";
    ciena-common-version:string "0.0.0";
  }
}
