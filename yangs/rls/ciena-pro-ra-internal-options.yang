module ciena-pro-ra-internal-options {
  namespace "urn:ciena:params:xml:ns:yang:ciena-pro-file-internal-options";
  prefix internal-options;

  import ciena-common-version {
    prefix ciena-common-version;
  }
  import ciena-common-yang {
    prefix ciena-common-yang;
  }

  organization
    "Ciena Corporation";
  contact
    "Web URL: http://www.ciena.com/
     Postal:  7035 Ridge Road
              Hanover, Maryland 21076
              U.S.A.
     Phone:   +1 800-921-1144
     Fax:     +1 410-694-5750";
  description
    "This module defines the object model used to subscribe to native elements.
     This also defines a list of mapper model names to be used";

  revision 2022-02-09 {
    description
      "Add mapper model";
    ciena-common-version:string "1.1.0";
  }
  revision 2022-01-22 {
    description
      "Initial revision of native elements options";
    ciena-common-version:string "1.0.0";
  }

  container internal-options {
    description
      "Top-level container for pro-ra internal data options.";
    list publisher {
      description
        "This is a list of services, domains and paths against the
         native data where the subscriber is to be registered.";
      key "path domain service";
      leaf path {
        type ciena-common-yang:target-node;
        description
          "The path of object subscribing to.";
      }
      leaf service {
        type string;
        description
          "The service where the subscriber is to be registered.";
      }
      leaf domain {
        type string;
        description
          "The domain of the service where the subscriber is to be registered.";
      }
    }
    list mapper {
      description
        "This is a list of mapper model names to be used
         for translation.";
      key "model-name";
      leaf model-name {
        type string;
        description
          "The name of translation model.";
      }
    }
  }
}
