module ciena-pro-comms-mgr {
  namespace "urn:ciena:params:xml:ns:yang:ciena-pro-comms-mgr";
  prefix ciena-pro-comms-mgr;

  import ciena-common-version {
    prefix ciena-common-version;
  }

  organization
    "Ciena Corporation";
  contact
    "Web URL: http://www.ciena.com/";
  description
    "Provides RPC for comms-mgr service to translate external
     interface name to internal interface name ";

  revision 2022-06-03 {
    description
      "Modified description of if-name-internal-get and if-name-external-get rpc's";
    ciena-common-version:string "1.0.1";
  }
  revision 2019-10-08 {
    description
      "Initial version";
    ciena-common-version:string "1.0.0";
  }

  rpc if-name-internal-get {
    input {
      leaf if-name {
        type string {
          length "1..511";
        }
        description
          "Interface name inputted by the user in external format (eg loopback)";
      }
    }
    output {
      leaf if-name {
        type string {
          length "1..511";
        }
        description
          "Interface name outputted by machine in internal OS format (eg lo) returns NULL if the translation was not successful";
      }
    }
  }

  rpc if-name-external-get {
    input {
      leaf if-name {
        type string {
          length "1..511";
        }
        description
          "Interface name inputted by the user in internal OS format (eg lo)";
      }
    }
    output {
      leaf if-name {
        type string {
          length "1..511";
        }
        description
          "Interface name outputted by machine in external format (eg loopback) returns NULL if the translation was not successful ";
      }
    }
  }
}
