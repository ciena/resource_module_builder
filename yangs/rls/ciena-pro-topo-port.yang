module ciena-pro-topo-port {
  namespace "urn:ciena:params:xml:ns:yang:ciena-pro-topo-port";
  prefix port;

  import ciena-pro-topo-types {
    prefix topo-types;
  }
  import ciena-common-version {
    prefix version;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's topological port object for the 6500r-Series platform";

  revision 2020-07-20 {
    description
      "RlS 2.1 increase size of topo-port name";
    version:version "version" {
      version:string "0.1.0";
    }
  }
  revision 2018-05-08 {
    description
      "6500r-series Release 1.0";
  }

  list topo-port {
    key "name";
    leaf name {
      type string {
        length "1..200";
      }
      description
        "Topological port identifier";
    }
    list associated-objects {
      key "name";
      uses topo-types:associated-object;
      description
        "User application defined data";
    }
  }
}
