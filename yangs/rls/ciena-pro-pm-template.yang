module ciena-pro-pm-template {
  namespace "urn:ciena:params:xml:ns:yang:ciena-pro-pm-template";
  prefix pm-template;

  import ciena-common-version {
    prefix ciena-common-version;
  }
  import ciena-pro-pm-types {
    prefix pm-types;
  }
  import ciena-pro-types {
    prefix ciena-pro-types;
  }

  organization
    "Ciena Corporation";
  contact
    "Web URL: http://www.ciena.com";
  description
    "This module describes Ciena's pm runtime objects for the Bifrost platform";

  revision 2022-02-18 {
    description
      "remove 6500 dependency";
    ciena-common-version:string "1.0.0";
  }
  revision 2019-08-22 {
    description
      "Initial revision";
  }

  list card {
    key "name";
    leaf name {
      type ciena-pro-types:pec-code;
      description
        "Pec code of the card.";
    }
    list pm-instances {
      key "pm-resource-instance";
      leaf pm-resource-instance {
        type instance-identifier;
        mandatory true;
      }
      leaf data-resource-instance {
        type instance-identifier;
        mandatory false;
        description
          "path to where data read from";
      }
      leaf secondary-data-resource-instance {
        type instance-identifier;
        mandatory false;
        description
          "secondary path to where data read from";
      }
      list pm-val {
        key "measid";
        leaf measid {
          type string;
        }
        uses pm-types:pm-measurement;
        list pm-types {
          key "montype";
          leaf montype {
            type pm-types:montype;
            description
              "pm monitoring types";
          }
          leaf qualifier {
            type pm-types:qualifier;
          }
        }
        leaf location {
          type pm-types:location;
        }
        leaf direction {
          type pm-types:direction;
        }
      }
    }
    list slot {
      key "name";
      leaf name {
        type string;
      }
    }
  }
}
