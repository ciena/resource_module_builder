module CPL-OID-MIB {
  namespace "urn:ietf:params:xml:ns:yang:smiv2:CPL-OID-MIB";
  prefix cpl-oid;

  import yang-smi {
    prefix smi;
  }

  organization
    "Ciena Corporation";
  contact
    "Ciena Corporation
     1201 Winterson Road
     Linthicum, Maryland 21090
     United States
     1-800-921-1144
     www.ciena.com";
  description
    "This is a top-level MIB for CPL whose purpose
     is to lay out the objects in the OID hierarchy";

  revision 2016-01-11 {
    description
      "Add the cplOtdr object identifier";
  }
  revision 2015-01-22 {
    description
      "Add the cpPerfMon object identifier";
  }
  revision 2014-11-28 {
    description
      "Add the pinsTx object identifier";
  }
  revision 2013-10-01 {
    description
      "Add the cplPc object identifier";
  }
  revision 2010-05-11 {
    description
      "[Revision added by libsmi due to a LAST-UPDATED clause.]";
  }
  revision 2010-05-11 {
    description
      "Cleanup ";
  }
  revision 2006-01-30 {
    description
      "Add the cplRaman object identifier";
  }
  revision 2005-02-09 {
    description
      "This oid just places the other mibs in the
       hierarchy";
  }
}
