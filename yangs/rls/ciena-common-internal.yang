module ciena-common-internal {
  namespace "urn:ciena:params:xml:ns:yang:ciena-common-internal";
  prefix options;

  import ciena-common-version {
    prefix version;
  }
  import ciena-common-yang {
    prefix yang;
  }

  organization
    "Ciena Corporation";
  contact
    "Web URL: http://www.ciena.com/
     Postal:  7035 Ridge Road
             Hanover, Maryland 21076
             U.S.A.
     Phone:   +1 800-921-1144
     Fax:     +1 410-694-5750";
  description
    "Used internally by the DDF framework components";

  revision 2021-09-15 {
    description
      "Added config options";
    version:version "version" {
      version:string "1.2.0";
    }
  }
  revision 2021-04-19 {
    description
      "Add yang-get-next to support iterative paging";
    reference
      "";
    version:version "version" {
      version:string "1.1.0";
    }
  }
  revision 2020-09-01 {
    description
      "Initial revision.";
    reference
      "";
    version:version "version" {
      version:string "1.0.0";
    }
  }

  container get-next {
    yang:alias "yang-get-next";
    leaf iterative {
      type boolean;
      default "false";
      description
        "Internal flag indicating whether data can be get from service iteratively.";
    }
    leaf more {
      type boolean;
      default "false";
      description
        "Internal flag indicating whether there is more data left in to be retrieved.";
    }
  }

  rpc shutdown-service {
    description
      "Shutdown an internal service";
  }

  container ddy-config-options {
    leaf config-dir-path {
      type string;
      description
        "Path to the config directory";
    }
    config false;
  }
}
