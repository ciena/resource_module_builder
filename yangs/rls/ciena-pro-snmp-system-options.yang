module ciena-pro-snmp-system-options {
  namespace "urn:ciena:params:xml:ns:yang:ciena-pro-snmp-system-options";
  prefix ciena-pro-snmp-system-options;

  import ciena-common-version {
    prefix version;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's SNMP model";

  revision 2020-12-23 {
    description
      "Initial revision.";
    version:version "version" {
      version:string "1.0.0";
    }
  }

  container snmp-system-options {
    container mibs {
      leaf path {
        type string;
        default "/var/opt/ap/pub/mibs";
        description
          "describes mibs file path on the system,
           default path  /var/opt/ap/pub/mibs";
      }
    }
  }
}
