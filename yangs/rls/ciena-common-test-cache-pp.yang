module ciena-common-test-cache-pp {
  namespace "urn:ciena:params:xml:ns:yang:ciena-common-test-cache-pp";
  prefix test-cache-pp;

  import ciena-common-test {
    prefix test;
  }
  import ciena-common-test-list {
    prefix testlist;
  }
  import ciena-common-yang {
    prefix ciena-common-yang;
  }

  organization
    "Ciena Corporation";
  contact
    "Web URL: http://www.ciena.com";
  description
    "Test module - Cache Publish Patches (PP)";

  revision 2021-10-19 {
    description
      "Initial revision";
  }

  grouping cache-pp-abc-grouping {
    leaf a {
      type uint8;
    }
    leaf b {
      type boolean;
    }
    leaf c {
      type string;
    }
  }

  container cache-pp-test {
    uses cache-pp-abc-grouping;
  }
}
