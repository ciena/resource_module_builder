module ciena-osrp-dtl {
  yang-version 1.1;
  namespace "urn:ciena:params:xml:ns:yang:ciena-osrp-dtl";
  prefix dtl;

  import ciena-osrp-types {
    prefix ciena-osrp-types;
  }

  import ciena-common-version {
    prefix ciena-common-version;
  }

  organization
    "Ciena Corporation";
  contact
    "Web URL: http://www.ciena.com
     Postal: Ciena India Pvt. Ltd.
     Sector 32, Plot 14,
     Gurgaon 122001,
     Haryana, India";
  description
    "This module describes Ciena's OSRP DTL (Designated Transit List)
     object model for the 6500r platform.";

  revision 2021-04-02 {
    ciena-common-version:string "1.2.2";
    description
      "Changes Transmission Information element descriptions.";
  }
  revision 2021-03-08 {
    ciena-common-version:string "1.2.1";
    description
      "associated-fail-hop typo fixed.";
  }
  revision 2021-02-08 {
    ciena-common-version:string "1.2.0";
    description
      "Addded associated-fail-hop.";
  }
  revision 2020-12-24 {
    ciena-common-version:string "1.1.1";
    description
      "Changed description in spectral-width";
  }
  revision 2020-12-08 {
    ciena-common-version:string "1.1.0";
    description
      "Added spectral-width in tx-info-data container";
  }
  revision 2019-09-06 {
    ciena-common-version:string "1.0.0";
    description
      "6500r-series Release 2.0
       YANG cleanup.";
  }
  revision 2019-04-24 {
    description
      "Initial revision.";
  }

  grouping ciena-osrp-dtl-mount {
    list dtl {
      key "name";
      leaf name {
        type ciena-osrp-types:dtl-key;
        mandatory true;
        description
          "Name of DTL. To retrieve all Dtls, use ALL/all.";
      }

      list dtl-data {
        key "nodename";
        description
          "Transit List of OSRP hops.";
        uses ciena-osrp-types:hop-info;
      }

      leaf dtl-type {
        type enumeration {
          enum "none";
          enum "manual-switch";
        }
        default "none";
        description
          "Specifies the purpose of this DTL during mesh restoration
           or manual switch operations of an SNC.";
      }

      leaf label {
        type ciena-osrp-types:label;
      }

      leaf max-freq {
        type ciena-osrp-types:frequency;
        default "196125.000";
        description
          "Maximum Frequency constraint for DTL (GHz).";
      }

      leaf min-freq {
        type ciena-osrp-types:frequency;
        default "191325.000";
        description
          "Minimum Frequency constraint for DTL (GHz).";
      }

      list tx-info-data {
        key "channel-port-name";
        description
          "List of channels' Transmission Information to use on this path.";
        leaf channel-port-name {
          type ciena-osrp-types:port-name;
          mandatory true;
          description
            "Channel Mux Port (slot/port) the transmission information applies to.";
        }

        leaf frequency {
          type ciena-osrp-types:frequency;
          description
            "Center Frequency of channel on this path.";
        }

        leaf guard-band {
          type ciena-osrp-types:spectrum;
          description
            "Guard Band for channel.";
        }

        leaf link-optimization-mode {
          type ciena-osrp-types:link-optimization-mode;
          description
            "Link Optimization Mode.";
        }

        leaf max-freq-dispersion {
          type decimal64 {
            fraction-digits 2;
          }
          units "ps-nm";
          description
            "Dispersion (ps/nm) of the path at maximum band frequency.";
        }

        leaf min-freq-dispersion {
          type decimal64 {
            fraction-digits 2;
          }
          units "ps-nm";
          description
            "Dispersion (ps/nm) of the path at minimum band frequency.";
        }

        leaf spectral-width {
          type ciena-osrp-types:spectrum;
          mandatory true;
          description
            "Spectral-width (GHz).";
        }

        leaf transmission-mode {
          type ciena-osrp-types:transmission-mode;
          description
            "Transmission Mode.";
        }
      }

      container associated-failed-hop {
        description
          "Associated hop whose failure should trigger this dtl.";
        uses ciena-osrp-types:hop-info;
      }

      leaf uuid {
        type ciena-osrp-types:uuid;
      }
    }
  }

  grouping ciena-osrp-dtl-mount-actions;

  uses ciena-osrp-dtl-mount;
}
