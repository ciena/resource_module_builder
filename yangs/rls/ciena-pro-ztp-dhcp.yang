module ciena-pro-ztp-dhcp {
  namespace "urn:ciena:params:xml:ns:yang:ciena-pro-ztp-dhcp";
  prefix ciena-pro-ztp-dhcp;

  import ciena-6500r-types {
    prefix ciena-6500r-types;
  }
  import ciena-common-version {
    prefix ciena-common-version;
  }

  organization
    "Ciena Corporation";
  contact
    "Web URL: http://www.ciena.com/";
  description
    "This module defines DHCP list for zero touch provisioning.";

  revision 2019-08-16 {
    description
      "Initial version";
    ciena-common-version:string "1.0.0";
  }

  container ztp-dhcp-leases {
    description
      "Enclosing container for the list of dhcp leases associated
       with an interface";
    list ztp-dhcp-lease {
      key "interface-name";
      description
        "The list of dhcp leases associated with an interface";
      leaf interface-name {
        type string;
        mandatory true;
        description
          "The name of the interface.";
      }
      leaf interface-addr {
        type string;
        mandatory true;
        description
          "The addr of the interface.";
      }
      leaf interface-addr-mask {
        type string;
        mandatory true;
        description
          "The mask for the interface addr.";
      }
      leaf dhcp-type {
        type enumeration {
          enum dhcp {
            description
              "The lease comes from DHCP protocol.";
          }
          enum dhcp6 {
            description
              "The lease comes from DHCP6 protocol.";
          }
        }
        mandatory true;
      }
      leaf bootfile-path {
        type string;
        mandatory true;
        description
          "The path of the bootfile. It should be in a URL format.";
      }
      leaf bootfile-name {
        type string;
        description
          "The name of the bootfile.";
      }
      leaf log-servers {
        type string;
        description
          "The remote log servers";
      }
      leaf ntp-servers {
        type string;
        description
          "The NTP servers";
      }
      leaf vendor-opts {
        type string {
          length "1..2500";
        }
        description
          "dhcpv6 option 17.";
      }
      leaf option-43 {
        type string;
        description
          "dhcp option 43.";
      }
      leaf option-231 {
        type string;
        description
          "dhcp option 231.";
      }
      leaf option-232 {
        type string;
        description
          "dhcp option 232.";
      }
      leaf option-233 {
        type string;
        description
          "dhcp option 233.";
      }
      leaf option-235 {
        type string;
        description
          "dhcp option 235.";
      }
    }
  }
}
