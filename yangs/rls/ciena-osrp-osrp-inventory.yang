module ciena-osrp-osrp-inventory {
  namespace "urn:ciena:params:xml:ns:yang:ciena-osrp-osrp-inventory";
  prefix osrp-inventory;

  import ciena-osrp-osrp-port {
    prefix ciena-osrp-osrp-port;
  }
  import ciena-osrp-osrp-conn {
    prefix ciena-osrp-osrp-conn;
  }
  import ciena-osrp-osrp-channel-diagnostics {
    prefix ciena-osrp-osrp-channel-diagnostics;
  }
  import ciena-common-yang {
    prefix yang;
  }
  import ciena-common-version {
    prefix ciena-common-version;
  }

  organization
    "Ciena Corporation";
  contact
    "Web URL: http://www.ciena.com
     Postal: Ciena India Pvt. Ltd.
     Sector 32, Plot 14,
     Gurgaon 122001,
     Haryana, India";
  description
    "This module describes Ciena's osrp complete inventory object for the 6500r platform";

  revision 2022-05-03 {
    description
      "added osrp-inventory-grouping.";
    ciena-common-version:string "1.2.1";
  }
  revision 2021-09-24 {
    description
      "mounted osrp-channel-diagnostics in sync-data";
    ciena-common-version:string "1.2.0";
  }
  revision 2020-10-12 {
    description
      "mounted osrp-conn in sync-data";
    ciena-common-version:string "1.1.0";
  }
  revision 2020-03-19 {
    description
      "6500r-series Release 2.0
       Initial revision.";
    ciena-common-version:string "1.0.0";
  }

  grouping osrp-inventory-common {
    leaf osrp-node-name {
      type string {
        length "3..512";
      }
      description
        "Name of OSRP Node.";
    }
    container sync-data {
      yang:mount-start "ciena-osrp-osrp-port";
      uses ciena-osrp-osrp-port:ciena-osrp-osrp-port-mount-data;
      uses ciena-osrp-osrp-port:ciena-osrp-osrp-port-mount-actions-notifs;
      yang:mount-end "ciena-osrp-osrp-port";
      yang:mount-start "ciena-osrp-osrp-conn";
      uses ciena-osrp-osrp-conn:ciena-osrp-osrp-conn-mount-data;
      uses ciena-osrp-osrp-conn:ciena-osrp-osrp-conn-mount-actions-notifs;
      yang:mount-end "ciena-osrp-osrp-conn";
      yang:mount-start "ciena-osrp-osrp-channel-diagnostics";
      uses ciena-osrp-osrp-channel-diagnostics:ciena-osrp-osrp-channel-diagnostics-mount-data;
      uses ciena-osrp-osrp-channel-diagnostics:ciena-osrp-osrp-channel-diagnostics-mount-actions-notifs;
      yang:mount-end "ciena-osrp-osrp-channel-diagnostics";
    }
  }

  list osrp-inventory {
    key "osrp-node-name";
    uses osrp-inventory-common;
  }
}
