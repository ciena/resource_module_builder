module CIENA-PRO-TYPES-MIB {
  namespace "urn:ietf:params:xml:ns:yang:smiv2:CIENA-PRO-TYPES-MIB";
  prefix ciena-pro;

  import CIENA-SMI {
    prefix ciena-smi;
  }
  import ietf-yang-types {
    prefix yang;
  }

  organization
    "Ciena Corporation";
  contact
    "Web: http://www.ciena.com
     Postal:   7035 Ridge Road
               Hanover, Maryland 21076
               U.S.A
     Phone:    +1 800-921-1144
     Fax:      +1 410-694-5750";
  description
    "This modules describes Ciena's release object for the all platform's";

  revision 2021-06-28 {
    description
      "Added MacAddress.";
  }
  revision 2020-10-01 {
    description
      "Initial Revision.";
  }

  typedef TimeTicks64 {
    type yang:counter64;
    description
      "This type is based on the timeticks type, but with 64-bit width.";
  }

  typedef DateTime {
    type binary;
    description
      "YYYY-MM-DDTHH:MM:SSZ+-hh:mm

       where YYYY is the year, MM is the month expressed as a two-digit
       month (zero padding if required), DD is the day of the month,
       expressed as a two digit value. T is the literal character 'T',
       HH is the hour of the day expressed as a two digit number, using
       the 24-hour clock, MM is the minute of the hour expressed as a
       two digit number. Z is the literal character 'Z', followed by a
       timezone offset expressed in hours (hh) and minutes (mm), both
       expressed as two digit numbers. The time offset is specified as
       a positive or negative offset to UTC using the '+' or '-'
       character preceding the offset.

       Optionally, fractional seconds can be expressed after the minute
       of the hour as a decimal number of unspecified precision
       reflecting fractions of a second.";
  }

  typedef DomainName {
    type string {
      length "1..253";
      pattern '.{1,253}';
    }
    description
      "A UTF-8 string with a max length of 253 characters";
  }

  typedef AlarmDirection {
    type enumeration {
      enum tx {
        value 1;
      }
      enum rx {
        value 2;
      }
      enum bi {
        value 3;
      }
    }
    description
      "";
  }

  typedef AlarmLocation {
    type enumeration {
      enum nearend {
        value 2;
      }
      enum farend {
        value 3;
      }
    }
    description
      "";
  }

  typedef AlarmSeverity {
    type enumeration {
      enum unknown {
        value 1;
      }
      enum critical {
        value 2;
      }
      enum major {
        value 3;
      }
      enum minor {
        value 4;
      }
      enum warning {
        value 5;
      }
    }
    description
      "Severity, based on X.733 perceived severity.";
  }

  typedef AlarmServiceImpact {
    type enumeration {
      enum nsa {
        value 1;
      }
      enum sa {
        value 2;
      }
    }
    description
      "Service impact, either sa (service-affecting) or nsa (not-service-affecting).";
  }

  typedef MacAddress {
    type string {
      length "6";
      pattern '(((([0-9A-Fa-f]{2})){5,5})([0-9A-Fa-f]{2}))';
    }
    description
      "It indicate the value must consist of a one-byte hex string or two-hex digits, such as 01 or AB.";
  }

  typedef DisplayString16 {
    type string {
      length "1..16";
      pattern '.{1,16}';
    }
    description
      "A UTF-8 string with a max length of 16 characters";
  }

  typedef DisplayString32 {
    type string {
      length "1..32";
      pattern '.{1,32}';
    }
    description
      "A UTF-8 string with a max length of 32 characters";
  }

  typedef DisplayString64 {
    type string {
      length "1..64";
      pattern '.{1,64}';
    }
    description
      "A UTF-8 string with a max length of 64 characters";
  }

  typedef DisplayString128 {
    type string {
      length "1..128";
      pattern '.{1,128}';
    }
    description
      "A UTF-8 string with a max length of 128 characters";
  }
}
