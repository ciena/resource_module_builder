module ciena-6500r-diagnose-equipment {
  yang-version 1.1;
  namespace "urn:ciena:params:xml:ns:yang:ciena-6500r-diagnose-equipment";
  prefix rlsdgn;

  import ciena-common-version {
    prefix ciena-common-version;
  }
  import ciena-common-yang {
    prefix ciena-common-yang;
  }
  import ietf-yang-types {
    prefix yang;
  }

  organization
    "Ciena Corporation";
  contact
    "Web URL: http://www.ciena.com";
  description
    "This module describes Ciena's diagnose equipment object for 6500r platform";

  revision 2022-05-10 {
    description
      "Initial Revision";
    ciena-common-version:string "1.0.0";
    reference
      "RLS 3.0.0";
  }

  rpc trigger-diagnose-equipment {
    input {
      leaf resource {
        type instance-identifier;
        mandatory true;
        description
          "Resource to trigger a diagnose equipment to re-evaluate alarm";
      }
    }
    output {
      uses ciena-common-yang:rpc-result-common;
    }
  }
}
