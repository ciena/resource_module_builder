module ciena-6500r-line-assoc {
  yang-version 1.1;
  namespace "urn:ciena:params:xml:ns:yang:ciena-6500r-line-assoc";
  prefix lineassoc;

  import ciena-6500r-types {
    prefix ciena-6500r-types;
  }

  import ciena-common-version {
    prefix version;
  }

  organization
    "Ciena Corporation";
  contact
    "Web URL: http://www.ciena.com/
     Postal:  7035 Ridge Road
             Hanover, Maryland 21076
             U.S.A.
     Phone:   +1 800-921-1144
     Fax:     +1 410-694-5750";
  description
    "This module describes Ciena's line association object for the 6500r platform.
     E.g. line-1 of DLE is connected to SRA (line-1) in slot1, line-2 of DLE is connected to SRA (line-1) in slot2.
     This is use to configure the communication on the EPE between cards.";

  revision 2020-06-30 {
    version:version "version" {
      version:string "0.1.1";
    }
    description
      "Fix version formating";
  }
  revision 2019-11-01 {
    version:version "version" {
      version:string "0.1.0";
    }
    description
      "Initial version";
  }

  grouping ciena-6500r-line-assoc-mount {
    list line-assoc {
      key "line-number";
      leaf line-number {
        type uint32;
        description
          "Line number";
      }

      uses ciena-6500r-types:admin-state;

      leaf local-slot-id {
        type uint32;
        description
          "slot identification";
      }

      leaf fe-slot-id {
        type uint32;
        description
          "Far end slot identification";
      }

      leaf fe-line-number {
        type uint32;
        description
          "Far end line number";
      }
    }
  }

  grouping ciena-6500r-line-assoc-mount-actions;

  uses ciena-6500r-line-assoc-mount;
}
