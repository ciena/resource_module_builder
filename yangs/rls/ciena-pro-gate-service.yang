module ciena-pro-gate-service {
  namespace "urn:ciena:params:xml:ns:yang:ciena-pro-gate-service";
  prefix gateServ;

  import ciena-common-version {
    prefix ciena-common-version;
  }

  organization
    "Ciena Corporation";
  contact
    "Web URL: http://www.ciena.com/
     Postal:  7035 Ridge Road
             Hanover, Maryland 21076
             U.S.A.
     Phone:   +1 800-921-1144
     Fax:     +1 410-694-5750";
  description
    "Monitoring of service activation and failure";

  revision 2020-10-20 {
    description
      "Initial revision";
    ciena-common-version:string "1.0.0";
  }

  rpc enter-active-state-platform {
    description
      "RPC that gets invoked when the gate-service transitions to ACTIVE state";
  }

  rpc enter-fault-state-platform {
    description
      "RPC that gets invoked when the gate-service transitions to FAULT state";
  }

  rpc enter-degrade-state-platform {
    description
      "RPC that gets invoked when the gate-service transitions to DEGRADE state";
  }
}
