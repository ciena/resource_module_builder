module ciena-pro-power-supply {
  namespace "urn:ciena:params:xml:ns:yang:ciena-pro-power-supply";
  prefix power-supply;

  import ciena-common-version {
    prefix version;
  }

  import ciena-pro-types {
    prefix ciena-pro-types;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's power supply object";

  revision 2021-05-11 {
    version:version "version" {
      version:string "1.0.0";
    }
    description
      "Initial version";
  }

  grouping power-supply {
    leaf name {
      type string;
      description
        "A power supply name";
    }

    leaf input-voltage {
      type ciena-pro-types:votage-V-1-precision;
      config false;
      description
        "Input voltage of power module";
    }
  }
}
