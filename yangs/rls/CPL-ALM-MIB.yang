module CPL-ALM-MIB {
  namespace "urn:ietf:params:xml:ns:yang:smiv2:CPL-ALM-MIB";
  prefix cpl-alm;

  import CPL-OID-MIB {
    prefix cpl-oid;
  }
  import CPL-TC-MIB {
    prefix cpl-tc;
  }
  import SNMPv2-TC {
    prefix smiv2;
  }
  import yang-smi {
    prefix smi;
  }
  import ciena-common-version {
    prefix ciena-common-version;
  }

  organization
    "Ciena Corporation";
  contact
    "Ciena Corporation
     1201 Winterson Road
     Linthicum, Maryland 21090
     United States
     1-800-921-1144
     www.ciena.com";
  description
    "CPL subtending card alarms.";

  revision 2023-03-14 {
    description
      "Add almObjWSD.";
    ciena-common-version:string "1.0.47";
  }
  revision 2023-01-30 {
    description
      "Add alarmLoopbackActiveFacility.";
    ciena-common-version:string "1.0.46";
  }
  revision 2022-06-02 {
    description
      "Add alarmProtManualSwitchActive,
           alarmProtForcedSwitchActive,
           alarmProtLockoutActive,
           alarmProtWaitToRestore,
           alarmProtWaitToRestoreRemote,
           alarmAseModeActive,
           alarmProtForcedSwitchActiveRemote,
           alarmProtLockoutActiveRemote.";
    ciena-common-version:string "1.0.45";
  }
  revision 2021-12-01 {
    description
      "Add secure eraase alarms.";
    ciena-common-version:string "1.0.44";
  }
  revision 2021-11-03 {
    description
      "Add clamped alarm.";
    ciena-common-version:string "1.0.43";
  }
  revision 2021-05-11 {
    description
      "Adding additional-info";
    ciena-common-version:string "1.0.42";
  }
  revision 2020-12-10 {
    description
      "Adding alarmDegrade and alarmOOR enum values.";
    ciena-common-version:string "1.0.41";
  }
  revision 2020-11-26 {
    description
      "Adding alarmTelemetryOTSFDI and alarmTelemetryOTSRDI.";
    ciena-common-version:string "1.0.40";
  }
  revision 2020-11-11 {
    description
      "Adding alarmObjProtection and alarmProtRemotePositionMismatch.";
    ciena-common-version:string "1.0.39";
  }
  revision 2020-11-10 {
    description
      "Adding alarmRamanActivationInhibited.";
    ciena-common-version:string "1.0.38";
  }
  revision 2020-10-22 {
    description
      "Adding alarmAutomaticShutoffDisabled.";
    ciena-common-version:string "1.0.37";
  }
  revision 2020-03-16 {
    description
      "Adding almObjWSC.";
    ciena-common-version:string "1.0.36";
  }
  revision 2019-11-29 {
    description
      "Adding alarmLowORLOUT.";
    ciena-common-version:string "1.0.35";
  }
  revision 2019-06-07 {
    description
      "Adding missing alarms from R12.9.";
    ciena-common-version:string "1.0.34";
  }
  revision 2019-04-26 {
    description
      "Added alarmCvPortidMismatch, alarmCvHighFiberLoss
       and alarmCvTxFailure.";
    ciena-common-version:string "1.0.33";
  }
  revision 2018-11-15 {
    description
      "Added alarmOscCrossFiberSuspected.";
    ciena-common-version:string "1.0.32";
  }
  revision 2018-10-02 {
    description
      "Added alarmVoaOSCtargPowUnachievable.";
    ciena-common-version:string "1.0.31";
  }
  revision 2018-04-10 {
    description
      "Added alarmPluggableMismatched.";
    ciena-common-version:string "1.0.30";
  }
  revision 2017-12-12 {
    description
      "Added alarmLowORLIN And alarmLowORLOUT alarms.";
    ciena-common-version:string "1.0.29";
  }
  revision 2016-09-23 {
    description
      "Added alarmHardwareSubsystemFailure alarm.";
    ciena-common-version:string "1.0.28";
  }
  revision 2016-06-03 {
    description
      "Added Circuit Pack Upgrade Failed alarm.";
    ciena-common-version:string "1.0.27";
  }
  revision 2016-02-23 {
    description
      "Added OTDR alarms.";
    ciena-common-version:string "1.0.26";
  }
  revision 2015-05-22 {
    description
      "Added High Temp and High Temp Warning alarms in generic section.";
    ciena-common-version:string "1.0.25";
  }
  revision 2015-04-27 {
    description
      "Added WSC Link Status Failure alarm in OSC section.";
    ciena-common-version:string "1.0.24";
  }
  revision 2015-04-23 {
    description
      "Added almObjOSC.";
    ciena-common-version:string "1.0.23";
  }
  revision 2015-04-10 {
    description
      "Included RDI, LOF and RFI alarms in OSC section.";
    ciena-common-version:string "1.0.22";
  }
  revision 2015-03-13 {
    description
      "Included Wayside Port Failure alarm in OSC section.";
    ciena-common-version:string "1.0.21";
  }
  revision 2015-02-12 {
    description
      "Included OSC alarms for T-Series OSC support.";
    ciena-common-version:string "1.0.20";
  }
  revision 2014-07-28 {
    description
      "Add group index handling";
    ciena-common-version:string "1.0.19";
  }
  revision 2014-05-28 {
    description
      "Add alarmSoftwareSubsystemFailure";
    ciena-common-version:string "1.0.18";
  }
  revision 2014-04-07 {
    description
      "Increase the upper limit of the cplAlarmInstanceNumber to 255";
    ciena-common-version:string "1.0.17";
  }
  revision 2014-01-07 {
    description
      "Add alarmFiberIdTxFailure";
    ciena-common-version:string "1.0.16";
  }
  revision 2013-10-24 {
    description
      "Add alarmHighOpticalPower";
    ciena-common-version:string "1.0.15";
  }
  revision 2013-10-01 {
    description
      "Add alarmPluggableCardMissing, alarmPluggableExcessModuleTemperature,
       alarmPluggableGeneralHwFailurePotSA, alarmPluggableGeneralHwFailureNSA
       and alarmPluggableForceFail.
       Add almObjPluggable.
       Increase the upper limit of the cplAlarmInstanceNumber to 36.
       Add pluggableForceFailTable.";
    ciena-common-version:string "1.0.14";
  }
  revision 2013-09-10 {
    description
      "Add alarmLaserSafetyOutputPowerReduced";
    ciena-common-version:string "1.0.13";
  }
  revision 2013-03-15 {
    description
      "[Revision added by libsmi due to a LAST-UPDATED clause.]";
    ciena-common-version:string "1.0.12";
  }
  revision 2013-03-15 {
    description
      "Add alarmChcMsgIncarnMismatch";
    ciena-common-version:string "1.0.11";
  }
  revision 2012-01-15 {
    description
      "Add voaOutputLOS and voaInputLOS";
    ciena-common-version:string "1.0.10";
  }
  revision 2010-05-11 {
    description
      "Editorial Cleanup and move alarmAmpGainOutOfRange
       from eqpt(20) to fac(1018).";
    ciena-common-version:string "1.0.9";
  }
  revision 2008-02-02 {
    description
      "Add alarmShutoffLatch.";
    ciena-common-version:string "1.0.8";
  }
  revision 2008-02-02 {
    description
      "Add alarmExcessPumpTemperature, alarmExcessOCM
       Temperature, alarmInputOpticalOverload,
       alarmAmpGainOutOfRange.";
    ciena-common-version:string "1.0.7";
  }
  revision 2007-05-02 {
    description
      "Increase the upper limit of the
       cplAlarmInstanceNumber to 12.";
    ciena-common-version:string "1.0.6";
  }
  revision 2007-02-09 {
    description
      "Add alarmShutoff.";
    ciena-common-version:string "1.0.5";
  }
  revision 2006-11-07 {
    description
      "Remove alarmLLLDown and alarmEthernetLink,
       and replace them with an alarm for each of
       the two interfaces. ";
    ciena-common-version:string "1.0.4";
  }
  revision 2006-10-12 {
    description
      "Add alarmLatchOpen,alarmLLLDown,alarmEthernetLink
       and alarmForceFail alarms.
       Add reevaluateAlarms, and forceFail object types.";
    ciena-common-version:string "1.0.3";
  }
  revision 2006-06-22 {
    description
      "Add the alarms, alarmForceNoShutoff and
       alarmBelowTurnOnThreshold";
    ciena-common-version:string "1.0.2";
  }
  revision 2006-01-30 {
    description
      "Add alarm object name for the Raman amplifier";
    ciena-common-version:string "1.0.1";
  }
  revision 2005-01-14 {
    description
      "";
    ciena-common-version:string "1.0.0";
  }

  typedef AlarmAdditionalInfo {
    type string {
      length "0..127";
    }
    description
      "Holds additional information.";
  }

  typedef AlarmObjectName {
    type enumeration {
      enum almObjEQPT {
        value 1;
      }
      enum almObjEDFA {
        value 2;
      }
      enum almObjOPTMON {
        value 3;
      }
      enum almObjVOA {
        value 4;
      }
      enum almObjOPM {
        value 5;
      }
      enum almObjAM {
        value 6;
      }
      enum almObjUnsupported {
        value 7;
      }
      enum almObjRaman {
        value 8;
      }
      enum almObjIdler {
        value 9;
      }
      enum almObjPluggable {
        value 10;
      }
      enum almObjOSC {
        value 11;
      }
      enum almObjOTDR {
        value 12;
      }
      enum almObjCV {
        value 13;
      }
      enum almObjTelemetry {
        value 14;
      }
      enum almObjWSC {
        value 15;
      }
      enum almObjProtection {
        value 16;
      }
      enum almObjWSD {
        value 17;
      }
    }
    description
      "Name of the objects";
  }

  typedef CplAlarmId {
    type enumeration {
      enum alarmMinorFanFailure {
        value 1;
      }
      enum alarmCriticalFanFailure {
        value 2;
      }
      enum alarmFanMissing {
        value 3;
      }
      enum alarmPUPSAFailure {
        value 4;
      }
      enum alarmPUPSBFailure {
        value 5;
      }
      enum alarmBatteryFeedA {
        value 6;
      }
      enum alarmBatteryFeedB {
        value 7;
      }
      enum alarmExcessPCBTemperature {
        value 8;
      }
      enum alarmExcessModuleTemperature {
        value 9;
      }
      enum alarmInputLOS {
        value 10;
      }
      enum alarmGeneralHwFailurePotSA {
        value 11;
      }
      enum alarmGeneralHwFailureNSA {
        value 12;
      }
      enum alarmLatchOpen {
        value 13;
      }
      enum alarmLLLDownA {
        value 14;
      }
      enum alarmLLLDownB {
        value 15;
      }
      enum alarmEthernetLinkA {
        value 16;
      }
      enum alarmEthernetLinkB {
        value 17;
      }
      enum alarmForceFail {
        value 18;
      }
      enum alarmExcessOCMTemperature {
        value 19;
      }
      enum alarmHighOpticalPower {
        value 20;
      }
      enum alarmFiberIdTxFailure {
        value 21;
      }
      enum alarmSoftwareSubsystemFailure {
        value 22;
      }
      enum alarmHighTemperatureWarning {
        value 23;
      }
      enum alarmHighTemperature {
        value 24;
      }
      enum alarmCircuitPackUpgradeFailed {
        value 25;
      }
      enum alarmAutoUpgradeInProgress {
        value 26;
      }
      enum alarmHardwareSubsystemFailure {
        value 27;
      }
      enum alarmDegradeLow {
        value 28;
      }
      enum alarmDegradeHigh {
        value 29;
      }
      enum alarmOORLow {
        value 30;
      }
      enum alarmOORHigh {
        value 31;
      }
      enum alarmSecureEraseInProgress {
        value 32;
      }
      enum alarmSecureEraseFailed {
        value 33;
      }
      enum alarmSecureEraseCompleted {
        value 34;
      }
      enum alarmOutputLOS {
        value 1001;
      }
      enum alarmTCShutoff {
        value 1002;
      }
      enum alarmLowORL {
        value 1003;
      }
      enum alarmAPR {
        value 1004;
      }
      enum alarmExcessivePumpCurrent {
        value 1005;
      }
      enum alarmExcessiveTECCurrent {
        value 1006;
      }
      enum alarmPumpCurrentSource {
        value 1008;
      }
      enum alarmVOAFailure {
        value 1009;
      }
      enum alarmForceShutoff {
        value 1010;
      }
      enum alarmForceAPR {
        value 1011;
      }
      enum alarmForceNoShutoff {
        value 1012;
      }
      enum alarmBelowTurnOnThreshold {
        value 1013;
      }
      enum alarmShutoff {
        value 1014;
      }
      enum alarmShutoffLatch {
        value 1015;
      }
      enum alarmExcessPumpTemperature {
        value 1016;
      }
      enum alarmAmpGainOutOfRange {
        value 1017;
      }
      enum alarmInputOpticalOverload {
        value 1018;
      }
      enum alarmLaserSafetyOutputPowerReduced {
        value 1019;
      }
      enum alarmAutomaticShutoff {
        value 1020;
      }
      enum alarmOLF {
        value 1021;
      }
      enum alarmLowORLIN {
        value 1022;
      }
      enum alarmLowORLOUT {
        value 1023;
      }
      enum alarmAutomaticShutoffDisabled {
        value 1024;
      }
      enum alarmClampedState {
        value 1025;
      }
      enum alarmAseModeActive {
        value 1026;
      }
      enum alarmOscLOS {
        value 2000;
      }
      enum alarmOscLOL {
        value 2001;
      }
      enum alarmOscSignalDegrade {
        value 2002;
      }
      enum alarmOscAutoShutoffCompromised {
        value 2003;
      }
      enum alarmOscRDI {
        value 2004;
      }
      enum alarmOscRFI {
        value 2005;
      }
      enum alarmOscLOF {
        value 2006;
      }
      enum alarmOscCrossFiberSuspected {
        value 2007;
      }
      enum alarmWscPortFailure {
        value 2100;
      }
      enum alarmWscLinkStatusFailure {
        value 2101;
      }
      enum alarmVoaOutputLOS {
        value 6000;
      }
      enum alarmVoaInputLOS {
        value 6001;
      }
      enum alarmVoaOSCtargPowUnachievable {
        value 6002;
      }
      enum alarmTelemetryRDI {
        value 6200;
      }
      enum alarmTelemetryOTSFDI {
        value 6201;
      }
      enum alarmTelemetryOTSRDI {
        value 6202;
      }
      enum alarmRamanCalibrationRequired {
        value 6500;
      }
      enum alarmRamanFailToTurnOn {
        value 6501;
      }
      enum alarmRamanTargetUnachievable {
        value 6502;
      }
      enum alarmRamanActivationInhibited {
        value 6503;
      }
      enum alarmCvPortidMismatch {
        value 6700;
      }
      enum alarmCvHighFiberLoss {
        value 6701;
      }
      enum alarmCvTxFailure {
        value 6702;
      }
      enum alarmChcMsgIncarnMismatch {
        value 7000;
      }
      enum alarmOtdrInProgress {
        value 7500;
      }
      enum alarmTelemetryLossOfSignal {
        value 7501;
      }
      enum alarmOtdrHiRelection {
        value 7502;
      }
      enum alarmOtdrHiLoss {
        value 7503;
      }
      enum alarmOtdrHiRelectionShort {
        value 7504;
      }
      enum alarmOtdrHiLossShort {
        value 7505;
      }
      enum alarmOtdrHiOffice {
        value 7506;
      }
      enum alarmPluggableCardMissing {
        value 8000;
      }
      enum alarmPluggableExcessModuleTemperature {
        value 8001;
      }
      enum alarmPluggableGeneralHwFailurePotSA {
        value 8002;
      }
      enum alarmPluggableGeneralHwFailureNSA {
        value 8003;
      }
      enum alarmPluggableForceFail {
        value 8004;
      }
      enum alarmPluggableMismatched {
        value 8005;
      }
      enum alarmProtRemotePositionMismatch {
        value 9000;
      }
      enum alarmProtManualSwitchActive {
        value 9001;
      }
      enum alarmProtForcedSwitchActive {
        value 9002;
      }
      enum alarmProtLockoutActive {
        value 9003;
      }
      enum alarmProtWaitToRestore {
        value 9004;
      }
      enum alarmProtWaitToRestoreRemote {
        value 9005;
      }
      enum alarmProtForcedSwitchActiveRemote {
        value 9006;
      }
      enum alarmProtLockoutActiveRemote {
        value 9007;
      }
      enum alarmLoopbackActiveFacility {
        value 10000;
      }
    }
    description
      "";
  }

  typedef PluggableModuleIndex {
    type int32 {
      range "1";
    }
  }

  typedef CplAlarmTestFault {
    type binary {
      length "5";
    }
    description
      "FOR DEBUGGING USE ONLY
       byte 1: raise or clear,
       byte 2: instance number,
       byte 3: faultId, from the alarm table
       byte 4: faultId, from the alarm table
       byte 5: cplAlarmObjectName";
  }

  typedef GroupIndex {
    type int32 {
      range "1..8";
    }
  }

  container groupAlarms {
    list groupAlarmEntry {
      key "groupAlarmGroupNumber groupAlarmId
           groupAlarmInstanceNumber groupAlarmObjectName";
      description
        "";
      smi:oid "1.3.6.1.4.1.562.73.5.11.1.1";
      leaf groupAlarmGroupNumber {
        type int32 {
          range "1..255";
        }
        description
          "This value represents the group this facility exists
           in. For example, what subslot it is in.";
        smi:oid "1.3.6.1.4.1.562.73.5.11.1.1.1";
      }
      leaf groupAlarmId {
        type cpl-alm:CplAlarmId;
        description
          "The alarm identifier";
        smi:oid "1.3.6.1.4.1.562.73.5.11.1.1.2";
      }
      leaf groupAlarmInstanceNumber {
        type int32 {
          range "1..255";
        }
        description
          "For facility type alarms on the amp, this
           corresponds to the EDFA (1 to 16). For other
           facilities, it corresponds to which fiber pair
           on the subcard. For equipment type alarms,for which
           only a single instance exists on the subcard, the
           value is 1.  For equipment type alarms against
           subcard module, the value is the subcard
           module id.";
        smi:oid "1.3.6.1.4.1.562.73.5.11.1.1.3";
      }
      leaf groupAlarmTimestamp {
        type smiv2:DateAndTime;
        config false;
        description
          "The time that this alarm was raised or cleared.
           Note that the field lastAlarmDateAndTime
           must be updated every time an alarm is raised
           or cleared. If the alarm was raised before the
           Time of Day has been set, a default time of
           Jan 1/2004, 00:00:00 is used, and is not changed
           if the Time of Day is subsequently set.";
        smi:oid "1.3.6.1.4.1.562.73.5.11.1.1.4";
      }
      leaf groupAlarmState {
        type cpl-tc:AlarmState;
        config false;
        description
          "raised or cleared";
        smi:oid "1.3.6.1.4.1.562.73.5.11.1.1.5";
      }
      leaf groupAlarmObjectName {
        type cpl-alm:AlarmObjectName;
        description
          "Describes which object on the subcard had the fault";
        smi:oid "1.3.6.1.4.1.562.73.5.11.1.1.6";
      }
    }
    list groupLastAlarmDateAndTimeEntry {
      key "groupLastAlarmDateAndTimeGroupNum";
      description
        "";
      smi:oid "1.3.6.1.4.1.562.73.5.11.3.1";
      leaf groupLastAlarmDateAndTimeGroupNum {
        type cpl-alm:GroupIndex;
        description
          "This value represents the group this facility exists
           in. For example, what subslot it is in.";
        reference
          "";
        smi:oid "1.3.6.1.4.1.562.73.5.11.3.1.1";
      }
      leaf groupLastAlarmDateAndTime {
        type smiv2:DateAndTime;
        config false;
        description
          "Update this value each time an event is sent
           (raise or clear). The manager can poll this single
            variable, and if it has been updated since the
            manager last polled, the mgr can do a get on the
            entire table.";
        smi:oid "1.3.6.1.4.1.562.73.5.11.3.1.2";
      }
    }
    list groupReraiseAlarmsEntry {
      key "groupReraiseAlarmsGroupNum";
      description
        "";
      smi:oid "1.3.6.1.4.1.562.73.5.11.4.1";
      leaf groupReraiseAlarmsGroupNum {
        type cpl-alm:GroupIndex;
        description
          "This value represents the group this facility exists
           in. For example, what subslot it is in.";
        reference
          "";
        smi:oid "1.3.6.1.4.1.562.73.5.11.4.1.1";
      }
      leaf groupReraiseAlarms {
        type cpl-tc:Boolean;
        config true;
        description
          "To have the subcard re-raise notifications
           for all supported alarms, both those that are
           RAISED and those that are CLEARED, the value of
           this variable is set to TRUE. This value will
           never be read.";
        smi:oid "1.3.6.1.4.1.562.73.5.11.4.1.2";
      }
    }
    list groupAlmFaultInsertionEntry {
      key "groupAlmFaultInsertionGroupNum";
      description
        "";
      smi:oid "1.3.6.1.4.1.562.73.5.11.5.1";
      leaf groupAlmFaultInsertionGroupNum {
        type cpl-alm:GroupIndex;
        description
          "This value represents the group this facility exists
           in. For example, what subslot it is in.";
        reference
          "";
        smi:oid "1.3.6.1.4.1.562.73.5.11.5.1.1";
      }
      leaf groupAlmFaultInsertion {
        type cpl-alm:CplAlarmTestFault;
        config true;
        description
          "FOR DEBUG/TEST USE ONLY.

           This MIB variable (actually a structure) is used only for
           testing the alarm system interface by the manager. The manager
           sets this variable, and gets a notification from the agent.

           The setting or clearing of any fault through this interface is not
           intended to change the state of the subcard in any way,
           nor inhibit the gathering of fault information on the subcard.
           Only a notifiction indicating that the given fault has
           occurred/cleared (as specified in the input) is sent. Therefore,
           the alarm table is NOT updated when a value is set for this
           variable.

           After testing has completed, the tester is expected to set the
           reRaiseAlarms MIB variable to cause the actual state of all
           fault points to be sent. ";
        smi:oid "1.3.6.1.4.1.562.73.5.11.5.1.2";
      }
    }
    list groupReevaluateAlarmsEntry {
      key "groupReevaluateAlarmsGroupNum";
      description
        "";
      smi:oid "1.3.6.1.4.1.562.73.5.11.6.1";
      leaf groupReevaluateAlarmsGroupNum {
        type cpl-alm:GroupIndex;
        description
          "This value represents the group this facility exists
           in. For example, what subslot it is in.";
        reference
          "";
        smi:oid "1.3.6.1.4.1.562.73.5.11.6.1.1";
      }
      leaf groupReevaluateAlarms {
        type cpl-tc:Boolean;
        config true;
        description
          "To have the subcard reevaluate the state
           off all of it's latched alarms and send
           notifications for all alarms that change state.
           This will be used to unlatch alarms.
           This value will never be set to FALSE, and
           consecutive sets to TRUE should all reevaluate
           alarms. This value will never be read.";
        smi:oid "1.3.6.1.4.1.562.73.5.11.6.1.2";
      }
    }
    list groupForceFailEntry {
      key "groupIndex";
      description
        "";
      smi:oid "1.3.6.1.4.1.562.73.5.11.7.1";
      leaf groupIndex {
        type cpl-alm:GroupIndex;
        description
          "This is the row number in the table";
        smi:oid "1.3.6.1.4.1.562.73.5.11.7.1.1";
      }
      leaf groupForceFail {
        type cpl-tc:Boolean;
        config true;
        description
          "To force fail a subcard module. When true, the
           module should turn the RED LED on, add a CP fail
           entry to the flightrecorder, and raise the
           forceFail alarm. When false, the subcard should turn
           out the RED LED, and clear the forceFail alarm.
           The manager and agent share control of the subcard
           fail LED, but this variable is only set and
           cleared by the manager. This and
           subcardMiscDataControlRedLed will be used exclusively
           (i.e. the shelf controller will only use one of
           the two variables to control the state of the
           RED LED).";
        smi:default "false";
        smi:oid "1.3.6.1.4.1.562.73.5.11.7.1.8";
      }
    }
    leaf groupMgmtProcReady {
      type cpl-tc:Boolean;
      config true;
      description
        "To have a subcard to inform it that MP is ready
         to process OAM request. This will be used to verify
         card presence. This value will never be set to false.
         This value will never be read.";
      smi:oid "1.3.6.1.4.1.562.73.5.11.8";
    }
    list groupAlarmEntry2 {
      key "groupAlarmGroupNumber2 groupAlarmId2 groupAlarmInstanceNumber2
           groupAlarmSecondInstance2 groupAlarmObjectName2";
      description
        "";
      smi:oid "1.3.6.1.4.1.562.73.5.11.9.1";
      leaf groupAlarmGroupNumber2 {
        type int32 {
          range "1..255";
        }
        description
          "This value represents the group this facility exists
           in. For example, what subslot it is in.";
        smi:oid "1.3.6.1.4.1.562.73.5.11.9.1.1";
      }
      leaf groupAlarmId2 {
        type cpl-alm:CplAlarmId;
        description
          "The alarm identifier";
        smi:oid "1.3.6.1.4.1.562.73.5.11.9.1.2";
      }
      leaf groupAlarmInstanceNumber2 {
        type int32 {
          range "1..255";
        }
        description
          "For facility type alarms on the amp, this
           corresponds to the EDFA (1 to 16). For other
           facilities, it corresponds to which fiber pair
           on the subcard. For equipment type alarms,for which
           only a single instance exists on the subcard, the
           value is 1.  For equipment type alarms against
           subcard module, the value is the subcard
           module id.";
        smi:oid "1.3.6.1.4.1.562.73.5.11.9.1.3";
      }
      leaf groupAlarmSecondInstance2 {
        type int32 {
          range "1..255";
        }
        description
          "This is used when a facility is indexed using two separate instances.
           For example, the OTDR facility is indexed using port and wavelength index.";
        smi:oid "1.3.6.1.4.1.562.73.5.11.9.1.4";
      }
      leaf groupAlarmObjectName2 {
        type cpl-alm:AlarmObjectName;
        description
          "Describes which object on the subcard had the fault";
        smi:oid "1.3.6.1.4.1.562.73.5.11.9.1.5";
      }
      leaf groupAlarmState2 {
        type cpl-tc:AlarmState;
        config false;
        description
          "raised or cleared";
        smi:oid "1.3.6.1.4.1.562.73.5.11.9.1.6";
      }
      leaf groupAlarmTimestamp2 {
        type smiv2:DateAndTime;
        config false;
        description
          "The time that this alarm was raised or cleared.
           Note that the field lastAlarmDateAndTime
           must be updated every time an alarm is raised
           or cleared. If the alarm was raised before the
           Time of Day has been set, a default time of
           Jan 1/2004, 00:00:00 is used, and is not changed
           if the Time of Day is subsequently set.";
        smi:oid "1.3.6.1.4.1.562.73.5.11.9.1.7";
      }
    }
    smi:oid "1.3.6.1.4.1.562.73.5.11";
  }

  notification cplAlarmNotification2 {
    description
      "Alarm notification, sent to the SNMP notification
       destination";
    smi:oid "1.3.6.1.4.1.562.73.5.4.0.2";
    leaf cplAlarmId {
      type CplAlarmId;
      description
        "Automagically generated leafref leaf.";
    }
    leaf cplAlarmState {
      type cpl-tc:AlarmState;
      description
        "raised or cleared";
      smi:oid "1.3.6.1.4.1.562.73.5.3.1.4";
    }
    leaf cplAlarmObjectName {
      type AlarmObjectName;
      description
        "Automagically generated leafref leaf.";
    }
    leaf cplAlarmInstanceNumber {
      type string;
      description
        "Automagically generated leafref leaf.";
    }
    leaf cplAlarmTimestamp {
      type smiv2:DateAndTime;
      description
        "The time that this alarm was raised or cleared.
         Note that the field lastAlarmDateAndTime
         must be updated every time an alarm is raised
         or cleared. If the alarm was raised before the
         Time of Day has been set, a default time of
         Jan 1/2004, 00:00:00 is used, and is not changed
         if the Time of Day is subsequently set.";
      smi:oid "1.3.6.1.4.1.562.73.5.3.1.3";
    }
    leaf cplAlarmAdditionalInfo {
      type cpl-alm:AlarmAdditionalInfo;
      description
        "Store additional info where applicable";
      smi:oid "1.3.6.1.4.1.562.73.5.3.1.6";
    }
  }

  notification groupAlarmNotification {
    description
      "Alarm notification, sent to the SNMP notification
       destination";
    smi:oid "1.3.6.1.4.1.562.73.5.11.2.0.1";
    container groupAlarmNotification-groupAlarmGroupNumber {
      leaf groupAlarmId {
        type leafref {
          path "/cpl-alm:groupAlarms/cpl-alm:groupAlarmEntry/cpl-alm:groupAlarmId";
        }
        description
          "Automagically generated leafref leaf.";
      }
      leaf groupAlarmInstanceNumber {
        type leafref {
          path "/cpl-alm:groupAlarms/cpl-alm:groupAlarmEntry/cpl-alm:groupAlarmInstanceNumber";
        }
        description
          "Automagically generated leafref leaf.";
      }
      leaf groupAlarmObjectName {
        type leafref {
          path "/cpl-alm:groupAlarms/cpl-alm:groupAlarmEntry/cpl-alm:groupAlarmObjectName";
        }
        description
          "Automagically generated leafref leaf.";
      }
      leaf groupAlarmGroupNumber {
        type leafref {
          path "/cpl-alm:groupAlarms/cpl-alm:groupAlarmEntry/cpl-alm:groupAlarmGroupNumber";
        }
        description
          "Automagically generated leafref leaf.";
      }
    }
    container groupAlarmNotification-groupAlarmId {
      leaf groupAlarmGroupNumber {
        type leafref {
          path "/cpl-alm:groupAlarms/cpl-alm:groupAlarmEntry/cpl-alm:groupAlarmGroupNumber";
        }
        description
          "Automagically generated leafref leaf.";
      }
      leaf groupAlarmInstanceNumber {
        type leafref {
          path "/cpl-alm:groupAlarms/cpl-alm:groupAlarmEntry/cpl-alm:groupAlarmInstanceNumber";
        }
        description
          "Automagically generated leafref leaf.";
      }
      leaf groupAlarmObjectName {
        type leafref {
          path "/cpl-alm:groupAlarms/cpl-alm:groupAlarmEntry/cpl-alm:groupAlarmObjectName";
        }
        description
          "Automagically generated leafref leaf.";
      }
      leaf groupAlarmId {
        type leafref {
          path "/cpl-alm:groupAlarms/cpl-alm:groupAlarmEntry/cpl-alm:groupAlarmId";
        }
        description
          "Automagically generated leafref leaf.";
      }
    }
    container groupAlarmNotification-groupAlarmState {
      leaf groupAlarmGroupNumber {
        type leafref {
          path "/cpl-alm:groupAlarms/cpl-alm:groupAlarmEntry/cpl-alm:groupAlarmGroupNumber";
        }
        description
          "Automagically generated leafref leaf.";
      }
      leaf groupAlarmId {
        type leafref {
          path "/cpl-alm:groupAlarms/cpl-alm:groupAlarmEntry/cpl-alm:groupAlarmId";
        }
        description
          "Automagically generated leafref leaf.";
      }
      leaf groupAlarmInstanceNumber {
        type leafref {
          path "/cpl-alm:groupAlarms/cpl-alm:groupAlarmEntry/cpl-alm:groupAlarmInstanceNumber";
        }
        description
          "Automagically generated leafref leaf.";
      }
      leaf groupAlarmObjectName {
        type leafref {
          path "/cpl-alm:groupAlarms/cpl-alm:groupAlarmEntry/cpl-alm:groupAlarmObjectName";
        }
        description
          "Automagically generated leafref leaf.";
      }
      leaf groupAlarmState {
        type cpl-tc:AlarmState;
        description
          "raised or cleared";
        smi:oid "1.3.6.1.4.1.562.73.5.11.1.1.5";
      }
    }
    container groupAlarmNotification-groupAlarmObjectName {
      leaf groupAlarmGroupNumber {
        type leafref {
          path "/cpl-alm:groupAlarms/cpl-alm:groupAlarmEntry/cpl-alm:groupAlarmGroupNumber";
        }
        description
          "Automagically generated leafref leaf.";
      }
      leaf groupAlarmId {
        type leafref {
          path "/cpl-alm:groupAlarms/cpl-alm:groupAlarmEntry/cpl-alm:groupAlarmId";
        }
        description
          "Automagically generated leafref leaf.";
      }
      leaf groupAlarmInstanceNumber {
        type leafref {
          path "/cpl-alm:groupAlarms/cpl-alm:groupAlarmEntry/cpl-alm:groupAlarmInstanceNumber";
        }
        description
          "Automagically generated leafref leaf.";
      }
      leaf groupAlarmObjectName {
        type leafref {
          path "/cpl-alm:groupAlarms/cpl-alm:groupAlarmEntry/cpl-alm:groupAlarmObjectName";
        }
        description
          "Automagically generated leafref leaf.";
      }
    }
    container groupAlarmNotification-groupAlarmInstanceNumber {
      leaf groupAlarmGroupNumber {
        type leafref {
          path "/cpl-alm:groupAlarms/cpl-alm:groupAlarmEntry/cpl-alm:groupAlarmGroupNumber";
        }
        description
          "Automagically generated leafref leaf.";
      }
      leaf groupAlarmId {
        type leafref {
          path "/cpl-alm:groupAlarms/cpl-alm:groupAlarmEntry/cpl-alm:groupAlarmId";
        }
        description
          "Automagically generated leafref leaf.";
      }
      leaf groupAlarmObjectName {
        type leafref {
          path "/cpl-alm:groupAlarms/cpl-alm:groupAlarmEntry/cpl-alm:groupAlarmObjectName";
        }
        description
          "Automagically generated leafref leaf.";
      }
      leaf groupAlarmInstanceNumber {
        type leafref {
          path "/cpl-alm:groupAlarms/cpl-alm:groupAlarmEntry/cpl-alm:groupAlarmInstanceNumber";
        }
        description
          "Automagically generated leafref leaf.";
      }
    }
    container groupAlarmNotification-groupAlarmTimestamp {
      leaf groupAlarmGroupNumber {
        type leafref {
          path "/cpl-alm:groupAlarms/cpl-alm:groupAlarmEntry/cpl-alm:groupAlarmGroupNumber";
        }
        description
          "Automagically generated leafref leaf.";
      }
      leaf groupAlarmId {
        type leafref {
          path "/cpl-alm:groupAlarms/cpl-alm:groupAlarmEntry/cpl-alm:groupAlarmId";
        }
        description
          "Automagically generated leafref leaf.";
      }
      leaf groupAlarmInstanceNumber {
        type leafref {
          path "/cpl-alm:groupAlarms/cpl-alm:groupAlarmEntry/cpl-alm:groupAlarmInstanceNumber";
        }
        description
          "Automagically generated leafref leaf.";
      }
      leaf groupAlarmObjectName {
        type leafref {
          path "/cpl-alm:groupAlarms/cpl-alm:groupAlarmEntry/cpl-alm:groupAlarmObjectName";
        }
        description
          "Automagically generated leafref leaf.";
      }
      leaf groupAlarmTimestamp {
        type smiv2:DateAndTime;
        description
          "The time that this alarm was raised or cleared.
           Note that the field lastAlarmDateAndTime
           must be updated every time an alarm is raised
           or cleared. If the alarm was raised before the
           Time of Day has been set, a default time of
           Jan 1/2004, 00:00:00 is used, and is not changed
           if the Time of Day is subsequently set.";
        smi:oid "1.3.6.1.4.1.562.73.5.11.1.1.4";
      }
    }
  }

  notification groupAlarmNotification2 {
    description
      "Alarm notification, sent to the SNMP notification
       destination";
    smi:oid "1.3.6.1.4.1.562.73.5.11.2.0.2";
    container groupAlarmNotification2-groupAlarmGroupNumber2 {
      leaf groupAlarmId2 {
        type leafref {
          path "/cpl-alm:groupAlarms/cpl-alm:groupAlarmEntry2/cpl-alm:groupAlarmId2";
        }
        description
          "Automagically generated leafref leaf.";
      }
      leaf groupAlarmInstanceNumber2 {
        type leafref {
          path "/cpl-alm:groupAlarms/cpl-alm:groupAlarmEntry2/cpl-alm:groupAlarmInstanceNumber2";
        }
        description
          "Automagically generated leafref leaf.";
      }
      leaf groupAlarmSecondInstance2 {
        type leafref {
          path "/cpl-alm:groupAlarms/cpl-alm:groupAlarmEntry2/cpl-alm:groupAlarmSecondInstance2";
        }
        description
          "Automagically generated leafref leaf.";
      }
      leaf groupAlarmObjectName2 {
        type leafref {
          path "/cpl-alm:groupAlarms/cpl-alm:groupAlarmEntry2/cpl-alm:groupAlarmObjectName2";
        }
        description
          "Automagically generated leafref leaf.";
      }
      leaf groupAlarmGroupNumber2 {
        type leafref {
          path "/cpl-alm:groupAlarms/cpl-alm:groupAlarmEntry2/cpl-alm:groupAlarmGroupNumber2";
        }
        description
          "Automagically generated leafref leaf.";
      }
    }
    container groupAlarmNotification2-groupAlarmId2 {
      leaf groupAlarmGroupNumber2 {
        type leafref {
          path "/cpl-alm:groupAlarms/cpl-alm:groupAlarmEntry2/cpl-alm:groupAlarmGroupNumber2";
        }
        description
          "Automagically generated leafref leaf.";
      }
      leaf groupAlarmInstanceNumber2 {
        type leafref {
          path "/cpl-alm:groupAlarms/cpl-alm:groupAlarmEntry2/cpl-alm:groupAlarmInstanceNumber2";
        }
        description
          "Automagically generated leafref leaf.";
      }
      leaf groupAlarmSecondInstance2 {
        type leafref {
          path "/cpl-alm:groupAlarms/cpl-alm:groupAlarmEntry2/cpl-alm:groupAlarmSecondInstance2";
        }
        description
          "Automagically generated leafref leaf.";
      }
      leaf groupAlarmObjectName2 {
        type leafref {
          path "/cpl-alm:groupAlarms/cpl-alm:groupAlarmEntry2/cpl-alm:groupAlarmObjectName2";
        }
        description
          "Automagically generated leafref leaf.";
      }
      leaf groupAlarmId2 {
        type leafref {
          path "/cpl-alm:groupAlarms/cpl-alm:groupAlarmEntry2/cpl-alm:groupAlarmId2";
        }
        description
          "Automagically generated leafref leaf.";
      }
    }
    container groupAlarmNotification2-groupAlarmState2 {
      leaf groupAlarmGroupNumber2 {
        type leafref {
          path "/cpl-alm:groupAlarms/cpl-alm:groupAlarmEntry2/cpl-alm:groupAlarmGroupNumber2";
        }
        description
          "Automagically generated leafref leaf.";
      }
      leaf groupAlarmId2 {
        type leafref {
          path "/cpl-alm:groupAlarms/cpl-alm:groupAlarmEntry2/cpl-alm:groupAlarmId2";
        }
        description
          "Automagically generated leafref leaf.";
      }
      leaf groupAlarmInstanceNumber2 {
        type leafref {
          path "/cpl-alm:groupAlarms/cpl-alm:groupAlarmEntry2/cpl-alm:groupAlarmInstanceNumber2";
        }
        description
          "Automagically generated leafref leaf.";
      }
      leaf groupAlarmSecondInstance2 {
        type leafref {
          path "/cpl-alm:groupAlarms/cpl-alm:groupAlarmEntry2/cpl-alm:groupAlarmSecondInstance2";
        }
        description
          "Automagically generated leafref leaf.";
      }
      leaf groupAlarmObjectName2 {
        type leafref {
          path "/cpl-alm:groupAlarms/cpl-alm:groupAlarmEntry2/cpl-alm:groupAlarmObjectName2";
        }
        description
          "Automagically generated leafref leaf.";
      }
      leaf groupAlarmState2 {
        type cpl-tc:AlarmState;
        description
          "raised or cleared";
        smi:oid "1.3.6.1.4.1.562.73.5.11.9.1.6";
      }
    }
    container groupAlarmNotification2-groupAlarmObjectName2 {
      leaf groupAlarmGroupNumber2 {
        type leafref {
          path "/cpl-alm:groupAlarms/cpl-alm:groupAlarmEntry2/cpl-alm:groupAlarmGroupNumber2";
        }
        description
          "Automagically generated leafref leaf.";
      }
      leaf groupAlarmId2 {
        type leafref {
          path "/cpl-alm:groupAlarms/cpl-alm:groupAlarmEntry2/cpl-alm:groupAlarmId2";
        }
        description
          "Automagically generated leafref leaf.";
      }
      leaf groupAlarmInstanceNumber2 {
        type leafref {
          path "/cpl-alm:groupAlarms/cpl-alm:groupAlarmEntry2/cpl-alm:groupAlarmInstanceNumber2";
        }
        description
          "Automagically generated leafref leaf.";
      }
      leaf groupAlarmSecondInstance2 {
        type leafref {
          path "/cpl-alm:groupAlarms/cpl-alm:groupAlarmEntry2/cpl-alm:groupAlarmSecondInstance2";
        }
        description
          "Automagically generated leafref leaf.";
      }
      leaf groupAlarmObjectName2 {
        type leafref {
          path "/cpl-alm:groupAlarms/cpl-alm:groupAlarmEntry2/cpl-alm:groupAlarmObjectName2";
        }
        description
          "Automagically generated leafref leaf.";
      }
    }
    container groupAlarmNotification2-groupAlarmInstanceNumber2 {
      leaf groupAlarmGroupNumber2 {
        type leafref {
          path "/cpl-alm:groupAlarms/cpl-alm:groupAlarmEntry2/cpl-alm:groupAlarmGroupNumber2";
        }
        description
          "Automagically generated leafref leaf.";
      }
      leaf groupAlarmId2 {
        type leafref {
          path "/cpl-alm:groupAlarms/cpl-alm:groupAlarmEntry2/cpl-alm:groupAlarmId2";
        }
        description
          "Automagically generated leafref leaf.";
      }
      leaf groupAlarmSecondInstance2 {
        type leafref {
          path "/cpl-alm:groupAlarms/cpl-alm:groupAlarmEntry2/cpl-alm:groupAlarmSecondInstance2";
        }
        description
          "Automagically generated leafref leaf.";
      }
      leaf groupAlarmObjectName2 {
        type leafref {
          path "/cpl-alm:groupAlarms/cpl-alm:groupAlarmEntry2/cpl-alm:groupAlarmObjectName2";
        }
        description
          "Automagically generated leafref leaf.";
      }
      leaf groupAlarmInstanceNumber2 {
        type leafref {
          path "/cpl-alm:groupAlarms/cpl-alm:groupAlarmEntry2/cpl-alm:groupAlarmInstanceNumber2";
        }
        description
          "Automagically generated leafref leaf.";
      }
    }
    container groupAlarmNotification2-groupAlarmSecondInstance2 {
      leaf groupAlarmGroupNumber2 {
        type leafref {
          path "/cpl-alm:groupAlarms/cpl-alm:groupAlarmEntry2/cpl-alm:groupAlarmGroupNumber2";
        }
        description
          "Automagically generated leafref leaf.";
      }
      leaf groupAlarmId2 {
        type leafref {
          path "/cpl-alm:groupAlarms/cpl-alm:groupAlarmEntry2/cpl-alm:groupAlarmId2";
        }
        description
          "Automagically generated leafref leaf.";
      }
      leaf groupAlarmInstanceNumber2 {
        type leafref {
          path "/cpl-alm:groupAlarms/cpl-alm:groupAlarmEntry2/cpl-alm:groupAlarmInstanceNumber2";
        }
        description
          "Automagically generated leafref leaf.";
      }
      leaf groupAlarmObjectName2 {
        type leafref {
          path "/cpl-alm:groupAlarms/cpl-alm:groupAlarmEntry2/cpl-alm:groupAlarmObjectName2";
        }
        description
          "Automagically generated leafref leaf.";
      }
      leaf groupAlarmSecondInstance2 {
        type leafref {
          path "/cpl-alm:groupAlarms/cpl-alm:groupAlarmEntry2/cpl-alm:groupAlarmSecondInstance2";
        }
        description
          "Automagically generated leafref leaf.";
      }
    }
    container groupAlarmNotification2-groupAlarmTimestamp2 {
      leaf groupAlarmGroupNumber2 {
        type leafref {
          path "/cpl-alm:groupAlarms/cpl-alm:groupAlarmEntry2/cpl-alm:groupAlarmGroupNumber2";
        }
        description
          "Automagically generated leafref leaf.";
      }
      leaf groupAlarmId2 {
        type leafref {
          path "/cpl-alm:groupAlarms/cpl-alm:groupAlarmEntry2/cpl-alm:groupAlarmId2";
        }
        description
          "Automagically generated leafref leaf.";
      }
      leaf groupAlarmInstanceNumber2 {
        type leafref {
          path "/cpl-alm:groupAlarms/cpl-alm:groupAlarmEntry2/cpl-alm:groupAlarmInstanceNumber2";
        }
        description
          "Automagically generated leafref leaf.";
      }
      leaf groupAlarmSecondInstance2 {
        type leafref {
          path "/cpl-alm:groupAlarms/cpl-alm:groupAlarmEntry2/cpl-alm:groupAlarmSecondInstance2";
        }
        description
          "Automagically generated leafref leaf.";
      }
      leaf groupAlarmObjectName2 {
        type leafref {
          path "/cpl-alm:groupAlarms/cpl-alm:groupAlarmEntry2/cpl-alm:groupAlarmObjectName2";
        }
        description
          "Automagically generated leafref leaf.";
      }
      leaf groupAlarmTimestamp2 {
        type smiv2:DateAndTime;
        description
          "The time that this alarm was raised or cleared.
           Note that the field lastAlarmDateAndTime
           must be updated every time an alarm is raised
           or cleared. If the alarm was raised before the
           Time of Day has been set, a default time of
           Jan 1/2004, 00:00:00 is used, and is not changed
           if the Time of Day is subsequently set.";
        smi:oid "1.3.6.1.4.1.562.73.5.11.9.1.7";
      }
    }
  }
}
