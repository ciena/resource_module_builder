module ciena-6500r-optical-control {
  yang-version 1.1;
  namespace "urn:ciena:params:xml:ns:yang:ciena-6500r-optical-control";
  prefix optical-control;

  import ciena-6500r-ports {
    prefix ports;
  }

  import ciena-6500r-types {
    prefix ciena-6500r-types;
  }

  import ciena-common-version {
    prefix version;
  }

  import ciena-pro-optical-types {
    prefix ciena-pro-optical-types;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's 6500r platform optical control facility model";

  revision 2021-03-05 {
    version:version "version" {
      version:string "1.0.0";
    }
    description
      "Initial revision";
  }

  grouping ciena-6500r-optical-control-mount {
    list optical-control {
      key "name";
      leaf name {
        type ciena-6500r-types:object-name;
        description
          "optical control facility name";
      }

      leaf parent-port {
        type leafref {
          path "/ports:port/ports:name";
        }
        mandatory true;
        description
          "optical control facility parent";
      }

      leaf type {
        type enumeration {
          enum "tx" {
            value 1;
            description
              "Type TX";
          }
        }
        description
          "Controller Type";
      }

      leaf control-mode {
        type enumeration {
          enum "downstream-power" {
            value 1;
            description
              "Optical power fluctuations are compensated for by a downstream controller rather than the local controller.";
          }
        }
        default "downstream-power";
        description
          "control mode";
      }

      uses ciena-6500r-types:admin-state;
    }
  }

  grouping ciena-6500r-optical-control-mount-actions;

  uses ciena-6500r-optical-control-mount;
}
