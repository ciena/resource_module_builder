module ciena-pro-coherent-device-platform-host-services {
  namespace "urn:ciena:ns:yang:ciena-pro-coherent-device-platform-host-services";
  prefix coherent-device-platform-host-services;

  import ciena-common-version {
    prefix version;
  }
  import ciena-pro-coherent-device-types {
    prefix coherent-device-types;
  }
  import ciena-pro-coherent-device-common-types {
    prefix coherent-device-common-types;
  }
  import ciena-pro-coherent-device-service-types {
    prefix coherent-device-service-types;
  }
  import ciena-pro-coherent-device-platform-host-types {
    prefix coherent-device-platform-host-types;
  }
  import ciena-pro-coherent-device-platform-host-ethernet-services-types {
    prefix coherent-device-platform-host-ethernet-services-types;
  }

  organization
    "Ciena Corporation";
  contact
    "Web URL: http://www.ciena.com/
     Postal:  7035 Ridge Road
            Hanover, Maryland 21076
            U.S.A.
     Phone:   +1 800-921-1144
     Fax:     +1 410-694-5750";
  description
    "Coherent-device platform host services model.";

  revision 2023-11-01 {
    description
      "Initial version";
    version:version "version" {
      version:string "1.0.0";
    }
    reference
      "1.0.0";
  }

  typedef host-service-mapping-enum {
    type enumeration {
      enum none {
        description
          "";
      }
      enum CBR {
        description
          "";
      }
      enum PKT {
        description
          "";
      }
    }
    description
      "";
  }

  typedef host-service-interface-format-enum {
    type enumeration {
      enum OTL4.4 {
        description
          "";
      }
      enum OTL4.2 {
        description
          "";
      }
      enum CAUI-4 {
        description
          "";
      }
      enum 100GAUI-2 {
        description
          "";
      }
      enum 200GAUI-4 {
        description
          "";
      }
      enum 400GAUI-8 {
        description
          "";
      }
      enum FOIC1.4 {
        description
          "";
      }
      enum FOIC1.2 {
        description
          "";
      }
    }
    description
      "";
  }

  typedef host-service-interface-fec-type-enum {
    type enumeration {
      enum off {
        description
          "";
      }
      enum KR4 {
        description
          "";
      }
      enum KP4 {
        description
          "";
      }
      enum GFEC {
        description
          "";
      }
    }
    description
      "";
  }

  typedef host-service-loopback-mode-enum {
    type enumeration {
      enum disabled {
        description
          "Loopback is not configured and not active.";
      }
      enum rx-to-tx {
        description
          "The received signal is being looped back to the transmitter.
           Also known as a facility loopback.";
      }
      enum tx-to-rx {
        description
          "The signal to be transmitted is being looped back to the internal source.
           Also known as a terminal loopback.";
      }
    }
    description
      "Ciena WaveLogic device loopback types.";
  }

  typedef host-service-ethernet-lsh-timeout-enum {
    type enumeration {
      enum 0 {
        description
          "";
      }
      enum 10 {
        description
          "";
      }
      enum 50 {
        description
          "";
      }
      enum 100 {
        description
          "";
      }
      enum 200 {
        description
          "";
      }
      enum 300 {
        description
          "";
      }
      enum 500 {
        description
          "";
      }
      enum 1000 {
        description
          "";
      }
      enum idle {
        description
          "";
      }
    }
    description
      "";
  }

  typedef host-service-ethernet-fault-inject-type-enum {
    type enumeration {
      enum none {
        description
          "";
      }
      enum lf {
        description
          "";
      }
      enum rf {
        description
          "";
      }
      enum idle-test-pattern {
        description
          "";
      }
    }
    description
      "";
  }

  typedef host-service-ethernet-client-network-odu-conditioning-enum {
    type enumeration {
      enum csf-lf {
        description
          "";
      }
      enum idle {
        description
          "";
      }
      enum ais {
        description
          "";
      }
    }
    description
      "";
  }

  grouping service-group-common-group {
    leaf service-id {
      type coherent-device-service-types:service-id-type;
      description
        "";
    }
    leaf mode {
      type coherent-device-service-types:service-mode-enum;
      description
        "A read-only leaf that indicates the actual mode for the WaveLogic device client/host interface.
         Configuration of this leaf is rejected. Its value is derived by the system.";
    }
    leaf mapping {
      type host-service-mapping-enum;
      default "none";
      description
        "";
    }
    leaf interface-format {
      type host-service-interface-format-enum;
      description
        "";
    }
    leaf interface-fec-type {
      type host-service-interface-fec-type-enum;
      description
        "";
    }
    leaf auto-condition-client-on-network-fault {
      type boolean;
      default "true";
      description
        "";
    }
    leaf type {
      type coherent-device-service-types:service-interface-type-enum;
      description
        "";
    }
    leaf rate {
      type identityref {
        base coherent-device-platform-host-types:data-rate-identity;
      }
      description
        "";
    }
    leaf admin-state {
      type coherent-device-types:admin-state-enum;
      default "enabled";
      description
        "";
    }
    leaf label {
      type string {
        length "128";
      }
      description
        "";
    }
    leaf loopback {
      type host-service-loopback-mode-enum;
      default "disabled";
      description
        "On the device host-interface an rx-to-tx loopback is toward the media-interface (fiber)
         and a tx-to-rx loopback is toward the system.

         On the device host-interface this attribute is read-only and managed internally by
         the platform.";
    }
    leaf connected {
      type boolean;
      description
        "Indication of whether this host interface service is connected to the media-side of the device.
         By default a service is connected when it is created. It can be disconnected by setting connected
         to false and this triggers host and media facing conditioning for this service.";
    }
    leaf connection-peer {
      type instance-identifier;
      description
        "When the transmission-mode is -E, the connection mode is always automatic and the system will automatically
         stage the connection-peer to the correct external service object based on the service-id.";
    }
    leaf parent-resource {
      type coherent-device-common-types:string128;
      description
        "";
    }
    description
      "";
  }

  grouping service-group-diagnostic-group {
    container diagnostics {
      leaf rx-to-tx-loopback {
        type boolean;
        default "false";
        description
          "An rx-to-tx loopback is enabled on the media-interface of the device.
           At this location the signal received from the fiber on the media-interface is returned
           toward the fiber.";
      }
      leaf tx-to-rx-loopback {
        type boolean;
        default "false";
        description
          "A tx-to-rx loopback is enabled on the media-interface of the device.
           At this location the signal received from the system on the host-interface is returned
           toward the system.";
      }
      description
        "";
    }
    description
      "";
  }

  grouping service-group-config-group {
    list service {
      key "service-id";
      uses service-group-common-group;
      uses coherent-device-platform-host-ethernet-services-types:host-ethernet-service-prov-config-group;
      description
        "";
    }
    description
      "";
  }

  grouping service-group-state-group {
    list service {
      key "service-id";
      uses service-group-common-group;
      leaf operational-state {
        type identityref {
          base coherent-device-types:operational-state-identity;
        }
        description
          "";
      }
      uses coherent-device-platform-host-ethernet-services-types:host-ethernet-service-prov-state-group;
      uses service-group-diagnostic-group;
      description
        "";
    }
    description
      "";
  }

  container host-service-groups {
    list service-group {
      key "supporting-resource";
      leaf supporting-resource {
        type instance-identifier;
        description
          "";
      }
      container config {
        uses service-group-config-group;
        description
          "";
      }
      container state {
        uses service-group-state-group;
        config false;
        description
          "";
      }
      description
        "";
    }
    description
      "";
  }
}
