module ciena-pro-perminfo {
  namespace "urn:ciena:params:xml:ns:yang:ciena-pro-perminfo";
  prefix perminfo;

  import ciena-pro-aaa-common {
    prefix common;
  }

  organization
    "Ciena";
  contact
    "";
  description
    "permission information definitions.";

  revision 2019-04-15 {
    description
      "";
    reference
      "";
  }

  grouping perminfo-grouping {
    list perminfo {
      key "name";
      leaf name {
        type common:string-maxl-64;
        description
          "The name that identifies permission holder.";
      }
      leaf level {
        type common:access-level;
        description
          "The access level that the name has.";
      }
      leaf interface {
        type common:access-interface;
        description
          "The interface that the name comes in.";
      }
    }
  }

  container perminfos {
    uses perminfo-grouping;
  }
}
