module ciena-6500r-oms-topo-svc-private {
  namespace "urn:ciena:params:xml:ns:yang:ciena-6500r-oms-topo-svc-private";
  prefix oms-topo-svc;

  import ciena-common-version {
    prefix version;
  }
  import ciena-common-yang {
    prefix ciena-common-yang;
  }
  import ciena-6500r-types {
    prefix ciena-6500r-types;
  }
  import ietf-inet-types {
    prefix inet;
  }
  import ciena-ddy-msg {
    prefix ddy-msg;
  }
  import ciena-ddm-zmq {
    prefix ddm-zmq;
  }
  import ciena-6500r-nodes {
    prefix ciena-6500r-nodes;
  }
  import ciena-6500r-fg {
    prefix fg-base-defs;
  }

  organization
    "Ciena Corporation";
  contact
    "Web URL: http://www.ciena.com/
     Postal:  7035 Ridge Road
              Hanover, Maryland 21076
              U.S.A.
     Phone:   +1 800-921-1144
     Fax:     +1 410-694-5750";
  description
    "This modules describes the private data for OMS Topo Service";

  revision 2023-05-10 {
    description
      "Add dir-svc lookup table used by OMS mounting block applications.";
    version:version "version" {
      version:string "2.5.0";
    }
    reference
      "RLS 3.1";
  }
  revision 2023-02-27 {
    description
      "Add node-list parameter to oms-topo-svc-debug rpc";
    version:version "version" {
      version:string "2.4.0";
    }
    reference
      "RLS 3.1";
  }
  revision 2022-05-25 {
    description
      "Add IPv6 address in line-in and line-out neighbour data";
    version:version "version" {
      version:string "2.3.0";
    }
    reference
      "RLS 3.0";
  }
  revision 2022-02-25 {
    description
      "Add flag for remote subscription audit : RLS 2.5";
    version:version "version" {
      version:string "2.2.0";
    }
    reference
      "RLS 2.5.0";
  }
  revision 2022-02-09 {
    description
      "Add node name change RPC";
    version:version "version" {
      version:string "2.1.0";
    }
    reference
      "RLS 3.0.0";
  }
  revision 2022-01-10 {
    description
      "Add network neighbour";
    version:version "version" {
      version:string "2.0.0";
    }
    reference
      "RLS 3.0.0";
  }
  revision 2021-12-17 {
    description
      "Add pfg-type to spans data";
    version:version "version" {
      version:string "1.9.0";
    }
    reference
      "RLS 3.0.0";
  }
  revision 2021-09-09 {
    description
      "Add node-type: RLS 2.5";
    version:version "version" {
      version:string "1.8.0";
    }
  }
  revision 2021-07-29 {
    description
      "Add instance-id-1 and instance-id-2 to the oms-topo-svc-debug rpc: RLS 2.5";
    version:version "version" {
      version:string "1.7.0";
    }
  }
  revision 2021-06-09 {
    description
      "Add new parameter, mounting block audit, in debug rpc: RLS 2.4";
    version:version "version" {
      version:string "1.6.0";
    }
  }
  revision 2021-01-05 {
    description
      "Add local node information: RLS 2.3";
    version:version "version" {
      version:string "1.5.0";
    }
  }
  revision 2020-12-21 {
    description
      "Add software-version: RLS 2.3";
    version:version "version" {
      version:string "1.4.0";
    }
  }
  revision 2020-10-30 {
    description
      "Add On-since value RLS 2.2";
    version:version "version" {
      version:string "1.3.0";
    }
  }
  revision 2020-09-25 {
    description
      "-Import ietf-inet-types for the purposes of IP addresses RLS 2.1";
    version:version "version" {
      version:string "1.2.0";
    }
  }
  revision 2020-06-04 {
    description
      "RLS Release 2.0/2.0.60";
    version:version "version" {
      version:string "1.1.0";
    }
  }

  grouping neighbour-data {
    leaf remote-node-name {
      type string;
      description
        "Remote node name";
    }
    leaf exp-remote-pfg-name {
      type string;
      description
        "Expected remote PFG name";
    }
    leaf remote-pfg-name {
      type string;
      description
        "Remote PFG name";
    }
    leaf remote-osc {
      type string;
      description
        "Remote OSC port";
    }
    leaf remote-interface {
      type string;
      description
        "Remote Interface";
    }
    leaf remote-line-port {
      type string;
      description
        "Remote line port";
    }
    leaf remote-node-ip-address {
      type inet:ip-address;
      description
        "Remote node IP address";
    }
    leaf remote-node-ipv6-address {
      type inet:ipv6-address;
      description
        "Remote node IPv6 address";
    }
  }

  container system-info {
    description
      "Information about local node, for example, member name, ip address, software version etc.";
    leaf node-name {
      type string;
      description
        "Node name";
    }
    leaf node-ip-address {
      type inet:ip-address;
      description
        "Node IP address";
    }
    leaf node-ipv6-address {
      type inet:ipv6-address;
      description
        "Node IPv6 address";
    }
    leaf software-version {
      type string;
      description
        "Actual software release version that is currently running and is expected to match active-version after an upgrade is completed.
         Format: RLS-xx.yy.zz.bbbb";
    }
  }
  list nodes-private {
    key "node-name";
    leaf node-name {
      type string;
      description
        "Node name";
    }
    leaf node-ip-address {
      type inet:ip-address;
      description
        "Node IP address";
    }
    leaf node-ipv6-address {
      type inet:ipv6-address;
      description
        "Node IPv6 address";
    }
    leaf is-remote {
      type boolean;
      default "false";
      description
        "Indicates if this is a remote node";
    }
    leaf is-up {
      type boolean;
      default "true";
      description
        "Indicates if the remote node is up";
    }
    leaf cache-updated {
      type boolean;
      default "false";
      description
        "Indicates if the mounted data cache was successfully updated and published to other services";
    }
    leaf remote-oms-topo-svc-domain {
      type string;
      description
        "Domain of the OMS Topo Service running on a remote site";
    }
    leaf remote-oms-topo-svc-service {
      type string;
      description
        "Service of the OMS Topo Service running on a remote site";
    }
    leaf local-id {
      type string;
      description
        "An unique identifier to logically group a set of micro-services";
    }
    leaf on-since {
      type uint64;
      description
        "Time when this domain was last started, in nanoseconds.";
    }
    leaf software-version {
      type string;
      description
        "Actual software release version that is currently running and is expected to match active-version after an upgrade is completed.
         Format: RLS-xx.yy.zz.bbbb";
    }
    uses ciena-6500r-nodes:node-type;
    list spans {
      key "pfg-name";
      leaf pfg-name {
        type ciena-6500r-types:object-name;
        description
          "The name of the PFG.";
      }
      leaf local-line-out-osc {
        type instance-identifier;
        description
          "Local line out OSC port";
      }
      leaf local-line-out-port {
        type string;
        description
          "Local line out port";
      }
      leaf local-line-in-osc {
        type instance-identifier;
        description
          "Local line in OSC port";
      }
      leaf local-line-in-port {
        type string;
        description
          "Local line in port";
      }
      container line-in-neighbour {
        uses neighbour-data;
      }
      container line-out-neighbour {
        uses neighbour-data;
      }
      leaf pfg-type {
        type identityref {
          base fg-base-defs:TYPE;
        }
      }
    }
    container site {
      list site-neighbours {
        key "remote-node-name";
        leaf remote-node-name {
          type string;
          description
            "Remote node name";
        }
        leaf remote-ip-address {
          type inet:ip-address;
          description
            "Remote node IP address";
        }
        leaf remote-ipv6-address {
          type inet:ipv6-address;
          description
            "Remote node IPv6 address";
        }
        list local-interface {
          key "local-interface-name";
          leaf local-interface-name {
            type instance-identifier;
            description
              "Local interface where the neighbour was discovered, or configured";
          }
        }
        list remote-interface {
          key "remote-interface-name";
          leaf remote-interface-name {
            type string;
            description
              "Interface on the neighbouring node which is adjacent to the local interface above";
          }
        }
      }
    }
    container network-neighbours {
      list network-neighbour {
        key "remote-node-name";
        leaf remote-node-name {
          type string;
          description
            "Remote node name";
        }
        leaf remote-ip-address {
          type inet:ip-address;
          description
            "Remote node IP address";
        }
        leaf remote-ipv6-address {
          type inet:ipv6-address;
          description
            "Remote node IPv6 address";
        }
        list local-interface {
          key "local-interface-name";
          leaf local-interface-name {
            type instance-identifier;
            description
              "Local interface where the neighbour was configured";
          }
        }
      }
    }
    config false;
  }
  list dirsvc-lookup {
    description
      "A lookup table for dir-svc with a list of resources, services, ip, pub IP port mappings.
       It will be looked up based on software version of the system.
       This will be used by the OMS mounting block (MB) applications for the purpose of getting direct remote
       get data, or peforming remote direct RPC/actions operations";
    key "sw-version";
    leaf sw-version {
      type string;
      description
        "The software version of the system";
    }
    list domains {
      key "domain";
      uses ddy-msg:domain-grouping;
    }
  }

  augment "/oms-topo-svc:dirsvc-lookup/domains/protocols" {
    uses ddm-zmq:zmq-options;
  }

  rpc oms-topo-svc-debug {
    input {
      leaf ip-address {
        type inet:ip-address;
        description
          "The IP address of the neighbour";
      }
      leaf ipv6-address {
        type inet:ipv6-address;
        description
          "Remote IPv6 address";
      }
      leaf remote-subscription-audit {
        type boolean;
        description
          "This is a special flag added for supporting auditing remote subscription.
           This is used to determine if remote subscription entry from the application
           is synced locally at OMS by checking providers call. This helps in determining
           the correct service for sending manual provider sync RPC to re-initiate provider
           sync if provider call is not found synced locally at OMS.";
      }
      leaf force-audit {
        type boolean;
        description
          "Force audit of all sections and neighbours";
      }
      leaf disable-republish {
        type boolean;
        description
          "Disable re-publish of remote notifications";
      }
      leaf dump-cache {
        type boolean;
        description
          "Dump the nodes cache";
      }
      leaf dump-version {
        type boolean;
        description
          "Dump the version";
      }
      leaf audit-period {
        type uint16;
        description
          "How often the audit should run, set to 0 to disable the audit";
        units "s";
      }
      leaf heartbeat-interval {
        type uint16;
        description
          "set heartbeat interval to get the data from remote nodes, set to 0 to fall back to default value of 5 sec";
        units "s";
      }
      container mounting-block-audit {
        leaf service-name {
          type string;
          description
            "Name of mounting block service which requires audit.";
        }
      }
      container node-name-change {
        leaf old-node-name {
          description
            "Name of old node.";
          mandatory true;
          type string;
        }
        leaf new-node-name {
          description
            "Name of new node.";
          mandatory true;
          type string;
        }
        uses ciena-6500r-nodes:node-type;
      }
      leaf instance-id-1 {
        type instance-identifier;
        description
          "Instance-id to be used to test oms-topo-svc APIs";
      }
      leaf instance-id-2 {
        type instance-identifier;
        description
          "A second instance-id, also to be used to test oms-topo-svc APIs";
      }
      list node-list {
        description
          "A list of nodes that the debug command will be run against";
        key "node-name";
        leaf node-name {
          type string;
        }
      }
    }
    output {
      list return-code-list {
        uses ciena-common-yang:return-code;
      }
      anyxml cache;
      anyxml data;
      leaf version {
        type string;
        description
          "Version info";
      }
    }
  }
}
