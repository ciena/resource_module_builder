module ietf-snmp {
  namespace "urn:ietf:params:xml:ns:yang:ietf-snmp";
  prefix snmp;

  include ietf-snmp-common {
    revision-date 2014-12-10;
  }

  include ietf-snmp-engine {
    revision-date 2014-12-10;
  }

  include ietf-snmp-target {
    revision-date 2014-12-10;
  }

  include ietf-snmp-notification {
    revision-date 2014-12-10;
  }

  include ietf-snmp-proxy {
    revision-date 2014-12-10;
  }

  include ietf-snmp-community {
    revision-date 2014-12-10;
  }

  include ietf-snmp-usm {
    revision-date 2014-12-10;
  }

  include ietf-snmp-tsm {
    revision-date 2014-12-10;
  }

  include ietf-snmp-vacm {
    revision-date 2014-12-10;
  }

  include ietf-snmp-tls {
    revision-date 2014-12-10;
  }

  include ietf-snmp-ssh {
    revision-date 2014-12-10;
  }

  organization
    "IETF NETMOD (NETCONF Data Modeling Language) Working Group";
  contact
    "WG Web:   <http://tools.ietf.org/wg/netmod/>
     WG List:  <mailto:netmod@ietf.org>

     WG Chair: Thomas Nadeau
               <mailto:tnadeau@lucidvision.com>

     WG Chair: Juergen Schoenwaelder
               <mailto:j.schoenwaelder@jacobs-university.de>

     Editor:   Martin Bjorklund
               <mailto:mbj@tail-f.com>

     Editor:   Juergen Schoenwaelder
               <mailto:j.schoenwaelder@jacobs-university.de>";
  description
    "This module contains a collection of YANG definitions for
     configuring SNMP engines.

     Copyright (c) 2014 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC 7407; see
     the RFC itself for full legal notices.";

  revision 2014-12-10 {
    description
      "Initial revision.";
    reference
      "RFC 7407: A YANG Data Model for SNMP Configuration";
  }
}
