module ciena-wavelogic-agent-stats-collector-options {
  namespace "urn:ciena:params:xml:ns:yang:ciena-wavelogic-agent-stats-collector-options";
  prefix wavelogic-agent-stats-collector-options;

  import ciena-common-version {
    prefix ciena-common-version;
  }

  organization
    "Ciena Corporation";
  contact
    "Web URL: http://www.ciena.com";
  description
    "This module defines the object model used to specify certain options for the Wavelogic Agent Stats Collector.";

  revision 2024-04-25 {
    description
      "Initial revision";
    ciena-common-version:string "1.0.0";
    reference
      "1.0.0";
  }

  container options {
    description
      "Top-level container for WLRA stats collector options.";
    leaf bin-interval {
      description
        "Option to configure the desired interval for the timed binning of statistics. The value must be specified
         in seconds, in multiples of 10.";
      type uint16;
      units "seconds";
    }
  }
}
