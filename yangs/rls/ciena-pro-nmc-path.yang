module ciena-pro-nmc-path {
  namespace "urn:ciena:params:xml:ns:yang:ciena-pro-nmc-path";
  prefix pro-nmc-path;

  import ciena-common-version {
    prefix ciena-common-version;
  }
  import ciena-pro-optical-types {
    prefix ciena-pro-optical-types;
  }

  organization
    "Ciena Corporation";
  contact
    "Web URL: http://www.ciena.com/
     Postal:  7035 Ridge Road
             Hanover, Maryland 21076
             U.S.A.
     Phone:   +1 800-921-1144
     Fax:     +1 410-694-5750";
  description
    "This module implements a construct to represent a stitched
     path of nmc elements.";

  revision 2021-03-24 {
    description
      "Initial version";
    ciena-common-version:version "version" {
      ciena-common-version:string "1.0.0";
    }
  }

  grouping nmc-path {
    leaf name {
      type string;
      description
        "This is a path that is constituted by nmc elements";
    }
    leaf owner {
      type string;
      description
        "This identifies the provisioning ownership";
    }
    leaf from {
      type instance-identifier;
      mandatory true;
      description
        "From port identifier";
    }
    leaf to {
      type instance-identifier;
      mandatory true;
      description
        "To port identifier";
    }
    leaf center-freq {
      type ciena-pro-optical-types:frequency;
      mandatory true;
      description
        "Center frequency of each network media channel element";
    }
    leaf spectral-width {
      type ciena-pro-optical-types:frequency;
      mandatory true;
      description
        "Spectral width of each network media channel element";
    }
    leaf user-label {
      type string;
      description
        "User provisioned label";
    }
    leaf nmc-network-id {
      type string;
      description
        "Network unique identifier of the end-to-end network media channel this path relates to";
    }
    leaf minimal {
      type boolean;
      default "false";
      description
        "indicates if minimal(only on WSS switch links) nmc provisioning is used ";
    }
    list path {
      key "element";
      leaf element {
        type instance-identifier;
        description
          "The identifer of the path element";
      }
    }
  }
}
