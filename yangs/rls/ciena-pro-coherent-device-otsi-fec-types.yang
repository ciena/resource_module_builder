module ciena-pro-coherent-device-otsi-fec-types {
  namespace "urn:ciena:ns:yang:coherent-device-otsi-fec-types";
  prefix coherent-device-otsi-fec-types;

  import ciena-common-version {
    prefix version;
  }
  import ciena-pro-coherent-device-types {
    prefix coherent-device-types;
  }
  import ciena-pro-wavelogic-device-extension-types {
    prefix wavelogic-device-extension-types;
  }

  organization
    "Ciena Corporation";
  contact
    "Web URL: http://www.ciena.com/
     Postal:  7035 Ridge Road
              Hanover, Maryland 21076
              U.S.A.
     Phone:   +1 800-921-1144
     Fax:     +1 410-694-5750";
  description
    "OTSI FEC definitions for coherent devices.";

  revision 2024-01-01 {
    description
      "Initial version.";
    version:version "version" {
      version:string "1.0.0";
    }
    reference
      "1.0.0";
  }

  identity coherent-device-fec-format-identity {
    description
      "FEC format identity.";
  }

  identity off {
    base coherent-device-fec-format-identity;
    description
      "FEC is disabled.";
  }

  identity kp4 {
    base coherent-device-fec-format-identity;
    description
      "FEC format value KP4 [IEEE802.3].";
  }

  identity kr4 {
    base coherent-device-fec-format-identity;
    description
      "FEC format value KR4 [IEEE802.3].";
  }

  identity gfec {
    base coherent-device-fec-format-identity;
    description
      "FEC format value GFEC.
       Also known as RS-8 FEC. [G.709 Reed-Solomon FEC].";
  }

  identity cfec {
    base coherent-device-fec-format-identity;
    description
      "FEC format for 400ZR";
  }

  identity ofec {
    base coherent-device-fec-format-identity;
    description
      "FEC format for 400ZR+ and OTN-STND transmission mode groups";
  }

  identity sfec {
    base coherent-device-fec-format-identity;
    description
      "FEC format for Ciena PKT-MAX and OTN-MAX transmission mode groups";
  }

  typedef coherent-device-fec-admin-state-enum {
    type enumeration {
      enum enabled {
        description
          "FEC is administratively enabled.";
      }
      enum disabled {
        description
          "FEC is administratively disabled.";
      }
      enum automatic {
        description
          "FEC is administatively configured to allow the system to automatically
           enable or disable FEC as required for the device or configuration of the device present.";
      }
    }
    description
      "";
  }

  grouping coherent-device-fec-admin-and-format-config-group {
    description
      "";
    leaf admin-state {
      type coherent-device-fec-admin-state-enum;
      default "automatic";
      description
        "Forward Error Correction (FEC) administrative state.";
    }
    leaf format {
      type identityref {
        base coherent-device-fec-format-identity;
      }
      description
        "Forward Error Correction (FEC) format.";
    }
  }

  grouping coherent-device-fec-admin-and-format-state-group {
    description
      "";
    leaf admin-state {
      type coherent-device-fec-admin-state-enum;
      default "automatic";
      description
        "Forward Error Correction (FEC) administrative state.";
    }
    leaf operational-state {
      type identityref {
        base coherent-device-types:operational-state-identity;
      }
      config false;
      description
        "";
    }
    leaf format {
      type identityref {
        base coherent-device-fec-format-identity;
      }
      description
        "Forward Error Correction (FEC) format.";
    }
  }

  grouping coherent-device-otsi-fec-config-group {
    container fec {
      uses coherent-device-fec-admin-and-format-config-group;
      uses wavelogic-device-extension-types:wavelogic-device-prefec-sd-sf-threshold-config-group;
      description
        "";
    }
    description
      "";
  }

  grouping coherent-device-otsi-fec-state-group {
    container fec {
      uses coherent-device-fec-admin-and-format-state-group;
      uses wavelogic-device-extension-types:wavelogic-device-prefec-sd-sf-threshold-state-group;
      description
        "";
    }
    description
      "";
  }
}
