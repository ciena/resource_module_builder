module CIENA-6500R-INVENTORY-NMCMONS-MIB {
  namespace "urn:ietf:params:xml:ns:yang:smiv2:CIENA-6500R-INVENTORY-NMCMONS-MIB";
  prefix ciena-6500r-inventory;

  import CIENA-6500R-INVENTORY-MIB {
    prefix ciena-6500r;
  }
  import CIENA-6500R-TYPES-MIB {
    prefix ciena-6500r-types;
  }
  import CIENA-PRO-TYPES-MIB {
    prefix ciena-pro;
  }
  import SNMPv2-TC {
    prefix smiv2;
  }

  organization
    "Ciena Corporation";
  contact
    "Web URL: http://www.ciena.com/
     Postal:  7035 Ridge Road
     Hanover, Maryland 21076
     U.S.A.
     Phone:   +1 800-921-1144
     Fax:    Inventory +1 410-694-5750";
  description
    "This modules describes Ciena's photonic nmcmon object.";

  revision 2022-03-25 {
    description
      "Added new parameter rlsInventoryNmcmonsSignalType.";
  }
  revision 2021-11-15 {
    description
      "Initial revision.";
  }

  container cienaRlsInventoryNmcmonsMIB {
    list rlsInventoryNmcmonsEntry {
      config false;
      key "rlsInventoryNmcmonsSlotName rlsInventoryNmcmonsName
           rlsInventoryNmcmonsCenterFreq";
      description
        "";
      leaf rlsInventoryNmcmonsSlotName {
        type ciena-pro:DisplayString32;
        config false;
        description
          "The name of the slot.";
      }
      leaf rlsInventoryNmcmonsName {
        type ciena-pro:DisplayString128;
        config false;
        description
          "Nmcmon name.";
      }
      leaf rlsInventoryNmcmonsParentPort {
        type ciena-pro:DisplayString128;
        config false;
        description
          "Parent Port of Nmcmon";
      }
      leaf rlsInventoryNmcmonsSignalType {
        type enumeration {
          enum osc {
            value 0;
          }
          enum tps {
            value 1;
          }
          enum cv {
            value 2;
          }
          enum otdr {
            value 3;
          }
          enum tg {
            value 4;
          }
          enum totalpower {
            value 5;
          }
          enum c-band {
            value 6;
          }
          enum l-band {
            value 7;
          }
          enum c-l-band {
            value 8;
          }
          enum nmcmon {
            value 9;
          }
          enum sdmon {
            value 10;
          }
        }
        config false;
        description
          "Signal Type of the pwrmon.";
      }
      leaf rlsInventoryNmcmonsCenterFreq {
        type uint32;
        config false;
        description
          "Center Frequency of Nmcmon";
      }
      leaf rlsInventoryNmcmonsSpectralWidth {
        type ciena-pro:DisplayString128;
        config false;
        description
          "Spectral Width of Nmcmon";
      }
      leaf rlsInventoryNmcmonsTxPower {
        type ciena-pro:DisplayString32;
        config false;
        description
          "Expected power of Nmcmon";
      }
    }
  }
}
