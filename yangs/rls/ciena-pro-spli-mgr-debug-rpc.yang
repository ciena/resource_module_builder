module ciena-pro-spli-mgr-debug-rpc {
  namespace "urn:ciena:params:xml:ns:yang:ciena-pro-spli-mgr-debug-rpc";
  prefix rpc;

  organization
    "Ciena Corporation";
  contact
    "Web URL: http://www.ciena.com/
     Postal:  7035 Ridge Road
             Hanover, Maryland 21076
             U.S.A.
     Phone:   +1 800-921-1144
     Fax:     +1 410-694-5750";
  description
    "This Yang is for debugging purpose only. Implemented SPLI & SCM debug Commands";

  revision 2020-12-07 {
    description
      "Initial revision";
  }
  revision 2020-12-08 {
    description
      "Added Slot Port support in Yang";
  }

  rpc scm-debug {
    description
      "SCM Debug Interface";
    input {
      leaf command {
        mandatory true;
        description
          "command to execute, Pass help for info";
        type string {
          length "0..100";
        }
      }
      leaf logspath {
        description
          "Logs Dump Path";
        type string {
          length "0..100";
        }
      }
      leaf slot {
        description
          "Slot of the CMD";
        type uint8 {
          range "0..255";
        }
      }
      leaf port {
        description
          "Port of the CMD";
        type uint8 {
          range "0..255";
        }
      }
    }
    output {
      leaf result {
        description
          "output result message";
        type string {
          length "0..100";
        }
      }
      leaf response {
        description
          "outout response message";
        type string {
          length "0..200";
        }
      }
    }
  }
}
