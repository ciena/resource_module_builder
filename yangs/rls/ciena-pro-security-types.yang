module ciena-pro-security-types {
  namespace "urn:ciena:params:xml:ns:yang:ciena-pro-security-types";
  prefix security-types;

  import ciena-common-version {
    prefix version;
  }
  import ciena-common-yang {
    prefix yang;
  }

  organization
    "Ciena Corporation";
  contact
    "Web URL: http://www.ciena.com/
     Postal:  7035 Ridge Road
             Hanover, Maryland 21076
             U.S.A.
     Phone:   +1 800-921-1144
     Fax:     +1 410-694-5750";
  description
    "This module defines common data types of security and command log
     functionality.";

  revision 2022-03-24 {
    description
      "Initial version of common data types.";
    version:version "version" {
      version:string "1.0.0";
    }
  }

  typedef user-name {
    type string {
      length "2..64";
    }
    description
      "User name string that has a range of 2 to 64 characters.
       Valid character includes alphanumeric and '-', '_', '.'";
  }

  typedef access-level {
    type enumeration {
      enum limited {
        description
          "User has limited (mostly read-only) privileges. Limited user shall
           - be a read only user with access to retrieve most of the system configurations.
           - NOT be able to retrieve most of  security configurations, except their own user and user session information.
           - be able to change their own password";
      }
      enum admin {
        description
          "User has administrative privileges. Admin user shall
           - be able to perform all the capabilities of limited user
           - be able to provision most of the system configurations
           - NOT be able to retrieve and provision most of  security configurations,
            except retrieve their own user and user session information
           - be able to change their own password";
      }
      enum super {
        description
          "User has superuser privileges. Super user shall
           - be able to perform all the capabilities of admin and limited user
           - be able to perform all retrieval and provisioning of security related configurations
             (Configuring  and retrieving users, user sessions, TACACS+, banners, ssh, intrusion ...)
           - be able to execute RPC ";
      }
      enum diag {
        description
          "User has debug shell access. Diag user shall
           - be able to perform all the capabilities of super user
           - be able to execute the CLI command diag-shell";
      }
      enum initial {
        description
          "User has very limited access. Initial user shall
           - only be able to change their own password
           - Note: can not create a user with initial access level, only used for default user.";
      }
    }
  }
}
