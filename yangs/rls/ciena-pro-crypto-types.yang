module ciena-pro-crypto-types {
  namespace "urn:ciena:params:xml:ns:yang:ciena-pro-crypto-types";
  prefix ciena-pro-crypto-types;

  import ciena-common-version {
    prefix ciena-common-version;
  }

  organization
    "Ciena Corporation";
  contact
    "Web URL: http://www.ciena.com/
     Postal:  7035 Ridge Road
             Hanover, Maryland 21076
             U.S.A.
     Phone:   +1 800-921-1144
     Fax:     +1 410-694-5750";
  description
    "This module defines common YANG types for cryptographic
     applications";

  revision 2020-10-22 {
    ciena-common-version:string "0.1.0";
    description
      "Make model platform independent";
  }
  revision 2018-10-23 {
    description
      "Initial version, based on ietf-crypto-types";
  }

  typedef key-algorithm {
    type enumeration {
      enum "dsa512" {
        description
          "The DSA algorithm using a 512-bit key.";
      }
      enum "dsa1024" {
        description
          "The DSA algorithm using a 1024-bit key.";
      }
      enum "dsa2048" {
        description
          "The DSA algorithm using a 2048-bit key.";
      }
      enum "dsa3072" {
        description
          "The DSA algorithm using a 3072-bit key.";
      }
      enum "rsa1024" {
        description
          "The RSA algorithm using a 1024-bit key.";
        reference
          "RFC 8017:PKCS #1: RSA Cryptography Specifications Version 2.2.";
      }
      enum "rsa2048" {
        description
          "The RSA algorithm using a 2048-bit key.";
        reference
          "RFC 8017:PKCS #1: RSA Cryptography Specifications Version 2.2.";
      }
      enum "rsa3072" {
        description
          "The RSA algorithm using a 3072-bit key.";
        reference
          "RFC 8017:PKCS #1: RSA Cryptography Specifications Version 2.2.";
      }
      enum "rsa4096" {
        description
          "The RSA algorithm using a 4096-bit key.";
        reference
          "RFC 8017:PKCS #1: RSA Cryptography Specifications Version 2.2.";
      }
      enum "secp192r1" {
        description
          "The secp192r1 algorithm.";
        reference
          "RFC 5480: Elliptic Curve Cryptography Subject Public Key Information.";
      }
      enum "secp256r1" {
        description
          "The secp256r1 algorithm.";
        reference
          "RFC 5480: Elliptic Curve Cryptography Subject Public Key Information.";
      }
      enum "secp384r1" {
        description
          "The secp384r1 algorithm.";
        reference
          "RFC 5480: Elliptic Curve Cryptography Subject Public Key Information.";
      }
      enum "secp521r1" {
        description
          "The secp521r1 algorithm.";
        reference
          "RFC 5480: Elliptic Curve Cryptography Subject Public Key Information.";
      }
      enum "ed25519" {
        description
          "The Ed25519 algorithm.";
        reference
          "RFC 8032: Edwards-Curve Digital Signature Algorithm (EdDSA).";
      }
    }
    description
      "Base identity from which all key-algorithms are derived.";
  }
}
