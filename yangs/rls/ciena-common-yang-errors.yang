module ciena-common-yang-errors {
  yang-version 1.1;
  namespace "urn:ciena:params:xml:ns:yang:ciena-common-yang-errors";
  prefix yang-errors;

  import ciena-common-yang {
    prefix ciena-common-yang;
  }
  import ciena-common-version {
    prefix version;
  }

  organization
    "Ciena Corporation";
  contact
    "Web URL: http://www.ciena.com/
     Postal:  7035 Ridge Road
             Hanover, Maryland 21076
             U.S.A.
     Phone:   +1 800-921-1144
     Fax:     +1 410-694-5750";
  description
    "Module to extend the basic errors with commonly userd errors and
     warnings in the system.";

  revision 2022-08-23 {
    description
      "Initial revision.";
    version:version "version" {
      version:string "1.0.0";
    }
  }

  identity invalid-input {
    base ciena-common-yang:error-code;
    description
      "Invalid input for an RPC or action";
  }

  identity data-not-unique {
    base ciena-common-yang:error-code;
    description
      "Violation of 'unique' constraint.";
  }

  identity too-many-elements {
    base ciena-common-yang:error-code;
    description
      "Number of elements exceeds the maximum allowed";
  }

  identity too-few-elements {
    base ciena-common-yang:error-code;
    description
      "Number of elements is less than the minimum required";
  }

  identity must-violation {
    base ciena-common-yang:error-code;
    description
      "Violation of 'must' statement";
  }

  identity instance-required {
    base ciena-common-yang:error-code;
    description
      "Instance identifier or leafref leaf with 'require-instance' constraint refers to a non-existing instance";
  }

  identity missing-choice {
    base ciena-common-yang:error-code;
    description
      "A choice statement is mandatory, but no nodes exist";
  }
}
