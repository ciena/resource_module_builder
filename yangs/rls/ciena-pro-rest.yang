module ciena-pro-rest {
  namespace "urn:ciena:params:xml:ns:yang:ciena-pro-rest";
  prefix ciena-pro-rest;

  import ciena-common-version {
    prefix version;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's rest model";

  revision 2020-09-23 {
    version:version "version" {
      version:string "1.1.0";
    }
    description
      "Added rest container and added
       enable-disable enum for holding state";
  }
  revision 2020-08-05 {
    version:version "version" {
      version:string "1.0.0";
    }
    description
      "Initial revision.";
  }

  typedef status-type {
    type enumeration {
      enum "disable" {
        description
          "Disable state.";
      }
      enum "enable" {
        description
          "Enable state.";
      }
    }
    description
      "Status type - enable or disable";
  }

  container rest {
    container server {
      leaf state {
        type status-type;
        mandatory true;
        description
          "Flag to enable or disable REST interface";
      }
    }
  }

  rpc kill-session {
    description
      "Force the termination of a REST session.";
    input {
      leaf session-id {
        type uint64;
        mandatory true;
        description
          "Particular session to kill.";
      }
    }
  }
}
