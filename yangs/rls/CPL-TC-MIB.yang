module CPL-TC-MIB {
  namespace "urn:ietf:params:xml:ns:yang:smiv2:CPL-TC-MIB";
  prefix cpl-tc;

  import CPL-OID-MIB {
    prefix cpl-oid;
  }
  import yang-smi {
    prefix smi;
  }

  organization
    "Ciena Corporation";
  contact
    "Ciena Corporation
     1201 Winterson Road
     Linthicum, Maryland 21090
     United States
     1-800-921-1144
     www.ciena.com";
  description
    "Textual conventions for the CPL project
     subtending cards";

  revision 2014-03-04 {
    description
      "Removed FixedX1000. References to FixedX1000 have been changed to Uint16.";
  }
  revision 2014-02-14 {
    description
      "Added FixedX1000";
  }
  revision 2012-03-12 {
    description
      "[Revision added by libsmi due to a LAST-UPDATED clause.]";
  }
  revision 2012-03-12 {
    description
      "Added L Band ITU wavelengths";
  }
  revision 2010-05-11 {
    description
      "Cleanup ";
  }
  revision 2010-04-13 {
    description
      "Change WavelengthId from 88 to 104, Add
       WavelengthInNm ITU wavelengths";
  }
  revision 2006-01-30 {
    description
      "Move some common amplifier textual conventions
       to the TC MIB";
  }
  revision 2003-12-05 {
    description
      "first DRAFT release";
  }

  typedef AlarmState {
    type enumeration {
      enum cleared {
        value 1;
      }
      enum raised {
        value 2;
      }
    }
    description
      "whether the alarm is raised or cleared";
  }

  typedef PrimaryState {
    type enumeration {
      enum is {
        value 1;
      }
      enum oos {
        value 2;
      }
      enum uas {
        value 3;
      }
    }
    description
      "in service, or out-of-service";
  }

  typedef Boolean {
    type enumeration {
      enum false {
        value 1;
      }
      enum true {
        value 2;
      }
    }
    description
      "boolean type";
  }

  typedef Int8 {
    type int32 {
      range "-128..127";
    }
    description
      "An 8 bit signed integer.";
  }

  typedef Int16 {
    type int32 {
      range "-32768..32767";
    }
    description
      "A 16 bit signed integer.";
  }

  typedef Uint8 {
    type int32 {
      range "0..255";
    }
    description
      "An 8 bit unsigned integer.";
  }

  typedef Uint16 {
    type int32 {
      range "0..65535";
    }
    description
      "A 16 bit unsigned integer.";
  }

  typedef Uint32 {
    type uint32 {
      range "0..4294967295";
    }
    description
      "A 32 bit unsigned integer.";
  }

  typedef FixedX10 {
    type int32;
    description
      "This represents a fixed point number with a
       single digit after the decimal point. However,
       because SNMP does not support floats, we multiply
       the number by 10 before SNMP gets it. To obtain
       actual value, divide by 10 and keep the remainder
       as the value after the decimal point. For example,
       the number 5.7 would be represented using this type
       as 57";
  }

  typedef FixedX100 {
    type int32;
    description
      "This represents a fixed point number with a
       2 digits after the decimal point. However,
       because SNMP does not support floats, we multiply
       the number by 100 before SNMP gets it. To obtain
       actual value, divide by 100 and keep the remainder
       as the value after the decimal point. For example,
       the number 5.70 would be represented using this
       type as 570";
  }

  typedef HysteresisRange {
    type cpl-tc:FixedX10 {
      range "0..200";
    }
    description
      "Hysteresis is used in calculating when an
       alarming condition that has been raised should be
       cleared. An alarm is raised when a value drops
       below a threshold. An alarm is cleared when the
       value rises to threshold + hysteresis.
       An example helps: suppose that LOS threshold is
       set to -31db, and LOS Hysteresis is set to 3db.
       When the signal strength lowers to -31, the alarm
       is raised. However, the alarm is not cleared
       until the signal strength rises to -31 + 3 ->
       -28db. ";
  }

  typedef WavelengthId {
    type int32 {
      range "1..96";
    }
    description
      "Index in a Wavelength table";
  }

  typedef PortIndex {
    type int32 {
      range "1..127";
    }
    description
      "Port Number Index";
  }

  typedef WavelengthInNm {
    type enumeration {
      enum wvLen93 {
        value 152877;
      }
      enum wvLen94 {
        value 152916;
      }
      enum wvLen95 {
        value 152955;
      }
      enum wvLen96 {
        value 152994;
      }
      enum wvLen1 {
        value 153033;
      }
      enum wvLen2 {
        value 153072;
      }
      enum wvLen3 {
        value 153112;
      }
      enum wvLen4 {
        value 153151;
      }
      enum wvLen5 {
        value 153190;
      }
      enum wvLen6 {
        value 153229;
      }
      enum wvLen7 {
        value 153268;
      }
      enum wvLen8 {
        value 153307;
      }
      enum wvLen9 {
        value 153347;
      }
      enum wvLen10 {
        value 153386;
      }
      enum wvLen11 {
        value 153425;
      }
      enum wvLen12 {
        value 153464;
      }
      enum wvLen13 {
        value 153504;
      }
      enum wvLen14 {
        value 153543;
      }
      enum wvLen15 {
        value 153582;
      }
      enum wvLen16 {
        value 153622;
      }
      enum wvLen17 {
        value 153661;
      }
      enum wvLen18 {
        value 153700;
      }
      enum wvLen19 {
        value 153740;
      }
      enum wvLen20 {
        value 153779;
      }
      enum wvLen21 {
        value 153819;
      }
      enum wvLen22 {
        value 153858;
      }
      enum wvLen23 {
        value 153898;
      }
      enum wvLen24 {
        value 153937;
      }
      enum wvLen25 {
        value 153977;
      }
      enum wvLen26 {
        value 154016;
      }
      enum wvLen27 {
        value 154056;
      }
      enum wvLen28 {
        value 154095;
      }
      enum wvLen29 {
        value 154135;
      }
      enum wvLen30 {
        value 154175;
      }
      enum wvLen31 {
        value 154214;
      }
      enum wvLen32 {
        value 154254;
      }
      enum wvLen33 {
        value 154294;
      }
      enum wvLen34 {
        value 154333;
      }
      enum wvLen35 {
        value 154373;
      }
      enum wvLen36 {
        value 154413;
      }
      enum wvLen37 {
        value 154453;
      }
      enum wvLen38 {
        value 154492;
      }
      enum wvLen39 {
        value 154532;
      }
      enum wvLen40 {
        value 154572;
      }
      enum wvLen41 {
        value 154612;
      }
      enum wvLen42 {
        value 154652;
      }
      enum wvLen43 {
        value 154692;
      }
      enum wvLen44 {
        value 154732;
      }
      enum wvLen45 {
        value 154772;
      }
      enum wvLen46 {
        value 154811;
      }
      enum wvLen47 {
        value 154851;
      }
      enum wvLen48 {
        value 154891;
      }
      enum wvLen49 {
        value 154932;
      }
      enum wvLen50 {
        value 154972;
      }
      enum wvLen51 {
        value 155012;
      }
      enum wvLen52 {
        value 155052;
      }
      enum wvLen53 {
        value 155092;
      }
      enum wvLen54 {
        value 155132;
      }
      enum wvLen55 {
        value 155172;
      }
      enum wvLen56 {
        value 155212;
      }
      enum wvLen57 {
        value 155252;
      }
      enum wvLen58 {
        value 155293;
      }
      enum wvLen59 {
        value 155333;
      }
      enum wvLen60 {
        value 155373;
      }
      enum wvLen61 {
        value 155413;
      }
      enum wvLen62 {
        value 155454;
      }
      enum wvLen63 {
        value 155494;
      }
      enum wvLen64 {
        value 155534;
      }
      enum wvLen65 {
        value 155575;
      }
      enum wvLen66 {
        value 155615;
      }
      enum wvLen67 {
        value 155655;
      }
      enum wvLen68 {
        value 155696;
      }
      enum wvLen69 {
        value 155736;
      }
      enum wvLen70 {
        value 155777;
      }
      enum wvLen71 {
        value 155817;
      }
      enum wvLen72 {
        value 155858;
      }
      enum wvLen73 {
        value 155898;
      }
      enum wvLen74 {
        value 155939;
      }
      enum wvLen75 {
        value 155979;
      }
      enum wvLen76 {
        value 156020;
      }
      enum wvLen77 {
        value 156061;
      }
      enum wvLen78 {
        value 156101;
      }
      enum wvLen79 {
        value 156142;
      }
      enum wvLen80 {
        value 156183;
      }
      enum wvLen81 {
        value 156223;
      }
      enum wvLen82 {
        value 156264;
      }
      enum wvLen83 {
        value 156305;
      }
      enum wvLen84 {
        value 156345;
      }
      enum wvLen85 {
        value 156386;
      }
      enum wvLen86 {
        value 156427;
      }
      enum wvLen87 {
        value 156468;
      }
      enum wvLen88 {
        value 156509;
      }
      enum wvLen89 {
        value 156550;
      }
      enum wvLen90 {
        value 156590;
      }
      enum wvLen91 {
        value 156631;
      }
      enum wvLen92 {
        value 156672;
      }
    }
    description
      "These represent the C Band wavelengths in nm of the
       wavelengths on the ITU grid. They are specified
       to 2 decimal places of precision instead of the
       3 normally used";
  }

  typedef OpticalPowerRange {
    type cpl-tc:FixedX10 {
      range "-600..300";
    }
    description
      "Measured Optical Power Range in dBm";
  }

  typedef ShutoffThresholdRange {
    type cpl-tc:FixedX10 {
      range "-600..200";
    }
    description
      "Level at for Threshold Crossing in dbm";
  }

  typedef InputPowerRange {
    type cpl-tc:FixedX10 {
      range "-650..200";
    }
    description
      "";
  }

  typedef OutputPowerRange {
    type cpl-tc:FixedX10 {
      range "-500..300";
    }
    description
      "";
  }

  typedef ORLRange {
    type cpl-tc:FixedX10 {
      range "0..500";
    }
    description
      "Optical Return Loss";
  }
}
