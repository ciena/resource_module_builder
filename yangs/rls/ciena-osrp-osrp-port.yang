module ciena-osrp-osrp-port {
  yang-version 1.1;
  namespace "urn:ciena:params:xml:ns:yang:ciena-osrp-osrp-port";
  prefix osrp-port;

  import ciena-common-yang {
    prefix ciena-common-yang;
  }
  import ciena-osrp-common-port {
    prefix ciena-osrp-common-port;
  }
  import ciena-common-version {
    prefix ciena-common-version;
  }

  organization
    "Ciena Corporation";
  contact
    "Web URL: http://www.ciena.com
     Postal: Ciena India Pvt. Ltd.
     Sector 32, Plot 14,
     Gurgaon 122001,
     Haryana, India";
  description
    "This module describes Ciena's osrp-port object for the 6500r platform";

  revision 2021-07-28 {
    description
      "grouped osrp-port to common yang.";
    ciena-common-version:string "1.4.0";
  }
  revision 2021-02-05 {
    description
      "fault-source is removed from faults list key.";
    ciena-common-version:string "1.3.0";
  }
  revision 2021-01-09 {
    description
      "Node-id length extended.";
    ciena-common-version:string "1.2.0";
  }
  revision 2020-10-07 {
    description
      "Added logical-port-id for tlpi display for channel-port on osrp.";
    ciena-common-version:string "1.1.0";
  }
  revision 2020-09-07 {
    description
      "ip-address field added in remote-config for InterShelf/InterSite Comms.";
    ciena-common-version:string "1.0.1";
  }
  revision 2020-03-30 {
    description
      "Initial revision.";
    ciena-common-version:string "1.0.0";
  }

  grouping ciena-osrp-osrp-port-mount-data {
    list osrp-port {
      key "name";
      uses ciena-osrp-common-port:osrp-common-port;
    }
  }

  grouping ciena-osrp-osrp-port-mount-actions-notifs;

  grouping ciena-osrp-osrp-port-mount-actions-notifs-as-cont;

  grouping ciena-osrp-osrp-port-mount-data-actions-notifs-as-cont {
    list osrp-port {
      key "name";
      uses ciena-osrp-common-port:osrp-common-port;
    }
  }

  uses ciena-osrp-osrp-port-mount-data;
}
