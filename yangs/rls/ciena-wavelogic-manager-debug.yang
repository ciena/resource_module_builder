module ciena-wavelogic-manager-debug {
  namespace "urn:ciena:params:xml:ns:yang:ciena-wavelogic-manager-debug";
  prefix wavelogic-manager-debug;

  import ciena-common-version {
    prefix ciena-common-version;
  }
  import ciena-common-yang {
    prefix yang;
  }
  import ciena-pro-coherent-device-common-types {
    prefix coherent-device-common-types;
  }
  import ciena-pro-coherent-device {
    prefix coherent-device;
  }
  import ciena-pro-coherent-device-types {
    prefix coherent-device-types;
  }

  organization
    "Ciena Corporation";
  contact
    "Web URL: http://www.ciena.com";
  description
    "Wavelogic Manager debug module";

  revision 2022-10-31 {
    description
      "Add create-coherent-device-instance";
    ciena-common-version:string "1.1.0";
  }
  revision 2022-10-13 {
    description
      "Initial revision";
    ciena-common-version:string "1.0.0";
    reference
      "1.0.0";
  }

  container debug {
    leaf flags {
      type uint32;
      description
        "multi-purpose debug flags.";
    }
    description
      "debug";
  }

  rpc create-ra-management-instance {
    input {
      leaf ra-name {
        type coherent-device-common-types:string255;
        description
          "The name string of assocated RA.";
      }
      leaf ipport {
        type string;
        description
          "IP and Port in the URL of the destination.";
      }
      leaf pubipport {
        type string;
        description
          "IP and Port of the publisher to connect to";
      }
    }
    output {
      leaf success {
        type boolean;
      }
      leaf error-str {
        type string;
        mandatory false;
        description
          "A string description of the return code.";
      }
    }
  }

  rpc delete-ra-management-instance {
    input {
      leaf ra-name {
        type coherent-device-common-types:string255;
        description
          "The name string of assocated RA.";
      }
    }
    output {
      leaf success {
        type boolean;
      }
      leaf error-str {
        type string;
        mandatory false;
        description
          "A string description of the return code.";
      }
    }
  }

  rpc configure-ra-management-instance {
    input {
      leaf ra-name {
        type coherent-device-common-types:string255;
        mandatory true;
        description
          "The name string of assocated RA.";
      }
      leaf action {
        type yang:yang-action;
        mandatory true;
      }
      leaf ipport {
        type string;
        description
          "IP and Port in the URL of the destination.";
      }
      leaf pubipport {
        type string;
        description
          "IP and Port of the publisher to connect to";
      }
    }
    output {
      leaf success {
        type boolean;
      }
      leaf error-str {
        type string;
        mandatory false;
        description
          "A string description of the return code.";
      }
    }
  }

  rpc activate-device-stage-registration {
    input {
      leaf domain {
        type string;
        description
          "Target domain for the registration";
      }
      leaf service {
        type string;
        description
          "Target service for the registration";
      }
    }
    output {
      leaf success {
        type boolean;
      }
      leaf error-str {
        type string;
        mandatory false;
        description
          "A string description of the return code.";
      }
    }
  }

  rpc configure-coherent-device-instance {
    input {
      leaf device-id {
        type coherent-device-types:device-id-type;
        mandatory true;
        description
          "The top-level identifier for a coherent device represented
           in this list.";
      }
      leaf action {
        type yang:yang-action;
        mandatory true;
      }
      uses coherent-device:coherent-device-config-common-group;
      uses coherent-device:coherent-device-config-media-interface-list-group;
    }
    output {
      leaf success {
        type boolean;
      }
      leaf error-str {
        type string;
        mandatory false;
        description
          "A string description of the return code.";
      }
    }
  }
}
