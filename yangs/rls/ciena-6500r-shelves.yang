module ciena-6500r-shelves {
  namespace "urn:ciena:params:xml:ns:yang:ciena-6500r-shelves";
  prefix shelves;

  import ciena-6500r-types {
    prefix ciena-6500r-types;
  }

  import ciena-common-yang {
    prefix yang;
  }

  import ietf-yang-types {
    prefix ietf-yang;
  }

  import ciena-common-version {
    prefix ciena-common-version;
  }

  import ciena-pro-alarm-correlation {
    prefix ciena-pro-alarm-correlation;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's shelves object for the 6500r platform";

  revision 2020-11-12 {
    ciena-common-version:string "1.3.0";
    description
      "Added the mac address to shelf container";
  }
  revision 2020-08-10 {
    ciena-common-version:string "1.2.0";
    description
      "Added the alarm-correlation upstream-fault-maksing-group to shelf container";
  }
  revision 2020-05-08 {
    ciena-common-version:string "1.1.0";
    description
      "Marked current-power and power config containers as non-config";
  }
  revision 2020-03-24 {
    ciena-common-version:string "1.1.0";
    description
      "Added current-power";
  }
  revision 2017-10-01 {
    description
      "6500r Release 1.0-
       Added container: shelves";
  }

  container shelf {
    leaf name {
      type ciena-6500r-types:object-name;
      description
        "Shelf name";
    }

    leaf pec {
      type ciena-6500r-types:pec-code;
      description
        "Pec code";
    }

    leaf c-type {
      type string;
      description
        "c-type";
    }

    leaf label {
      type string;
      description
        "label";
    }

    leaf ui-name {
      type string;
      description
        "ui-name";
    }

    leaf product {
      type ciena-6500r-types:product;
      description
        "Product";
    }

    leaf shelf-type {
      type ciena-6500r-types:shelf-type;
      description
        " SHELF-type";
    }

    leaf serial-number {
      type string;
      config false;
      description
        "The vendor-specific serial number string for the
         component.";
    }

    leaf manufacturing-date {
      type ietf-yang:date-and-time;
      config false;
      description
        "The date of manufacturing of the managed component.";
    }

    leaf hardware-release {
      type string;
      config false;
      description
        "Release level.";
    }

    container current-power {
      config false;
      leaf value {
        type int32;
        units "W";
        config false;
        description
          "Current-power value.";
      }

      leaf measurement-type {
        type enumeration {
          enum "measured";
          enum "estimated";
          enum "unknown";
        }
        config false;
        description
          "Flag to indicate if current power is measured, estimated or unknown.";
      }
    }

    container power {
      config false;
      leaf low-power {
        type uint16 {
          range "0..960";
        }
        units "W";
        config false;
        description
          "Low power (in W) for this card";
      }

      leaf max-power {
        type uint16 {
          range "0..960";
        }
        units "W";
        config false;
        description
          "Maximum power (in W) for this card";
      }
    }

    container shelf-location {
      leaf frame-identification-code {
        type string;
        description
          "FIC";
      }

      leaf bay-num {
        type ciena-6500r-types:INT {
          range "0..99";
        }
        default "0";
        description
          "Bay Number";
      }

      leaf phys-shelf {
        type ciena-6500r-types:INT {
          range "0..99";
        }
        default "0";
        description
          "Physical Shelf Number";
      }
    }

    leaf mac-address {
      type ietf-yang:mac-address;
      config false;
      description
        "MAC address";
    }

    uses ciena-pro-alarm-correlation:upstream-fault-masking-group;
  }
}
