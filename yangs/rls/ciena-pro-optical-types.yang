module ciena-pro-optical-types {
  namespace "urn:ciena:params:xml:ns:yang:ciena-pro-optical-types";
  prefix pro-optical-types;

  import ciena-common-version {
    prefix ciena-common-version;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena common objects.";

  revision 2021-05-14 {
    ciena-common-version:version "version" {
      ciena-common-version:string "1.2.0";
    }
    description
      "Added 2 new types called delta-dB-2-precision and coeff-2-precision.";
  }
  revision 2020-11-16 {
    ciena-common-version:version "version" {
      ciena-common-version:string "1.1.0";
    }
    description
      "Added a new type called delta-dB-1-precision, and three new groupings:
       grouping monitoring-thresholds-grouping, grouping monitoring-hysteresis-grouping
       and monitoring-diagnostic-grouping.";
  }
  revision 2020-08-01 {
    ciena-common-version:version "version" {
      ciena-common-version:string "1.0.0";
    }
    description
      "Initial version";
  }

  typedef frequency {
    type decimal64 {
      fraction-digits 3;
    }
    units "GHz";
  }

  typedef power {
    type decimal64 {
      fraction-digits 2;
    }
    units "dBm";
  }

  typedef power-dBm-1-precision {
    type decimal64 {
      fraction-digits 1;
    }
    units "dBm";
  }

  typedef gain-loss {
    type decimal64 {
      fraction-digits 2;
    }
    units "dB";
    description
      "Positive for gain, negative for loss";
  }

  typedef gain {
    type decimal64 {
      fraction-digits 2;
    }
    units "dB";
    description
      "Positive for gain";
  }

  typedef gain-dB-1-precision {
    type decimal64 {
      fraction-digits 1;
    }
    units "dB";
    description
      "Positive for gain";
  }

  typedef loss {
    type decimal64 {
      fraction-digits 2;
    }
    units "dB";
    description
      "Positive for loss";
  }

  typedef loss-dB-1-precision {
    type decimal64 {
      fraction-digits 1;
    }
    units "dB";
    description
      "Positive for loss";
  }

  typedef delta-dB-1-precision {
    type decimal64 {
      fraction-digits 1;
    }
    units "dB";
    description
      "Relative difference in power values.";
  }

  typedef delta-dB-2-precision {
    type decimal64 {
      fraction-digits 2;
    }
    units "dB";
    description
      "Relative difference in power values.";
  }

  typedef coeff-2-precision {
    type decimal64 {
      fraction-digits 2;
    }
    units "dB/dB";
    description
      "Coefficient with 2 decimal precision.";
  }

  typedef psd {
    type decimal64 {
      fraction-digits 2;
    }
    units "dBm/12.5GHz";
    description
      "Power Spectral Density";
  }

  typedef band-occupancy {
    type bits {
      bit BAND-C {
        position 0;
      }
      bit BAND-L {
        position 1;
      }
      bit OSC {
        position 2;
      }
      bit TELEMETRY {
        position 3;
      }
      bit TOTAL {
        position 4;
      }
    }
    description
      "Band Type";
  }

  typedef fiber-type {
    type enumeration {
      enum "unknown";
      enum "other";
      enum "AllWave";
      enum "DSF" {
        description
          "Dispersion Shifted single mode Fiber";
      }
      enum "FreeLight";
      enum "LEAF" {
        description
          "Large Effective Area Fiber";
      }
      enum "Enhanced LEAF";
      enum "Lambda Shifted";
      enum "NDSF" {
        description
          "Non-Dispersion Shifted Fiber";
      }
      enum "NDSF LWP" {
        description
          "NDSF Low Water Peak";
      }
      enum "PSC" {
        description
          "Pure Silica Fiber";
      }
      enum "TeraLight";
      enum "TeraWave ULL" {
        description
          "TeraWave Ultra Low Loss";
      }
      enum "TrueWave Classic";
      enum "TrueWave Plus";
      enum "TrueWave Reach";
      enum "TrueWave RS" {
        description
          "TrueWave Reduced Slope";
      }
      enum "EX2000";
      enum "EX3000";
      enum "MetroCor";
      enum "patchCord";
      enum "SMF28ULL";
    }
    description
      "Fiber type";
  }

  typedef orl-state {
    type enumeration {
      enum "valid" {
        value 1;
        description
          "ORL in valid state.";
      }
      enum "outputOORL" {
        value 2;
        description
          "Output is dark, OOR is low.";
      }
      enum "reflectOORL" {
        value 3;
        description
          "Reflection is dark, OOR is low.";
      }
      enum "reflectOORH" {
        value 4;
        description
          "Reflection is dark, OOR is high.";
      }
      enum "hssf" {
        value 5;
        description
          "Possible hardware subsystem failure.";
      }
      enum "shutoff" {
        value 6;
        description
          "Shutoff mode is enabled.";
      }
      enum "unknown" {
        value 7;
        description
          "If the state from the device is not known.";
      }
      enum "notApplicable" {
        value 8;
        description
          "ORL state not applicable.";
      }
    }
    description
      "The ORL State";
  }

  grouping monitoring-thresholds-grouping {
    leaf out-of-range-high {
      type power-dBm-1-precision;
      description
        "Power threshold at which the out-of-range-high diagnostic
         point should be raised.";
    }

    leaf degrade-high {
      type power-dBm-1-precision;
      description
        "Power threshold at which the degrade-high diagnostic
         point should be raised.";
    }

    leaf degrade-low {
      type power-dBm-1-precision;
      description
        "Power threshold at which the degrade-low diagnostic
         point should be raised.";
    }

    leaf out-of-range-low {
      type power-dBm-1-precision;
      description
        "Power threshold at which the out-of-range-low diagnostic
         point should be raised.";
    }
  }

  grouping monitoring-hysteresis-grouping {
    leaf out-of-range-high-hysteresis {
      type delta-dB-1-precision;
      description
        "The hysteresis (delta) value relative to the out-of-range-high threshold,
         for clearing of the out-of-range-high diagnostic value.";
    }

    leaf degrade-high-hysteresis {
      type delta-dB-1-precision;
      description
        "The hysteresis (delta) value relative to the degrade-high threshold,
         for clearing of the out-of-range-high diagnostic value.";
    }

    leaf degrade-low-hysteresis {
      type delta-dB-1-precision;
      description
        "The hysteresis (delta) value relative to the degrade-low threshold,
         for clearing of the out-of-range-high diagnostic value.";
    }

    leaf out-of-range-low-hysteresis {
      type delta-dB-1-precision;
      description
        "The hysteresis (delta) value relative to the out-of-range-low threshold,
         for clearing of the out-of-range-low diagnostic value.";
    }
  }

  grouping monitoring-diagnostic-grouping {
    leaf out-of-range-high {
      type boolean;
      description
        "Raised when the power exceeds the out-of-range-high threshold.
         Clears when the power falls below the out-of-range-high threshold
         minus the out-of-range-high-hysteresis value.";
    }

    leaf degrade-high {
      type boolean;
      description
        "Raised when the power exceeds the degrade-high threshold.
         Clears when the power falls below the degrade-high threshold
         minus the degrade-high-hysteresis value.";
    }

    leaf degrade-low {
      type boolean;
      description
        "Raised when the power falls below the degrade-low threshold.
         Clears when the power exceeds the degrade-low threshold
         plus the degrade-low-hysteresis value.";
    }

    leaf out-of-range-low {
      type boolean;
      description
        "Raised when the power falls below the out-of-range-low threshold.
         Clears when the power exceeds the out-of-range-low threshold
         plus the out-of-range-low-hysteresis value.";
    }
  }
}
