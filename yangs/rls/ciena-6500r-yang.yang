module ciena-6500r-yang {
  namespace "urn:ciena:params:xml:ns:yang:ciena-6500r-yang";
  prefix yang;

  organization
    "Ciena Corporation";
  contact
    "Web URL: http://www.ciena.com/
     Postal:  7035 Ridge Road
             Hanover, Maryland 21076
             U.S.A.
     Phone:   +1 800-921-1144
     Fax:     +1 410-694-5750";
  description
    "password:This metadata is populated for distinguishing password node from others.
               access:This metadata is populated with security level information of a node.
         ";

  revision 2017-10-01 {
    description
      "";
  }

  extension handler {
    argument value;
  }

  extension create-supported {
    argument value;
  }

  extension edit-supported {
    argument value;
  }

  extension get-supported {
    argument value;
  }

  extension delete-supported {
    argument value;
  }

  extension password {
    argument value;
  }

  extension access {
    argument value;
  }
}
