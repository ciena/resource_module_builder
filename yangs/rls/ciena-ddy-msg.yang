module ciena-ddy-msg {
  namespace "urn:ciena:params:xml:ns:yang:ciena-ddy-msg";
  prefix ddy-msg;

  import ciena-common-version {
    prefix version;
  }

  import ciena-common-yang {
    prefix yang;
  }

  import ciena-common-exceptions {
    prefix except;
  }

  import ietf-inet-types {
    prefix ietf;
  }

  import ciena-ddy-msg-options {
    prefix msg-options;
  }

  organization
    "Ciena Corporation";
  contact
    "Web URL: http://www.ciena.com/
     Postal:  7035 Ridge Road
              Hanover, Maryland 21076
              U.S.A.
     Phone:   +1 800-921-1144
     Fax:     +1 410-694-5750";
  description
    "This is the model for the data driven messaging component of the
     Bifrost framework.";

  revision 2021-04-13 {
    version:version "version" {
      version:string "1.14.0";
    }
    description
      "Add domain to output of get-services rpc";
  }
  revision 2021-01-06 {
    version:version "version" {
      version:string "1.13.0";
    }
    description
      "Add resource-limits and start-command-prefix";
  }
  revision 2020-12-11 {
    version:version "version" {
      version:string "1.12.0";
    }
    description
      "Add a compatibility-state leaf and incompatible-reason leaf-list to domains";
  }
  revision 2020-10-31 {
    version:version "version" {
      version:string "1.11.0";
    }
    description
      "Add a registered-on leaf to providers";
  }
  revision 2020-06-16 {
    version:version "version" {
      version:string "1.10.0";
    }
    description
      "Add a provider_sync rpc";
  }
  revision 2020-06-15 {
    version:version "version" {
      version:string "1.9.1";
    }
    description
      "Changed instance-ids to target--nodes.";
  }
  revision 2020-05-08 {
    version:version "version" {
      version:string "1.8.0";
    }
    description
      "Introduce service resource refresh rpc";
  }
  revision 2020-03-13 {
    version:version "version" {
      version:string "1.9.0";
    }
    description
      "Add a local-id to a domain.";
  }
  revision 2020-03-01 {
    version:version "version" {
      version:string "1.8.1";
    }
    description
      "Fix module formatting and clarify the meaning of `depends` and
       `requires` description statements.";
  }
  revision 2019-11-13 {
    version:version "version" {
      version:string "1.8.0";
    }
    description
      "Added get-on-change flag to subscribers";
  }
  revision 2019-10-05 {
    version:version "version" {
      version:string "1.7.0";
    }
    description
      "Generic framework to define service dependency with other
       services and yang resources";
  }
  revision 2019-09-19 {
    version:version "version" {
      version:string "1.6.0";
    }
    description
      "Added domain and service as keys to
       providers lists.";
  }
  revision 2019-09-04 {
    version:version "version" {
      version:string "1.4.0";
    }
    description
      "Added scope and scope alias to domains and
       startup data to services.";
  }
  revision 2019-07-11 {
    version:version "version" {
      version:string "1.3.0";
    }
    description
      "Added request-id to providers";
  }
  revision 2019-05-31 {
    version:version "version" {
      version:string "1.2.0";
    }
    description
      "Added domain-service grouping to providers";
  }
  revision 2019-05-10 {
    version:string "1.1.0";
    description
      "Moved on-since to be config=false.";
  }
  revision 2019-03-21 {
    version:string "1.0.0";
    description
      "Initial revision";
  }

  identity message-timeout {
    base except:exception;
    description
      "An exception type for messaging timeouts. When this exception
       is thrown, it indicates that the last messaging operation timed
       out.";
  }

  identity ddm-importance {
    description
      "Indication of how important the domain or service is.";
  }

  identity critical {
    base ddm-importance;
    description
      "If this service fails, this indicates a complete system failure.";
  }

  identity non-critical {
    base ddm-importance;
    description
      "If this service fails, this not a critical failure.";
  }

  identity error-messaging {
    base yang:error-code;
    description
      "Error was generated by a messaging failure.";
  }

  identity ddm-protocols {
    description
      "The base identity to represent ddy-msg protocols.";
  }

  identity ddm-format {
    description
      "The base identity to represent ddy-msg data formats.";
  }

  identity ddm-json {
    base ddm-format;
    description
      "JSON format";
  }

  identity ddm-xml {
    base ddm-format;
    description
      "XML format";
  }

  identity ddm-gpb {
    base ddm-format;
    description
      "Google protobuf format";
  }

  identity local {
    base ddm-protocols;
    description
      "Local messaging for within the domain";
  }

  identity ddm-resource-type {
    description
      "The type of a resource supported by a domain.";
  }

  identity ddm-yang-module {
    base ddm-resource-type;
    description
      "A YANG module resource.";
  }

  identity dependency-type {
    description
      "Base identity for a dependency type";
  }

  identity model {
    base dependency-type;
    description
      "Service dependency to a yang module. This list is used during
       compile and run time to associate a set of yang resources to a
       service";
  }

  identity messaging {
    base dependency-type;
    description
      "Service messaging dependency on other services. This list is used
       to perform heartbeat and detect early messaging failure";
  }

  identity incompatible-reason-type {
    description
      "The reason for incompatibility state of domain";
  }

  identity protocol-mismatch {
    base incompatible-reason-type;
    description
      "The reason of incompatibility is protocol-mismatch.";
  }

  identity unknown {
    base incompatible-reason-type;
    description
      "The reason of incompatibility is unknown.";
  }

  typedef state-type {
    type enumeration {
      enum "UNKNOWN";
      enum "ACTIVE";
      enum "INACTIVE";
      enum "ACTIVATING";
      enum "DEACTIVATING";
      enum "FAILED";
    }
    description
      "The current running state of the service";
  }

  grouping version-grouping {
    description
      "Grouping that contains resource version information";
    container version {
      description
        "This version data is semantic versioning for the module.
         If the major number has increased, this is a non-backwards-
         API change.  If a minor number has increased, this is a
         backwards compatible change, extension, or deprecation.  If
         the patch number has increased there is no API change but
         an implementation change may exist.";
      leaf string {
        type string;
        description
          "String represenation of version field.  Must be in M.m.p
           format, which M = major, m = minor, and p = patch version";
      }

      leaf major {
        type uint32;
        description
          "Major revision for the module.  Changes to this indicate a
           non-backwards compatible change.  Changes must be incremental.";
      }

      leaf minor {
        type uint32;
        description
          "Minor revision for the module.  Changes to this indicate a
           backwards compatible change.  Changes must be incremental.";
      }

      leaf patch {
        type uint32;
        description
          "Patch revision for the module.  Changes to this indicate a
           internal change to implementaiton and no API change.
           Changes must be incremental.";
      }
    }
  }

  grouping resource-config {
    leaf resource-name {
      type string;
    }

    leaf proxied {
      type boolean;
      default "false";
      description
        "Indicates if the resource is proxied by this service
         (true) or if it is owned by this service (false)";
    }

    leaf resource-type {
      type identityref {
        base ddm-resource-type;
      }
    }

    uses version-grouping;

    leaf revision {
      type string;
    }
  }

  grouping domain-service-grouping {
    leaf domain {
      type string;
      description
        "The name of domain";
    }

    leaf service {
      type string;
      description
        "The name of service";
    }
  }

  grouping service-grouping {
    list service {
      key "name";
      leaf name {
        type string;
        description
          "Service name";
      }

      leaf-list requires {
        type string;
        description
          "A list of services that must be present in the domains file
           so that this service can communicate with them. Setting a service
           name in this list will tell dir-svc to copy the domain data
           to this service's domains.xml file so that they can communicate
           and bind remote handlers (etc).";
      }

      leaf-list depends {
        type string;
        description
          "A list of services that this service will communicate with.
           This can be used by a startup script or directory service to
           bring in domains entries for the non-local services so the local
           service can communicate. Can also be used to limit the scope of
           the included yang modules to only those required by the service.";
      }

      container dependency {
        description
          "Service has many different types of dependencies such as
           messaging dependencies, yang model dependencies and LCM
           dependencies. Certain actions are performed at run-time or
           compile-time based on those dependencies. There are two types
           of lists in this container: profiles-list and depends-list.
           The depends-list contains different types of dependencies and
           profiles-list contains a set of profiles that any depends-list
           item can associate itself with. Due to the generic nature of this
           container, other categories of dependency can be easily added
           through augmentation";
        list profiles {
          key "name";
          description
            "Profile hold attribute common to items in the depends list";
          leaf name {
            type string;
            description
              "Name of the profile";
          }
        }

        list depends {
          key "type name";
          description
            "Defines different types of dependencies";
          leaf type {
            type identityref {
              base dependency-type;
            }
            description
              "Type of the dependency";
          }

          leaf name {
            type string;
            description
              "Name is used to uniquely identify a dependency. It can be
               service name, yang module name and etc";
          }

          leaf profile-name {
            type instance-identifier;
            description
              "Name of the profile that it belongs to";
          }
        }
      }

      list resource {
        key "resource-name";
        uses resource-config;
      }

      leaf state {
        type identityref {
          base yang:state-name;
        }
        description
          "The state of the service.";
      }

      anyxml data {
        description
          "Data used to configure the service at startup.";
      }

      list subscription {
        key "id";
        config false;
        description
          "list of subscriptions that configured via internal RPC";
        leaf id {
          type uint64;
          description
            "uniquely identifies a subscription";
        }

        list filters {
          key "path";
          description
            "list of subscribed paths and filters. There can be multiple
             filters to a single subscription";
          leaf path {
            type yang:target-node;
            description
              "subscription path";
          }

          leaf fields {
            type string;
            description
              "The fields specify the interested data in the subscribed path";
            reference
              "IETF RFC 8040 fields specification:
               https://tools.ietf.org/html/rfc8040#section-4.8.3";
          }
        }

        container connection {
          leaf ip-address {
            type ietf:ip-address;
            description
              "IP address of destination";
          }

          leaf port {
            type uint16;
            description
              "port number of destination";
          }

          leaf protocol {
            type leafref {
              path "../../../../service/name";
            }
            description
              "The name of the service.";
          }
        }
      }

      container providers {
        list validator {
          key "target-node domain service";
          leaf target-node {
            type yang:target-node;
            description
              "The instance for which the validation provider is registered";
          }

          uses domain-service-grouping;

          uses registered-on-grouping;
        }

        list stager {
          key "target-node domain service";
          leaf target-node {
            type yang:target-node;
            description
              "The instance for which the staging provider is registered";
          }

          uses domain-service-grouping;

          uses registered-on-grouping;
        }

        list subscriber {
          yang:alias "providers-subscriber";
          key "target-node domain service";
          leaf target-node {
            type yang:target-node;
            description
              "The instance for which the subscription provider is registered";
          }

          uses domain-service-grouping;

          leaf frequency {
            type uint32;
            description
              "The frequency at which the subscriber must be notified";
          }

          leaf get-initial {
            type boolean;
            description
              "set to TRUE if request should report the data initially.";
          }

          leaf get-on-change {
            type boolean;
            default "true";
            description
              "flag that controls if the subscriber is to be notified
               for changed data.";
          }

          uses registered-on-grouping;
        }

        list notifier {
          yang:alias "providers-notifier";
          key "target-node domain service";
          leaf target-node {
            type yang:target-node;
            description
              "The notification for which subscription provider is registered";
          }

          uses domain-service-grouping;

          uses registered-on-grouping;
        }

        list id {
          yang:alias "providers-id";
          key "request-id";
          leaf request-id {
            type uint64;
            description
              "This is a special flag added for supporting polling
               mechanism. This helps in determining the correct service
               for sending updates at a regular interval";
          }

          leaf target-node {
            type yang:target-node;
            description
              "The node path for which subscription provider is registered
               for getting notifications on regular intervals";
          }
        }
      }
    }
  }

  grouping compatibility-grouping {
    leaf compatibility-status {
      type boolean;
      config false;
      description
        "The compatibility state of the domain.";
    }

    leaf-list incompatible-reason {
      type identityref {
        base incompatible-reason-type;
      }
      config false;
      description
        "The reason for compatibility state of the domain.";
    }
  }

  grouping state-on-since-grouping {
    leaf state {
      type state-type;
      description
        "The state of the domain.";
    }

    leaf on-since {
      type uint64;
      config false;
      description
        "Time when this domain was last started, in nanoseconds.";
    }
  }

  grouping scope-grouping {
    leaf scope {
      type string {
        length "1..32";
      }
      description
        "name of scope for a domain. A domain can have scopes like
         photonic-section, internal, ctm, etc";
    }

    leaf alias {
      type string;
      description
        "name of local domain in scope";
    }
  }

  grouping domain-grouping {
    leaf domain {
      type string;
      description
        "The name of the domain.";
    }

    leaf start-command {
      type string;
      description
        "Command to start this domain. Default value is the domain name.";
    }

    leaf start-command-prefix {
      type string {
        length "1..256";
      }
      description
        "A command prefix to the domain starter. This is to allow running domain starter within
         some debug tool such as valgrind,strace,gdbserver";
    }

    container resource-limits {
      description
        "List of limits on the kernel resource usage";
      leaf-list cpu-affinity {
        type uint32;
        description
          "Affinity to a CPU core. The core number starts from 0. If an invalid
           core number is provided it is ignored. Has no effect if changed on a running domain";
      }
    }

    leaf scope {
      type string {
        length "1..32";
      }
      description
        "name of scope for local domain. A domain can have scopes like
         photonic-section, internal, ctm, etc.";
    }

    leaf local {
      type boolean;
      description
        "Flag to indicate if this is the local domain in a process.";
    }

    leaf importance {
      type identityref {
        base ddm-importance;
      }
      default "non-critical";
      description
        "Indication of how important this domain is and how the system
         should react if it fails";
    }

    list scopes {
      key "scope";
      uses scope-grouping;
    }

    uses msg-options:local-id;

    list protocols {
      key "protocol";
      leaf protocol {
        type string;
        description
          "The name of the protocol.";
      }

      leaf rpc-only {
        type boolean;
        default "true";
        description
          "Flag that indicates if this protocol should be invoked using only
           RPC calls (true), or if it supports action invocation using internal
           calls (false).";
      }

      leaf type {
        type identityref {
          base ddm-protocols;
        }
        description
          "The type of the protocol.";
      }

      leaf service {
        type string;
        description
          "Local messaging service to invoke for this protocol.";
      }
    }

    leaf protocol {
      type leafref {
        path "../protocols/protocol";
      }
    }

    leaf managed {
      type boolean;
      description
        "Indicates if the lifecycle of the domain is managed by the directory
         service (true) or not (false).";
    }

    uses compatibility-grouping;

    uses state-on-since-grouping;

    container heartbeat {
      leaf send-interval {
        type uint32;
        units "msecs";
        default "10000";
        description
          "Interval between heartbeat messages sent by this domain. A value of
           zero disables heartbeat message.";
      }

      leaf supported {
        type boolean;
        default "true";
        description
          "Indicates if this domain supports heartbeat messages. A value of
           false means that no heartbeat message should be sent to this domain.";
      }

      leaf failures {
        type uint32;
        config false;
        description
          "Number of heartbeat failures since the last successful heartbeat";
      }

      leaf fail-threshold {
        type uint32;
        default "3";
        description
          "Maximum number of heartbeat failures before the domain state is set
           to FAILED.";
      }
    }

    uses service-grouping;
  }

  grouping registered-on-grouping {
    leaf registered-on {
      type uint64;
      config false;
      description
        "The time of registration, filled by publisher";
    }
  }

  container domain {
    config false;
    leaf domain {
      type string;
      description
        "The name of the domain.";
    }

    uses msg-options:local-id;

    uses state-on-since-grouping;

    uses service-grouping;
  }

  list domains {
    key "domain";
    uses domain-grouping;
  }

  list provider-callout {
    key "target-node";
    leaf target-node {
      type yang:target-node;
      description
        "The instance for which a provider call is to be performed";
    }

    list validator {
      key "domain service";
      uses domain-service-grouping;
    }

    list stager {
      key "domain service";
      uses domain-service-grouping;
    }

    list subscriber {
      key "domain service";
      uses domain-service-grouping;

      leaf request-id {
        type uint64;
        description
          "This is a special flag added for supporting polling mechanism.
           This helps in determining the correct service for sending
           update at a regular interval";
      }

      leaf get-on-change {
        type boolean;
        default "true";
        description
          "flag that controls if the subscriber is to be notified for
           changed data.";
      }
    }

    list notifier {
      key "domain service";
      uses domain-service-grouping;
    }
  }

  rpc get-services {
    description
      "This RPC will return a list of services related to set of data.  This
       can be used to determine which services need to have locks, or how to
       distribute data to multiple services if needed";
    input {
      anyxml data {
        description
          "The input data to get related services for";
      }

      leaf names-only {
        type boolean;
        default "true";
        description
          "Flag to indicate if only the names of the services are needed,
           or if the provided data should be split and associated with
           each service";
      }
    }

    output {
      list services {
        leaf domain {
          type string;
          description
            "Name of the domain related to the input data";
        }

        leaf service {
          type string;
          description
            "Name of the service related to the input data";
        }

        anyxml data {
          description
            "The data from the input associated with this service. This
             is only provided if the 'names-only' parameter is false.";
        }
      }

      uses yang:rpc-result-common;
    }
  }

  rpc refresh-service {
    description
      "Refresh all resources belonging to a service. It does an internal
       get on a service data and then publishes them to all subscribers";
    input {
      leaf service-name {
        type string;
        description
          "Name of the service";
      }
    }

    output {
      uses yang:rpc-result-common;
    }
  }

  rpc stop-service {
    description
      "This RPC shuts down a service.";
    input {
      leaf service-name {
        type string;
        description
          "Name of the service";
      }
    }

    output {
      leaf result {
        type string;
        description
          "Return OK on success";
      }
    }
  }

  rpc provider-sync {
    description
      "Sync to domain.
       It queries domain specified by the service and performs sync.
       In case domain is not specified, it syncs to all domains which specify scope";
    input {
      leaf domain {
        type string;
        description
          "Name of domain to sync to.";
      }
    }

    output {
      uses yang:rpc-result-common;
    }
  }
}
