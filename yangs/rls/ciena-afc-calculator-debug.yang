module ciena-afc-calculator-debug {
  yang-version 1.1;
  namespace "urn:ciena:params:xml:ns:yang:ciena-afc-calculator-debug";
  prefix afc-calculator-debug;

  import ciena-common-version {
    prefix ciena-common-version;
  }
  import ciena-common-yang {
    prefix ciena-common;
  }

  organization
    "Ciena Corporation";
  contact
    "dicksonw";
  description
    "afc-calculator-debug";

  revision 2023-07-14 {
    description
      "Add yang version";
    ciena-common-version:string "1.0.0";
  }
  revision 2023-04-14 {
    description
      "Initial commit for debug RPC.";
    reference
      "None";
  }

  rpc set-debug-mode {
    description
      "set debug mode to skip certain checks; for testing/debugging only";
    input {
      leaf mode {
        type uint32;
        description
          "0-off 1-on";
      }
    }
    output {
      uses ciena-common:rpc-result-common;
      leaf out {
        type string {
          length "1..100";
        }
        description
          "response";
      }
    }
  }
}
