module ciena-6500r-logical-protection-group {
  namespace "urn:ciena:params:xml:ns:yang:ciena-6500r-logical-protection-group";
  prefix logical-protection-group;

  import ciena-common-yang {
    prefix yang;
  }
  import ciena-common-version {
    prefix ciena-common-version;
  }
  import ciena-6500r-fg {
    prefix pfg;
  }

  organization
    "Ciena Corporation";
  contact
    "Web URL: http://www.ciena.com/
     Postal:  7035 Ridge Road
              Hanover, Maryland 21076
              U.S.A.
     Phone:   +1 800-921-1144
     Fax:     +1 410-694-5750";
  description
    "This model is used to manage logical protection groups eg. Implementing an abstract higher order protection group with cascaded 1x2 hardware devices.";

  revision 2022-04-19 {
    description
      "Initial Revision";
    ciena-common-version:string "1.0.0";
    reference
      "RLS 3.0.0";
  }

  rpc get-device-switch-input-ports {
    input {
      leaf pfg-name {
        type leafref {
          path "/pfg:functional-group/pfg:name";
        }
        mandatory true;
        description
          "Name of the protection rx pfg";
      }
    }
    output {
      uses yang:rpc-result-common;
      list input-ports {
        leaf node-name {
          type string;
          description
            "Node name of the protection device switch input port";
        }
        leaf slot-name {
          type string;
          description
            "Slot name of the protection device switch input port";
        }
        leaf port-name {
          type string;
          description
            "Input port name of the protection device";
        }
      }
    }
  }
}
