module ciena-pro-rx-proxy {
  namespace "urn:ciena:params:xml:ns:yang:ciena-pro-rx-proxy";
  prefix rx-proxy;

  import ciena-common-version {
    prefix ciena-common-version;
  }

  import ciena-pro-types {
    prefix ciena-pro-types;
  }

  import ciena-pro-optical-types {
    prefix ciena-pro-optical-types;
  }

  organization
    "Ciena Corporation";
  contact
    "Web URL: http://www.ciena.com/
     Postal:  7035 Ridge Road
             Hanover, Maryland 21076
             U.S.A.
     Phone:   +1 800-921-1144
     Fax:     +1 410-694-5750";
  description
    "This module describes Ciena's receiver proxy data model.";

  revision 2020-11-04 {
    ciena-common-version:version "version" {
      ciena-common-version:string "1.2.0";
    }
    description
      "Add rx-acquisition-hold-off";
  }
  revision 2020-09-17 {
    ciena-common-version:version "version" {
      ciena-common-version:string "1.1.0";
    }
    description
      "Add ignore-rx-fault";
  }
  revision 2020-08-01 {
    ciena-common-version:version "version" {
      ciena-common-version:string "1.0.0";
    }
    description
      "Initial version";
  }

  grouping receiver {
    description
      "Receiver proxy parameters";
    leaf och-degrade {
      type boolean;
      description
        "OCH degrade";
    }

    leaf och-fault {
      type boolean;
      description
        "OCH fault";
    }

    leaf rx-faults {
      type enumeration {
        enum "All" {
          value 1;
          description
            "All RX faults are considered.";
        }
        enum "None" {
          value 2;
          description
            "None of RX faults are considered.";
        }
        enum "Degrade" {
          value 3;
          description
            "RX Degrade is considered.";
        }
        enum "Fail" {
          value 4;
          description
            "RX Failed is considered.";
        }
      }
    }

    leaf ignore-rx-fault {
      type boolean;
      default "false";
      description
        "Ignore rx faults";
    }

    leaf rx-acquisition-hold-off {
      type uint16;
      units "seconds";
      default "10";
      description
        "Indicates the acquisition hold-off time to be set on the Transponder. It specifies the hold-off time before the rx tries to hunt for a new tx signal lock after losing a lock.";
    }
  }

  grouping rx-proxy {
    leaf name {
      type ciena-pro-types:object-name;
      description
        "Receiver proxy object name";
    }

    leaf target-psd {
      type ciena-pro-optical-types:psd;
      description
        "Power Spectral Density";
    }

    uses receiver;
  }
}
