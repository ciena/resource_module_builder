module CIENA-PRO-SYSTEM-MIB {
  namespace "urn:ietf:params:xml:ns:yang:smiv2:CIENA-PRO-SYSTEM-MIB";
  prefix ciena-pro-system;

  import CIENA-PRO-TYPES-MIB {
    prefix ciena-pro;
  }
  import CIENA-SMI {
    prefix ciena-smi;
  }

  organization
    "Ciena Corporation";
  contact
    "Web: http://www.ciena.com
     Postal:   7035 Ridge Road
               Hanover, Maryland 21076
               U.S.A
     Phone:    +1 800-921-1144
     Fax:      +1 410-694-5750";
  description
    "MIB for managing system-wide services and functions on network devices.";

  revision 2021-06-11 {
    description
      "Added new parameters
       cienaProSystemStateNetworkId,
       cienaProSystemStateNetworkName,
       cienaProSystemStateSiteId,
       cienaProSystemStateSiteName,
       cienaProSystemStateGroupId,
       cienaProSystemStateGroupName,
       cienaProSystemStateMemberId";
  }
  revision 2020-10-01 {
    description
      "Initial Revision.";
  }

  container cienaProSystemState {
    leaf cienaProSystemStateHostName {
      type ciena-pro:DomainName;
      config false;
      description
        "The hostname of the device -- should be a single domain label, without the domain.";
    }
    leaf cienaProSystemStateLoginBanner {
      type binary {
        length "1..2542";
      }
      config false;
      description
        "The console login message displayed before the login prompt,
         i.e., before a user logs into the system.";
    }
    leaf cienaProSystemStateMotdBanner {
      type binary {
        length "1..512";
      }
      config false;
      description
        "The console message displayed after a user logs into the
         system.  They system may append additional standard
         information such as the current system date and time, uptime,
         last login timestamp, etc.";
    }
    leaf cienaProSystemCurrDateTime {
      type ciena-pro:DateTime;
      config false;
      description
        "The current system date and time.";
    }
    leaf cienaProSystemStateBootTime {
      type ciena-pro:TimeTicks64;
      config false;
      description
        "This timestamp indicates the time that the system was last
         restarted.  The value is the timestamp in nanoseconds relative
         to the Unix Epoch (Jan 1, 1970 00:00:00 UTC).";
    }
    leaf cienaProSystemStateNetworkId {
      type uint32;
      config false;
      description
        "An integer to uniquely identify the sub-network domain in which this
         network element is managed.";
    }
    leaf cienaProSystemStateNetworkName {
      type ciena-pro:DisplayString64;
      config false;
      description
        "A name for the sub-network domain.";
    }
    leaf cienaProSystemStateSiteId {
      type uint32;
      config false;
      description
        "An integer to uniquely identify the site where this network element
         is located. This is used to help group network elements together.
         All equipment in a common site should share the same site identifier. ";
    }
    leaf cienaProSystemStateSiteName {
      type ciena-pro:DisplayString64;
      config false;
      description
        "The name for the site where the network element is located. ";
    }
    leaf cienaProSystemStateGroupId {
      type uint32;
      config false;
      description
        "An integer to uniquely identify a group of network elements within a site.";
    }
    leaf cienaProSystemStateGroupName {
      type ciena-pro:DisplayString64;
      config false;
      description
        "A name for the group of network elements.";
    }
    leaf cienaProSystemStateMemberId {
      type uint32;
      config false;
      description
        "An integer to uniquely identify a unique network element within a group.";
    }
  }
}
