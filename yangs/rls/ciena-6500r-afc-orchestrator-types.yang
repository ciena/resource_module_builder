module ciena-6500r-afc-orchestrator-types {
  yang-version 1.1;
  namespace "urn:ciena:params:xml:ns:yang:ciena-6500r-afc-orchestrator-types";
  prefix afc-orchestrator-types;

  import ciena-common-version {
    prefix ciena-common-version;
  }
  import ciena-common-yang {
    prefix ciena-common-yang;
  }
  import ciena-pro-optical-types {
    prefix ciena-pro-optical-types;
  }
  import ciena-pro-amp {
    prefix pro-amp;
  }
  import ciena-pro-types {
    prefix pro-types;
  }
  import ciena-6500r-ramans {
    prefix ramans;
  }
  import ciena-pro-fiber-types {
    prefix fiber-types;
  }
  import ietf-yang-types {
    prefix yang-types;
  }
  import ciena-6500r-ports {
    prefix ciena-6500r-ports;
  }
  import ciena-pro-link {
    prefix ciena-pro-link;
  }

  organization
    "Ciena Corporation";
  contact
    "Web URL: http://www.ciena.com
     Postal: Ciena India Pvt. Ltd.
     Sector 32, Plot 14,
     Gurgaon 122001,
     Haryana, India";
  description
    "Auto fiber characterization orchestrator(AFCO) is an application
     which measures fiber non-linear parameters.";

  revision 2023-06-07 {
    description
      "Add unmeasurable status enum to auto fiber characterization orchestrator calculator status.";
    ciena-common-version:string "1.5.13";
  }
  revision 2023-03-27 {
    description
      "Add encryption tags to all elements of afc two peak measurements grouping.";
    ciena-common-version:string "1.5.12";
  }
  revision 2023-03-02 {
    description
      "Add max-target-power in save preAfc data of AMP.";
    ciena-common-version:string "1.5.11";
  }
  revision 2023-02-17 {
    description
      "Add afco-action enum invoke-gamma,set-voa and measure-voa.";
    ciena-common-version:string "1.5.10";
  }
  revision 2023-02-16 {
    description
      "Updated type of Voa in two-peak results to List.";
    ciena-common-version:string "1.5.10";
  }
  revision 2023-02-16 {
    description
      "Add OSC Wavelength in downstream fiber data.";
    ciena-common-version:string "1.5.9";
  }
  revision 2023-02-06 {
    description
      "Added AFC Mode definition.";
    ciena-common-version:string "1.5.8";
  }
  revision 2023-01-30 {
    description
      "Add fiber length source in downstream fiber data.";
    ciena-common-version:string "1.5.7";
  }
  revision 2023-01-11 {
    description
      "Add WSS attenuation in save pre AFC data.";
    ciena-common-version:string "1.5.6";
  }
  revision 2022-11-17 {
    description
      "Updating set-pre-amp enum of afco-action.";
    ciena-common-version:string "1.5.5";
  }
  revision 2022-10-15 {
    description
      "Add afco-action enum for 2 peak calibration and measurements.";
    ciena-common-version:string "1.5.4";
  }
  revision 2022-10-10 {
    description
      "Add type in pre afc data amp,
       add stage-amp, opm, pwrmon grouping for pre afc data.";
    ciena-common-version:string "1.5.3";
  }
  revision 2022-09-02 {
    description
      "Add afco-action enum for computing effective gamma offset using SRS measurements.";
    ciena-common-version:string "1.5.2";
  }
  revision 2022-08-30 {
    description
      "Add grouping for two peak measurements type and
       add target-gain-tilt amp data.";
    ciena-common-version:string "1.5.1";
  }
  revision 2022-07-27 {
    description
      "Add boundary and fiber data type for afc-calculator";
    ciena-common-version:string "1.5.0";
  }
  revision 2022-05-23 {
    description
      "Add not_triggered status enum to auto fiber characterization orchestrator status.";
    ciena-common-version:string "1.4.7";
  }
  revision 2022-04-12 {
    description
      "Add auto fiber characterization calculator status enum and
       add aborted status enum to auto fiber characterization orchestrator status.";
    ciena-common-version:string "1.4.6";
  }
  revision 2022-03-31 {
    description
      "Change source of forced-shutoff to ciena-pro-types.";
    ciena-common-version:string "1.4.5";
  }
  revision 2022-01-27 {
    description
      "Remove Raman-bootstrap-mode and bootstrap-time for RAMAN.";
    ciena-common-version:string "1.4.4";
  }
  revision 2022-01-15 {
    description
      "Introduced Target-gain for Amp in preAfcData.";
    ciena-common-version:string "1.4.3";
  }
  revision 2021-12-20 {
    description
      "Remove embedded definition for amp-mode & forced-shutoff and use imported definition from facility-manager & common-models";
    ciena-common-version:string "1.4.2";
  }
  revision 2021-12-16 {
    description
      "Remove embedded defination for gain-mode and use imported defination from facility-manager & common-models";
    ciena-common-version:string "1.4.1";
  }
  revision 2021-12-07 {
    description
      "Gain-mode/Raman-bootstrap-mode/bootstrap-time introduced for RAMAN.";
    ciena-common-version:string "1.4.0";
  }
  revision 2021-12-03 {
    description
      "Removed admin-state of VOA and added forced-shutoff as enum for Raman.";
    ciena-common-version:string "1.3.0";
  }
  revision 2021-11-19 {
    description
      "Removed some afco-fsm-state(local-fail and restore) and afco-actions(nop).";
    ciena-common-version:string "1.2.0";
  }
  revision 2021-11-15 {
    description
      "Dgff attenuation data is introduced and removed admin-state, added new forced-shutoff in Amp list.";
    ciena-common-version:string "1.1.0";
  }
  revision 2021-09-27 {
    description
      "6500r-series Release 2.5
           Initial version.";
    ciena-common-version:string "1.0.0";
  }

  grouping afco-data-voa {
    leaf object-id {
      type instance-identifier;
      description
        "Identifies objects with name of VOA Facility";
    }
    leaf target-loss {
      type ciena-pro-optical-types:loss-dB-1-precision;
      default "0";
      description
        "Target Loss in dB.";
    }
    leaf band-type {
      type string;
      description
        "Identifies band type of VOA facility";
    }
  }

  grouping afco-data-raman {
    leaf object-id {
      type instance-identifier;
      description
        "Identifies objects with name of RAMAN facility";
    }
    uses ramans:forced-shutoff;
    uses ramans:gain-mode;
    leaf band-type {
      type string;
      description
        "Identifies band type of RAMAN facility";
    }
  }

  grouping afco-data-dgff {
    leaf object-id {
      type instance-identifier;
      description
        "Identifies objects with name of DGFF facility";
    }
    leaf attenuation {
      description
        "DGFF WSS attenuation binary data";
      type binary {
        length "1..2000";
      }
    }
    leaf band-type {
      type string;
      description
        "Identifies band type of DGFF facility";
    }
  }

  grouping afco-data-wss {
    leaf object-id {
      type instance-identifier;
      description
        "Identifies objects with name of wss device";
    }
    leaf switch-selector {
      description
        "Switch selector binary data";
      type binary {
        length "1..2000";
      }
    }
    leaf attenuation {
      description
        "Attenuation binary data";
      type binary {
        length "1..2000";
      }
    }
    leaf band-type {
      type string;
      description
        "Identifies band type of WSS facility";
    }
  }

  grouping afco-data-amp {
    leaf object-id {
      type instance-identifier;
      description
        "Identifies objects with name of Amplifier";
    }
    uses pro-amp:amp-mode;
    uses pro-amp:gain-mode;
    leaf target-power {
      type decimal64 {
        fraction-digits 1;
      }
      units "dBm";
      description
        "Target Total Power in dBm.";
    }
    uses pro-types:forced-shutoff;
    leaf target-gain {
      type ciena-pro-optical-types:gain-dB-1-precision;
      description
        "Target Gain in dB.";
    }
    leaf target-gain-tilt {
      type decimal64 {
        fraction-digits 1;
      }
      units "dB";
      config false;
      description
        "Target gain tilt in dB.";
    }
    leaf band-type {
      type string;
      description
        "Identifies band type of AMP facility";
    }
    leaf type {
      type string;
      description
        "Type of Amp.";
    }
    leaf max-target-power {
      type decimal64 {
        fraction-digits 1;
      }
      units "dBm";
      description
        "Max Target Power in dBm.";
    }
  }

  grouping afco-data-boundary {
    leaf object-id {
      type instance-identifier;
      description
        "Identifies objects with name of boundary facility";
    }
    leaf band-type {
      type string;
      description
        "Identifies band type of Boundary facility";
    }
  }

  grouping afco-data-stage-amp {
    leaf object-id {
      type instance-identifier;
      description
        "Identifies object with name of Amplifier";
    }
    leaf band-type {
      type string;
      description
        "Identifies band type of facility";
    }
  }

  grouping afco-data-opm {
    leaf object-id {
      type instance-identifier;
      description
        "Identifies object with name of the opm";
    }
    leaf min-freq {
      type ciena-pro-optical-types:frequency;
      config false;
      description
        "Minimum frequency of the opm.";
    }
    leaf max-freq {
      type ciena-pro-optical-types:frequency;
      config false;
      description
        "Maximum frequency of the opm.";
    }
    leaf slice-width {
      type ciena-pro-optical-types:frequency;
      units "GHz";
      config false;
      description
        "The offset between the center frequencies of neighboring measurement slices.";
    }
    leaf band-type {
      type string;
      description
        "Identifies band type of Boundary facility";
    }
    leaf direction {
      type leafref {
        path "/ciena-6500r-ports:port/ciena-6500r-ports:port-direction";
      }
      description
        "Direction of the opm(rx/ tx)";
    }
  }

  grouping afco-data-pwrmon {
    leaf object-id {
      type instance-identifier;
      description
        "Identifies object with name of pwrmon";
    }
    leaf center-frequency {
      type ciena-pro-optical-types:frequency;
      config false;
      description
        "Center frequency";
    }
    leaf spectral-width {
      type ciena-pro-optical-types:frequency;
      config false;
      description
        "Spectral width.";
    }
    leaf band-type {
      type string;
      description
        "Identifies band type of facility";
    }
    leaf direction {
      type leafref {
        path "/ciena-6500r-ports:port/ciena-6500r-ports:port-direction";
      }
      description
        "Direction of the pwrmon(rx/ tx)";
    }
  }

  grouping afco-fiber-attributes {
    leaf name {
      type string;
      description
        "Link name";
    }
    leaf from {
      type instance-identifier;
      description
        "From port identifier";
    }
    leaf to {
      type instance-identifier;
      description
        "To port identifier";
    }
    leaf fiber-alpha {
      type decimal64 {
        fraction-digits 2;
      }
      description
        "Alpha value of the fiber.";
    }
    leaf fiber-type {
      type leafref {
        path "/fiber-types:fiber-type/fiber-types:fiber-type";
      }
      default "unknown";
    }
    leaf fiber-length {
      type uint64;
      units "m";
      description
        "The fiber length derived by the system in meters";
    }
    leaf fiber-length-source {
      type ciena-pro-link:length-source-type;
      description
        "Source used to derive fiber-length";
    }
    leaf measured-physical-loss {
      type ciena-pro-optical-types:loss-dB-1-precision;
      description
        "The physical loss of the link derived from power measurement";
    }
    leaf input-patch-panel-loss {
      type ciena-pro-optical-types:loss-dB-1-precision;
      description
        "The patch panel loss at the input of the fiber.";
    }
    leaf output-patch-panel-loss {
      type ciena-pro-optical-types:loss-dB-1-precision;
      description
        "The patch panel loss at the output of the fiber.";
    }
    leaf osc-wavelength {
      type decimal64 {
        fraction-digits 2;
      }
      units "nm";
      description
        "OSC wavelength in nanometers";
    }
  }

  grouping afco-two-peak-measurements-data {
    leaf target-power {
      ciena-common-yang:encrypt "leaf-2";
      ciena-common-yang:encrypt-path "/ciena-6500r-afc-orchestrator-types/afco-two-peak-measurements-data";
      type decimal64 {
        fraction-digits 1;
      }
      units "dBm";
      config false;
      description
        "Target power set at the amp.";
    }
    leaf leaf-2 {
      type string {
        ciena-common-yang:stringptr "true";
      }
      ciena-common-yang:decrypt "target-power";
      ciena-common-yang:decrypt-path "/ciena-6500r-afc-orchestrator-types/afco-two-peak-measurements-data";
      config false;
    }
    list amp-measurements {
      ciena-common-yang:encrypt "list-1";
      ciena-common-yang:encrypt-path "/ciena-6500r-afc-orchestrator-types/afco-two-peak-measurements-data";
      key "name";
      description
        "Two peak amp measurements data.";
      config false;
      leaf name {
        ciena-common-yang:encrypt "leaf-1";
        ciena-common-yang:encrypt-path "/ciena-6500r-afc-orchestrator-types/afco-two-peak-measurements-data/list-1";
        type string;
        config false;
        description
          "Amp name";
      }
      leaf in-current-power {
        ciena-common-yang:encrypt "leaf-2";
        ciena-common-yang:encrypt-path "/ciena-6500r-afc-orchestrator-types/afco-two-peak-measurements-data/list-1";
        type decimal64 {
          fraction-digits 1;
        }
        units "dBm";
        config false;
        description
          "Input power to the AMP in dBm.";
      }
      leaf out-current-power {
        ciena-common-yang:encrypt "leaf-3";
        ciena-common-yang:encrypt-path "/ciena-6500r-afc-orchestrator-types/afco-two-peak-measurements-data/list-1";
        type decimal64 {
          fraction-digits 1;
        }
        units "dBm";
        config false;
        description
          "Output power from the AMP in dBm.";
      }
      leaf gain-tilt {
        ciena-common-yang:encrypt "leaf-4";
        ciena-common-yang:encrypt-path "/ciena-6500r-afc-orchestrator-types/afco-two-peak-measurements-data/list-1";
        type decimal64 {
          fraction-digits 1;
        }
        units "dB";
        config false;
        description
          "Measured Gain tilt in dB.";
      }
      leaf gain {
        ciena-common-yang:encrypt "leaf-5";
        ciena-common-yang:encrypt-path "/ciena-6500r-afc-orchestrator-types/afco-two-peak-measurements-data/list-1";
        type ciena-pro-optical-types:gain-dB-1-precision;
        config false;
        description
          "Measured Gain in dB.";
      }
      leaf amp-mode {
        ciena-common-yang:encrypt "amp-mode";
        ciena-common-yang:encrypt-path "/ciena-6500r-afc-orchestrator-types/afco-two-peak-measurements-data/list-1";
        type enumeration {
          enum power {
            value 1;
            description
              "Control to a Power Mode.";
          }
          enum gain {
            value 2;
            description
              "Control to a Gain Mode. (Default) ";
          }
          enum gainclamp {
            value 3;
            description
              "Control to a Gainclamp Mode.";
          }
          enum gain-tilt {
            value 4;
            description
              "Control seeks to achieve the specified target-gain-tilt.";
          }
          enum ase {
            value 5;
            description
              "Control to an ASE Mode to check line out fiber connectivity and APR/ORL detection.
               Amp output power is limited to the provisioned apr-power-level of the amp's config data.";
          }
        }
        default "gain";
        description
          "Control Mode of the AMP.";
      }
      leaf gain-mode {
        ciena-common-yang:encrypt "gain-mode";
        ciena-common-yang:encrypt-path "/ciena-6500r-afc-orchestrator-types/afco-two-peak-measurements-data/list-1";
        type enumeration {
          enum low {
            value 1;
            description
              "Gain Mode is Low.";
          }
          enum high {
            value 2;
            description
              "Gain Mode is High.";
          }
        }
        default "high";
        description
          "Gain Mode of the AMP.";
      }
    }
    list list-1 {
      ciena-common-yang:decrypt "amp-measurements";
      ciena-common-yang:decrypt-path "/ciena-6500r-afc-orchestrator-types/afco-two-peak-measurements-data";
      key "leaf-1";
      config false;
      leaf leaf-1 {
        type string {
          ciena-common-yang:stringptr "true";
        }
        ciena-common-yang:decrypt "name";
        ciena-common-yang:decrypt-path "/ciena-6500r-afc-orchestrator-types/afco-two-peak-measurements-data/amp-measurements";
        config false;
      }
      leaf leaf-2 {
        type string {
          ciena-common-yang:stringptr "true";
        }
        ciena-common-yang:decrypt "in-current-power";
        ciena-common-yang:decrypt-path "/ciena-6500r-afc-orchestrator-types/afco-two-peak-measurements-data/amp-measurements";
        config false;
      }
      leaf leaf-3 {
        type string {
          ciena-common-yang:stringptr "true";
        }
        ciena-common-yang:decrypt "out-current-power";
        ciena-common-yang:decrypt-path "/ciena-6500r-afc-orchestrator-types/afco-two-peak-measurements-data/amp-measurements";
        config false;
      }
      leaf leaf-4 {
        type string {
          ciena-common-yang:stringptr "true";
        }
        ciena-common-yang:decrypt "gain-tilt";
        ciena-common-yang:decrypt-path "/ciena-6500r-afc-orchestrator-types/afco-two-peak-measurements-data/amp-measurements";
        config false;
      }
      leaf leaf-5 {
        type string {
          ciena-common-yang:stringptr "true";
        }
        ciena-common-yang:decrypt "gain";
        ciena-common-yang:decrypt-path "/ciena-6500r-afc-orchestrator-types/afco-two-peak-measurements-data/amp-measurements";
        config false;
      }
      leaf amp-mode {
        type string {
          ciena-common-yang:stringptr "true";
        }
        ciena-common-yang:decrypt "amp-mode";
        ciena-common-yang:decrypt-path "/ciena-6500r-afc-orchestrator-types/afco-two-peak-measurements-data/amp-measurements";
      }
      leaf gain-mode {
        type string {
          ciena-common-yang:stringptr "true";
        }
        ciena-common-yang:decrypt "gain-mode";
        ciena-common-yang:decrypt-path "/ciena-6500r-afc-orchestrator-types/afco-two-peak-measurements-data/amp-measurements";
      }
    }
    list voa {
      ciena-common-yang:encrypt "list-2";
      ciena-common-yang:encrypt-path "/ciena-6500r-afc-orchestrator-types/afco-two-peak-measurements-data";
      key "name";
      description
        "Two peak voa measurements data.";
      config false;
      leaf name {
        ciena-common-yang:encrypt "leaf-1";
        ciena-common-yang:encrypt-path "/ciena-6500r-afc-orchestrator-types/afco-two-peak-measurements-data/list-2";
        type string;
        config false;
        description
          "Voa name";
      }
      leaf target-loss {
        ciena-common-yang:encrypt "leaf-2";
        ciena-common-yang:encrypt-path "/ciena-6500r-afc-orchestrator-types/afco-two-peak-measurements-data/list-2";
        type ciena-pro-optical-types:loss-dB-1-precision;
        config false;
        description
          "Target Loss in dB.";
      }
      leaf current-power {
        ciena-common-yang:encrypt "leaf-3";
        ciena-common-yang:encrypt-path "/ciena-6500r-afc-orchestrator-types/afco-two-peak-measurements-data/list-2";
        type decimal64 {
          fraction-digits 1;
        }
        units "dBm";
        config false;
        description
          "Measured current power at the VOA in dBm";
      }
    }
    list list-2 {
      ciena-common-yang:decrypt "voa";
      ciena-common-yang:decrypt-path "/ciena-6500r-afc-orchestrator-types/afco-two-peak-measurements-data";
      key "leaf-1";
      config false;
      leaf leaf-1 {
        type string {
          ciena-common-yang:stringptr "true";
        }
        ciena-common-yang:decrypt "name";
        ciena-common-yang:decrypt-path "/ciena-6500r-afc-orchestrator-types/afco-two-peak-measurements-data/voa";
        config false;
      }
      leaf leaf-2 {
        type string {
          ciena-common-yang:stringptr "true";
        }
        ciena-common-yang:decrypt "target-loss";
        ciena-common-yang:decrypt-path "/ciena-6500r-afc-orchestrator-types/afco-two-peak-measurements-data/voa";
        config false;
      }
      leaf leaf-3 {
        type string {
          ciena-common-yang:stringptr "true";
        }
        ciena-common-yang:decrypt "current-power";
        ciena-common-yang:decrypt-path "/ciena-6500r-afc-orchestrator-types/afco-two-peak-measurements-data/voa";
        config false;
      }
    }
    list opms {
      ciena-common-yang:encrypt "list-3";
      ciena-common-yang:encrypt-path "/ciena-6500r-afc-orchestrator-types/afco-two-peak-measurements-data";
      key "name";
      description
        "Two peak opms measurements data.";
      config false;
      leaf name {
        ciena-common-yang:encrypt "leaf-1";
        ciena-common-yang:encrypt-path "/ciena-6500r-afc-orchestrator-types/afco-two-peak-measurements-data/list-3";
        type string;
        config false;
        description
          "Opm name";
      }
      leaf-list power-slice {
        ciena-common-yang:encrypt "leaf-list-1";
        ciena-common-yang:encrypt-path "/ciena-6500r-afc-orchestrator-types/afco-two-peak-measurements-data/list-3";
        type ciena-pro-optical-types:power {
          range "-75..75.00";
        }
        units "dBm";
        config false;
        description
          "Power measured in an OPM slice in dBm.";
      }
    }
    list list-3 {
      ciena-common-yang:decrypt "opms";
      ciena-common-yang:decrypt-path "/ciena-6500r-afc-orchestrator-types/afco-two-peak-measurements-data";
      key "leaf-1";
      config false;
      leaf leaf-1 {
        type string {
          ciena-common-yang:stringptr "true";
        }
        ciena-common-yang:decrypt "name";
        ciena-common-yang:decrypt-path "/ciena-6500r-afc-orchestrator-types/afco-two-peak-measurements-data/opms";
        config false;
      }
      leaf-list leaf-list-1 {
        type string {
          ciena-common-yang:stringptr "true";
        }
        ciena-common-yang:decrypt "power-slice";
        ciena-common-yang:decrypt-path "/ciena-6500r-afc-orchestrator-types/afco-two-peak-measurements-data/opms";
        config false;
      }
    }
    list optmons {
      ciena-common-yang:encrypt "list-4";
      ciena-common-yang:encrypt-path "/ciena-6500r-afc-orchestrator-types/afco-two-peak-measurements-data";
      key "name";
      description
        "Two peak optmons measurements data.";
      config false;
      leaf name {
        ciena-common-yang:encrypt "leaf-1";
        ciena-common-yang:encrypt-path "/ciena-6500r-afc-orchestrator-types/afco-two-peak-measurements-data/list-4";
        type string;
        config false;
        description
          "Optmon name";
      }
      leaf current-power {
        ciena-common-yang:encrypt "leaf-2";
        ciena-common-yang:encrypt-path "/ciena-6500r-afc-orchestrator-types/afco-two-peak-measurements-data/list-4";
        type decimal64 {
          fraction-digits 1;
        }
        units "dBm";
        config false;
        description
          "Measured current power for the optmon in dBm";
      }
    }
    list list-4 {
      ciena-common-yang:decrypt "optmons";
      ciena-common-yang:decrypt-path "/ciena-6500r-afc-orchestrator-types/afco-two-peak-measurements-data";
      key "leaf-1";
      config false;
      leaf leaf-1 {
        type string {
          ciena-common-yang:stringptr "true";
        }
        ciena-common-yang:decrypt "name";
        ciena-common-yang:decrypt-path "/ciena-6500r-afc-orchestrator-types/afco-two-peak-measurements-data/optmons";
        config false;
      }
      leaf leaf-2 {
        type string {
          ciena-common-yang:stringptr "true";
        }
        ciena-common-yang:decrypt "current-power";
        ciena-common-yang:decrypt-path "/ciena-6500r-afc-orchestrator-types/afco-two-peak-measurements-data/optmons";
        config false;
      }
    }
    leaf timestamp {
      ciena-common-yang:encrypt "leaf-3";
      ciena-common-yang:encrypt-path "/ciena-6500r-afc-orchestrator-types/afco-two-peak-measurements-data";
      type yang-types:date-and-time;
      config false;
      description
        "Timestamp of two peak measurement.";
    }
    leaf leaf-3 {
      type string {
        ciena-common-yang:stringptr "true";
      }
      ciena-common-yang:decrypt "timestamp";
      ciena-common-yang:decrypt-path "/ciena-6500r-afc-orchestrator-types/afco-two-peak-measurements-data";
      config false;
    }
  }

  grouping afco-two-peak-data-amp {
    leaf name {
      ciena-common-yang:encrypt "leaf-1";
      ciena-common-yang:encrypt-path "/ciena-6500r-afc-orchestrator-types/afco-two-peak-data-amp";
      type string;
      config false;
      description
        "Amp name";
    }
    leaf leaf-1 {
      type string {
        ciena-common-yang:stringptr "true";
      }
      ciena-common-yang:decrypt "name";
      ciena-common-yang:decrypt-path "/ciena-6500r-afc-orchestrator-types/afco-two-peak-data-amp";
      config false;
    }
    leaf in-current-power {
      ciena-common-yang:encrypt "leaf-2";
      ciena-common-yang:encrypt-path "/ciena-6500r-afc-orchestrator-types/afco-two-peak-data-amp";
      type decimal64 {
        fraction-digits 1;
      }
      units "dBm";
      config false;
      description
        "Input power to the AMP in dBm.";
    }
    leaf leaf-2 {
      type string {
        ciena-common-yang:stringptr "true";
      }
      ciena-common-yang:decrypt "in-current-power";
      ciena-common-yang:decrypt-path "/ciena-6500r-afc-orchestrator-types/afco-two-peak-data-amp";
      config false;
    }
    leaf out-current-power {
      ciena-common-yang:encrypt "leaf-3";
      ciena-common-yang:encrypt-path "/ciena-6500r-afc-orchestrator-types/afco-two-peak-data-amp";
      type decimal64 {
        fraction-digits 1;
      }
      units "dBm";
      config false;
      description
        "Output power from the AMP in dBm.";
    }
    leaf leaf-3 {
      type string {
        ciena-common-yang:stringptr "true";
      }
      ciena-common-yang:decrypt "out-current-power";
      ciena-common-yang:decrypt-path "/ciena-6500r-afc-orchestrator-types/afco-two-peak-data-amp";
      config false;
    }
    leaf gain-tilt {
      ciena-common-yang:encrypt "leaf-4";
      ciena-common-yang:encrypt-path "/ciena-6500r-afc-orchestrator-types/afco-two-peak-data-amp";
      type decimal64 {
        fraction-digits 1;
      }
      units "dB";
      config false;
      description
        "Measured Gain tilt in dB.";
    }
    leaf leaf-4 {
      type string {
        ciena-common-yang:stringptr "true";
      }
      ciena-common-yang:decrypt "gain-tilt";
      ciena-common-yang:decrypt-path "/ciena-6500r-afc-orchestrator-types/afco-two-peak-data-amp";
      config false;
    }
    leaf gain {
      ciena-common-yang:encrypt "leaf-5";
      ciena-common-yang:encrypt-path "/ciena-6500r-afc-orchestrator-types/afco-two-peak-data-amp";
      type ciena-pro-optical-types:gain-dB-1-precision;
      config false;
      description
        "Measured Gain in dB.";
    }
    leaf leaf-5 {
      type string {
        ciena-common-yang:stringptr "true";
      }
      ciena-common-yang:decrypt "gain";
      ciena-common-yang:decrypt-path "/ciena-6500r-afc-orchestrator-types/afco-two-peak-data-amp";
      config false;
    }
    uses pro-amp:amp-mode;
    uses pro-amp:gain-mode;
  }

  grouping afco-two-peak-data-voa {
    leaf name {
      ciena-common-yang:encrypt "leaf-1";
      ciena-common-yang:encrypt-path "/ciena-6500r-afc-orchestrator-types/afco-two-peak-data-voa";
      type string;
      config false;
      description
        "Voa name";
    }
    leaf leaf-1 {
      type string {
        ciena-common-yang:stringptr "true";
      }
      ciena-common-yang:decrypt "name";
      ciena-common-yang:decrypt-path "/ciena-6500r-afc-orchestrator-types/afco-two-peak-data-voa";
      config false;
    }
    leaf target-loss {
      ciena-common-yang:encrypt "leaf-2";
      ciena-common-yang:encrypt-path "/ciena-6500r-afc-orchestrator-types/afco-two-peak-data-voa";
      type ciena-pro-optical-types:loss-dB-1-precision;
      config false;
      description
        "Target Loss in dB.";
    }
    leaf leaf-2 {
      type string {
        ciena-common-yang:stringptr "true";
      }
      ciena-common-yang:decrypt "target-loss";
      ciena-common-yang:decrypt-path "/ciena-6500r-afc-orchestrator-types/afco-two-peak-data-voa";
      config false;
    }
    leaf current-power {
      ciena-common-yang:encrypt "leaf-3";
      ciena-common-yang:encrypt-path "/ciena-6500r-afc-orchestrator-types/afco-two-peak-data-voa";
      type decimal64 {
        fraction-digits 1;
      }
      units "dBm";
      config false;
      description
        "Measured current power at the VOA in dBm";
    }
    leaf leaf-3 {
      type string {
        ciena-common-yang:stringptr "true";
      }
      ciena-common-yang:decrypt "current-power";
      ciena-common-yang:decrypt-path "/ciena-6500r-afc-orchestrator-types/afco-two-peak-data-voa";
      config false;
    }
  }

  grouping afco-two-peak-data-opm {
    leaf name {
      ciena-common-yang:encrypt "leaf-1";
      ciena-common-yang:encrypt-path "/ciena-6500r-afc-orchestrator-types/afco-two-peak-data-opm";
      type string;
      config false;
      description
        "Opm name";
    }
    leaf leaf-1 {
      type string {
        ciena-common-yang:stringptr "true";
      }
      ciena-common-yang:decrypt "name";
      ciena-common-yang:decrypt-path "/ciena-6500r-afc-orchestrator-types/afco-two-peak-data-opm";
      config false;
    }
    leaf-list power-slice {
      ciena-common-yang:encrypt "leaf-list-1";
      ciena-common-yang:encrypt-path "/ciena-6500r-afc-orchestrator-types/afco-two-peak-data-opm";
      type ciena-pro-optical-types:power {
        range "-75..75.00";
      }
      units "dBm";
      config false;
      description
        "Power measured in an OPM slice in dBm.";
    }
    leaf-list leaf-list-1 {
      type string {
        ciena-common-yang:stringptr "true";
      }
      ciena-common-yang:decrypt "power-slice";
      ciena-common-yang:decrypt-path "/ciena-6500r-afc-orchestrator-types/afco-two-peak-data-opm";
      config false;
    }
  }

  grouping afco-two-peak-data-optmon {
    leaf name {
      ciena-common-yang:encrypt "leaf-1";
      ciena-common-yang:encrypt-path "/ciena-6500r-afc-orchestrator-types/afco-two-peak-data-optmon";
      type string;
      config false;
      description
        "Optmon name";
    }
    leaf leaf-1 {
      type string {
        ciena-common-yang:stringptr "true";
      }
      ciena-common-yang:decrypt "name";
      ciena-common-yang:decrypt-path "/ciena-6500r-afc-orchestrator-types/afco-two-peak-data-optmon";
      config false;
    }
    leaf current-power {
      ciena-common-yang:encrypt "leaf-2";
      ciena-common-yang:encrypt-path "/ciena-6500r-afc-orchestrator-types/afco-two-peak-data-optmon";
      type decimal64 {
        fraction-digits 1;
      }
      units "dBm";
      config false;
      description
        "Measured current power for the optmon in dBm";
    }
    leaf leaf-2 {
      type string {
        ciena-common-yang:stringptr "true";
      }
      ciena-common-yang:decrypt "current-power";
      ciena-common-yang:decrypt-path "/ciena-6500r-afc-orchestrator-types/afco-two-peak-data-optmon";
      config false;
    }
  }

  typedef afco-fsm-state {
    type enumeration {
      enum init {
        description
          "Initial state of automatic fiber characterization orchestrator.";
      }
      enum wait-precondition {
        description
          "Wait for all device controllers to be in afc ready state (this ensures that baseline was taken) Save pre-AFC data when all DCs for this shelf are AFC ready.";
      }
      enum local-ready {
        description
          "Automatic fiber characterization is locally ready when all the external and internal dependencies are met.";
      }
      enum in-progress {
        description
          "Automatic fiber characterization performing its actions from the action table.";
      }
      enum local-complete {
        description
          "Automatic fiber characterization is completed.";
      }
      enum local-restore {
        description
          "Automatic fiber characterization is restore locally";
      }
      enum section-afc-completed {
        description
          "Automatic fiber characterization completed.";
      }
    }
  }

  typedef afco-mode {
    type enumeration {
      enum mode1 {
        description
          "AFC Mode 1 - Effective Gamma and Effective Dispersion";
      }
      enum mode2 {
        description
          "AFC Mode 2 - Effective Gamma";
      }
    }
  }

  typedef afco-actions {
    type enumeration {
      enum mux-block {
        description
          "Action to block all channels on Mux RLA.";
      }
      enum line-amp-block {
        description
          "Action to block line AMP and shut down all L-band AMP.";
      }
      enum measure-osc {
        description
          "Action to measure OSC Pwr at the end of each span after setting 23dBm output power or after block";
      }
      enum mux-open {
        description
          "Action to open 1000GHz for a reference freq on Mux RLA.";
      }
      enum line-amp-set {
        description
          "Action to set EDFA to have 23dBm output power.";
      }
      enum compute-gamma {
        description
          "Action to compute effective gamma offset using SRS measurements.";
      }
      enum set-algo-object {
        description
          "Action to set algo  object on AMP node on 2 peak measurements.";
      }
      enum create-channel-set-high-pwr-calibr {
        description
          "Action to create channel and set high power on MUX node on 2 peak calibrations.";
      }
      enum create-channel-set-high-pwr-measure {
        description
          "Action to create channel and set high power on MUX node on 2 peak measurements.";
      }
      enum invoke-calc-create-channel-set-high-pwr-measure {
        description
          "Action to invoke calc,create channel and set high power on MUX node on 2 peak measurements.";
      }
      enum set-low-pwr {
        description
          "Action to set low power on 2 peak measurements.";
      }
      enum set-low-pwr-reset {
        description
          "Action to set low power and reset index on 2 peak measurements.";
      }
      enum set-high-pwr {
        description
          "Action to set high power on 2 peak measurements.";
      }
      enum set-low-pwr-measure {
        description
          "Action to set low power and measure on 2 peak measurements.";
      }
      enum set-high-pwr-measure {
        description
          "Action to set high power and measure on 2 peak measurements.";
      }
      enum set-low-pwr-measure-reset {
        description
          "Action to reset index,set low power and measure on 2 peak measurements.";
      }
      enum set-high-pwr-measure-reset {
        description
          "Action to reset index,set high power and measure on 2 peak measurements.";
      }
      enum set-preamp-demux {
        description
          "Action to set preAmp on DEMUX on 2 peak measurements.";
      }
      enum read-depth0-set-low-pwr {
        description
          "Action to read depth0 and set low power on 2 peak measurements.";
      }
      enum compute-depth0 {
        description
          "Action to compute depth0 on DEMUX on 2 peak measurements.";
      }
      enum read-depth0 {
        description
          "Action to read depth0 on 2 peak measurements.";
      }
      enum reset-demux {
        description
          "Action to reset index on DEMUX on 2 peak measurements.";
      }
      enum two-peak-measure-amp {
        description
          "Action to measure 2 peak measurements on AMP node.";
      }
      enum two-peak-measure-mux-demux {
        description
          "Action to measure 2 peak measurements on MUX/DEMUX node.";
      }
      enum invoke-calc-set-low-pwr {
        description
          "Action to invoke calculator and set low power on 2 peak measurements.";
      }
      enum invoke-calc {
        description
          "Action to invoke calculator on 2 peak measurements.";
      }
      enum no-operation {
        description
          "No operations on SRS and 2 peak measurements.";
      }
      enum invoke-gamma {
        description
          "Action to invoke calculator on only SRS measurements.";
      }
      enum set-voa {
        description
          "Action to set voa, before start 2 peak.";
      }
      enum measure-voa {
        description
          "Action to measure voa's current-power.";
      }
    }
  }

  typedef afco-status {
    type enumeration {
      enum failed {
        description
          "Automatic fiber characterization orchestrator failed.";
      }
      enum succeed {
        description
          "Automatic fiber characterization orchestrator succeeded.";
      }
      enum unknown {
        description
          "Automatic fiber characterization orchestrator unknown.";
      }
      enum aborted {
        description
          "Automatic fiber characterization orchestrator aborted.";
      }
      enum not_triggered {
        description
          "Automatic fiber characterization orchestrator not_triggered by sco.";
      }
    }
  }

  typedef raman-on {
    type enumeration {
      enum On {
        value 1;
        description
          "ON.";
      }
      enum Off {
        value 0;
        description
          "OFF.";
      }
    }
  }

  typedef afc-calculator-status {
    type enumeration {
      enum unknown {
        description
          "Automatic fiber characterization calculator unknown.";
      }
      enum failed {
        description
          "Automatic fiber characterization calculator failed.";
      }
      enum succeed {
        description
          "Automatic fiber characterization calculator succeeded.";
      }
      enum unmeasurable {
        description
          "Automatic fiber characterization calculator unmeasurable.";
      }
    }
  }
}
