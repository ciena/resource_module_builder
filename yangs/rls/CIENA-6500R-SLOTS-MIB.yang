module CIENA-6500R-SLOTS-MIB {
  namespace "urn:ietf:params:xml:ns:yang:smiv2:CIENA-6500R-SLOTS-MIB";
  prefix ciena-6500r;

  import CIENA-SMI {
    prefix ciena-smi;
  }

  organization
    "Ciena Corporation";
  contact
    "Web URL: http://www.ciena.com/
     Postal:  7035 Ridge Road
     Hanover, Maryland 21076
     U.S.A.
     Phone:   +1 800-921-1144
     Fax:     +1 410-694-5750";
  description
    "This modules describes slots for the 6500r platform";

  revision 2022-01-10 {
    description
      "Added rlsEntity.";
  }
  revision 2020-09-30 {
    description
      "Initial revision.";
  }
}
