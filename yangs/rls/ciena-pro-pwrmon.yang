module ciena-pro-pwrmon {
  namespace "urn:ciena:params:xml:ns:yang:ciena-pro-pwrmon";
  prefix pro-pwrmon;

  import ciena-common-version {
    prefix ciena-common-version;
  }

  import ciena-pro-types {
    prefix ciena-pro-types;
  }

  import ciena-pro-optical-types {
    prefix ciena-pro-optical-types;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's power monitor object.";

  revision 2021-03-24 {
    ciena-common-version:version "version" {
      ciena-common-version:string "1.5.0";
    }
    description
      "Add direction leaf.";
  }
  revision 2021-01-27 {
    ciena-common-version:version "version" {
      ciena-common-version:string "1.4.0";
    }
    description
      "Added orl-threshold-ranges.";
  }
  revision 2020-11-16 {
    ciena-common-version:version "version" {
      ciena-common-version:string "1.3.0";
    }
    description
      "Added a monitoring thresholds, hysteresis and diagnostic points.";
  }
  revision 2020-10-22 {
    ciena-common-version:version "version" {
      ciena-common-version:string "1.2.0";
    }
    description
      "Added admin-state, min-power, max-power,
       loss-of-signal leaf";
  }
  revision 2020-09-08 {
    ciena-common-version:version "version" {
      ciena-common-version:string "1.1.0";
    }
    description
      "Added SDMON and NMCMON groups";
  }
  revision 2020-08-01 {
    ciena-common-version:version "version" {
      ciena-common-version:string "1.0.0";
    }
    description
      "Initial version";
  }

  grouping pwrmon-base {
    leaf name {
      type ciena-pro-types:object-name;
      description
        "pwrmon identification/name";
    }

    leaf center-freq {
      type ciena-pro-optical-types:frequency;
      description
        "Center Frequency.";
    }

    leaf spectral-width {
      type ciena-pro-optical-types:frequency;
      description
        "Spectral width.";
    }

    leaf signal-type {
      type enumeration {
        enum "OSC";
        enum "TPS Pilot Tone";
        enum "CV";
        enum "OTDR";
        enum "TG";
        enum "Total Power";
        enum "C-Band";
        enum "L-Band";
        enum "C+L-Band";
        enum "NMCMON";
        enum "SDMON";
      }
      description
        "Signal Type";
    }

    leaf power {
      type ciena-pro-optical-types:power-dBm-1-precision;
      config false;
      description
        "Total power within the band this pwrmon supports defined by the frequency attribute";
    }

    leaf target-power {
      type ciena-pro-optical-types:power-dBm-1-precision;
      description
        "Target power";
    }

    container target-power-ranges {
      leaf min {
        type ciena-pro-optical-types:power-dBm-1-precision;
      }

      leaf max {
        type ciena-pro-optical-types:power-dBm-1-precision;
      }
    }

    leaf los-threshold {
      type ciena-pro-optical-types:power-dBm-1-precision;
      description
        "Threshold at which to declare loss of signal";
    }

    leaf los-threshold-hysteresis {
      type decimal64 {
        fraction-digits 1;
      }
      units "dB";
      description
        "The hysteresis value used to calculate the pwrmon LOS clear threshold.";
    }

    container los-threshold-ranges {
      leaf min {
        type ciena-pro-optical-types:power-dBm-1-precision;
      }

      leaf max {
        type ciena-pro-optical-types:power-dBm-1-precision;
      }
    }

    leaf optical-return-loss {
      type ciena-pro-optical-types:loss-dB-1-precision;
      config false;
      description
        "Optical return loss (ORL) is the amount of light that is reflected back up the fiber toward the source by
         light reflections off the interface of the polished end surface of the mated connectors and air, you should
         probably check your connection.";
    }

    leaf parent-plug-slot {
      type ciena-pro-types:object-name;
      description
        "Parent plug slot number";
    }

    leaf orl-threshold {
      type ciena-pro-optical-types:loss-dB-1-precision;
      default "22";
      description
        "Threshold at which to declare the optical return loss alarm";
    }

    container orl-threshold-ranges {
      leaf min {
        type ciena-pro-optical-types:loss-dB-1-precision;
      }

      leaf max {
        type ciena-pro-optical-types:loss-dB-1-precision;
      }
    }

    leaf low-orl-hysteresis {
      type ciena-pro-optical-types:loss-dB-1-precision;
      default "3";
      description
        "Hysteresis at which to declare low optical return loss alarm";
    }

    leaf orl-state {
      type ciena-pro-optical-types:orl-state;
      config false;
      description
        "The ORL State";
    }

    uses ciena-pro-types:admin-state;

    leaf min-power {
      type ciena-pro-optical-types:power-dBm-1-precision;
      config false;
      description
        "Minimum tidemarked power at the optical monitor";
    }

    leaf max-power {
      type ciena-pro-optical-types:power-dBm-1-precision;
      config false;
      description
        "Maximum tidemarked power at the optical monitor";
    }

    leaf direction {
      type enumeration {
        enum "forward" {
          description
            "In the direction of traffic";
        }
        enum "reverse" {
          description
            "Opposite the direction of traffic";
        }
      }
      default "forward";
      description
        "Specifies the direction optical power is monitored relative to the direction of traffic.";
    }

    container monitoring-thresholds {
      uses ciena-pro-optical-types:monitoring-thresholds-grouping;

      uses ciena-pro-optical-types:monitoring-hysteresis-grouping;
    }
  }

  grouping pwrmon-diagnostic {
    leaf target-unachievable {
      type boolean;
      description
        "Target Unachievable";
    }

    leaf low-optical-return-loss {
      type boolean;
      description
        "Low Optical Return Loss";
    }

    leaf loss-of-signal {
      type boolean;
      description
        "Loss of Signal, Raised - when power falls
         below los-threshold and Cleared- when power
         rises above los-threshold + los-hysteresis";
    }

    uses ciena-pro-optical-types:monitoring-diagnostic-grouping;
  }

  grouping pwrmon {
    uses pwrmon-base;

    container diagnostic {
      config false;
      description
        "Facility diagnostic state.";
      uses pwrmon-diagnostic;
    }
  }
}
