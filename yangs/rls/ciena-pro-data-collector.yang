module ciena-pro-data-collector {
  yang-version 1.1;
  namespace "urn:ciena:params:xml:ns:yang:ciena-pro-data-collector";
  prefix data-collector;

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's R-series platform data collector model";

  revision 2017-01-01 {
    description
      "Initial revision";
  }

  grouping ciena-pro-data-collector-mount {
    container data-collector {
      list card {
        key "name";
        config true;
        leaf name {
          type string {
            length "1..512";
          }
          description
            "The name of the card.";
        }

        leaf present {
          type boolean;
          default "false";
          config true;
          description
            "Reflects the physical presence of the card.";
        }

        anyxml data {
          description
            "This data tree represents data on the card. Pushing configuration data to this node will attempt to send that configuration data to the node. Querying this node will get the config from the device";
        }
      }
    }
  }

  grouping ciena-pro-data-collector-mount-actions;

  uses ciena-pro-data-collector-mount;
}
