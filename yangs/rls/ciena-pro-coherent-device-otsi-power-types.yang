module ciena-pro-coherent-device-otsi-power-types {
  yang-version 1.1;
  namespace "urn:ciena:ns:yang:coherent-device-otsi-power-types";
  prefix coherent-device-otsi-power-types;

  import ciena-common-version {
    prefix version;
  }
  import ietf-yang-types {
    prefix ietf-yang-types;
  }
  import ciena-pro-coherent-device-common-types {
    prefix coherent-device-common-types;
  }

  organization
    "Ciena Corporation";
  contact
    "Web URL: http://www.ciena.com/
     Postal:  7035 Ridge Road
              Hanover, Maryland 21076
              U.S.A.
     Phone:   +1 800-921-1144
     Fax:     +1 410-694-5750";
  description
    "OTSI power definitions for coherent devices.";

  revision 2024-01-01 {
    description
      "Initial version.";
    version:version "version" {
      version:string "1.0.0";
    }
    reference
      "1.0.0";
  }

  grouping coherent-device-otsi-power-level-tidemarks-group {
    leaf min-value {
      type coherent-device-common-types:optical-power-dBm;
      description
        "The minimum value of the power-level since the last clear or restart. ";
    }
    leaf min-value-time {
      type ietf-yang-types:date-and-time;
      description
        "The time the minimum value was recorded.";
    }
    leaf max-value {
      type coherent-device-common-types:optical-power-dBm;
      description
        "The maximum value of the power-level since the last clear or restart. ";
    }
    leaf max-value-time {
      type ietf-yang-types:date-and-time;
      description
        "The time the maximum value was recorded.";
    }
    leaf last-clear-time {
      type ietf-yang-types:date-and-time;
      description
        "The last time the tidemarks were cleared. After a restart this leaf has
         no value and is not available in responses until at least one clear-min-max
         operation has occurred.";
    }
    action clear-min-max {
      description
        "Operation to clear the current OTSI minimum and maximum tidemarks for power-level monitoring.";
      output {
        leaf rc {
          type uint8;
          description
            "";
        }
        leaf reason {
          type string;
          description
            "";
        }
      }
    }
    description
      "";
  }

  grouping coherent-device-otsi-power-level-tidemarks-group-no-actions {
    leaf min-value {
      type coherent-device-common-types:optical-power-dBm;
      description
        "The minimum value of the power-level since the last clear or restart. ";
    }
    leaf min-value-time {
      type ietf-yang-types:date-and-time;
      description
        "The time the minimum value was recorded.";
    }
    leaf max-value {
      type coherent-device-common-types:optical-power-dBm;
      description
        "The maximum value of the power-level since the last clear or restart. ";
    }
    leaf max-value-time {
      type ietf-yang-types:date-and-time;
      description
        "The time the maximum value was recorded.";
    }
    leaf last-clear-time {
      type ietf-yang-types:date-and-time;
      description
        "The last time the tidemarks were cleared. After a restart this leaf has
         no value and is not available in responses until at least one clear-min-max
         operation has occurred.";
    }
    container clear-min-max {
      description
        "Operation to clear the current OTSI minimum and maximum tidemarks for power-level monitoring.";
      container output {
        leaf rc {
          type uint8;
          description
            "";
        }
        leaf reason {
          type string;
          description
            "";
        }
      }
    }
    description
      "";
  }

  grouping coherent-device-otsi-lane-power-default-thresholds-group {
    leaf power-low-alarm {
      type coherent-device-common-types:optical-power-dBm;
      description
        "Lane power low alarm threshold.";
    }
    leaf power-high-alarm {
      type coherent-device-common-types:optical-power-dBm;
      description
        "Lane power high alarm threshold.";
    }
    leaf power-low-warning {
      type coherent-device-common-types:optical-power-dBm;
      description
        "Lane power low warning threshold.";
    }
    leaf power-high-warning {
      type coherent-device-common-types:optical-power-dBm;
      description
        "Lane power high warning threshold.";
    }
    description
      "Lane power level default thresholds.";
  }

  grouping coherent-device-otsi-lane-power-channel-default-thresholds-group {
    leaf channel-power-low-alarm {
      type coherent-device-common-types:optical-power-dBm;
      description
        "Channel power low alarm threshold.";
    }
    leaf channel-power-high-alarm {
      type coherent-device-common-types:optical-power-dBm;
      description
        "Channel power high alarm threshold.";
    }
    leaf channel-power-low-warning {
      type coherent-device-common-types:optical-power-dBm;
      description
        "Channel power low warning threshold.";
    }
    leaf channel-power-high-warning {
      type coherent-device-common-types:optical-power-dBm;
      description
        "Channel power high warning threshold.";
    }
    description
      "Lane channel power level default thresholds.";
  }

  grouping coherent-device-otsi-lane-power-provisioned-thresholds-group {
    leaf enabled {
      type boolean;
      default "false";
      description
        "True to enable device power threshold override.";
    }
    leaf power-low-alarm {
      type coherent-device-common-types:optical-power-dBm;
      description
        "Lane power low alarm threshold config.";
    }
    leaf power-high-alarm {
      type coherent-device-common-types:optical-power-dBm;
      description
        "Lane power high alarm threshold config.";
    }
    leaf power-low-warning {
      type coherent-device-common-types:optical-power-dBm;
      description
        "Lane power low warning threshold config.";
    }
    leaf power-high-warning {
      type coherent-device-common-types:optical-power-dBm;
      description
        "Lane power high warning threshold config.";
    }
    description
      "Provisionable lane power thresholds.
       If provisioned override the default thresholds provided by the device.
       By default, if provisioned-thresholds ARE enabled and NO override value
       is provisioned, the default thresholds read from the device is used.";
  }

  grouping otsi-lane-power-channel-provisioned-thresholds-group {
    leaf channel-power-low-alarm {
      type coherent-device-common-types:optical-power-dBm;
      description
        "Channel power low alarm threshold config.";
    }
    leaf channel-power-high-alarm {
      type coherent-device-common-types:optical-power-dBm;
      description
        "Channel power high alarm threshold config.";
    }
    leaf channel-power-low-warning {
      type coherent-device-common-types:optical-power-dBm;
      description
        "Channel power low warning threshold config.";
    }
    leaf channel-power-high-warning {
      type coherent-device-common-types:optical-power-dBm;
      description
        "Channel power high warning threshold config.";
    }
    description
      "Provisionable lane channel power thresholds.
       If provisioned override the default thresholds provided by the device.
       By default, if provisioned-thresholds ARE enabled and NO override value
       is provisioned, the default thresholds read from the device is used.";
  }

  grouping coherent-device-otsi-power-config-group {
    list power {
      key "direction";
      leaf direction {
        type coherent-device-common-types:direction-enum;
        description
          "RX/TX direction.";
      }
      leaf number-of-lanes {
        type uint8;
        description
          "Indicate of the number of lanes on a specific device.";
      }
      list lane {
        key "lane-index";
        leaf lane-index {
          type uint8 {
            range "1..max";
          }
          description
            "Lane index value";
        }
        container threshold-overrides {
          uses coherent-device-otsi-lane-power-provisioned-thresholds-group;
          uses otsi-lane-power-channel-provisioned-thresholds-group;
          description
            "Lane power provisioned thresholds";
        }
        description
          "";
      }
      description
        "Per lane power levels and theshold management.";
    }
    description
      "";
  }

  grouping coherent-device-otsi-power-state-group {
    list power {
      key "direction";
      config false;
      leaf direction {
        type coherent-device-common-types:direction-enum;
        description
          "RX/TX direction.";
      }
      leaf number-of-lanes {
        type uint8;
        config false;
        description
          "Indicate of the number of lanes on a specific device.";
      }
      list lane {
        key "lane-index";
        leaf lane-index {
          type uint8 {
            range "1..max";
          }
          description
            "Lane index value";
        }
        container actual {
          config false;
          leaf value {
            type coherent-device-common-types:optical-power-dBm;
            description
              "";
          }
          uses coherent-device-otsi-power-level-tidemarks-group;
          description
            "Actual lane power.
             For multi-lane devices this is the per lane power.
             For single-lane devices, this is the total optical power.";
        }
        container actual-channel {
          config false;
          leaf value {
            type coherent-device-common-types:optical-power-dBm;
            description
              "";
          }
          uses coherent-device-otsi-power-level-tidemarks-group;
          description
            "Actual signal channel power on a lane.
             This is the signal power detected for a particular frequency.
             In contrast, actual lane power refers to total power
             at the receiver for this lane.";
        }
        container threshold-defaults {
          config false;
          uses coherent-device-otsi-lane-power-default-thresholds-group;
          uses coherent-device-otsi-lane-power-channel-default-thresholds-group;
          description
            "Lane power default thresholds";
        }
        container threshold-overrides {
          config false;
          uses coherent-device-otsi-lane-power-provisioned-thresholds-group;
          uses otsi-lane-power-channel-provisioned-thresholds-group;
          description
            "Lane power provisioned thresholds";
        }
        description
          "";
      }
      description
        "Per lane power levels and theshold management.";
    }
    description
      "";
  }

  grouping coherent-device-otsi-power-state-group-no-actions {
    list power {
      key "direction";
      config false;
      leaf direction {
        type coherent-device-common-types:direction-enum;
        description
          "RX/TX direction.";
      }
      leaf number-of-lanes {
        type uint8;
        config false;
        description
          "Indicate of the number of lanes on a specific device.";
      }
      list lane {
        key "lane-index";
        leaf lane-index {
          type uint8 {
            range "1..max";
          }
          description
            "Lane index value";
        }
        container actual {
          config false;
          leaf value {
            type coherent-device-common-types:optical-power-dBm;
            description
              "";
          }
          uses coherent-device-otsi-power-level-tidemarks-group-no-actions;
          description
            "Actual lane power.
             For multi-lane devices this is the per lane power.
             For single-lane devices, this is the total optical power.";
        }
        container actual-channel {
          config false;
          leaf value {
            type coherent-device-common-types:optical-power-dBm;
            description
              "";
          }
          uses coherent-device-otsi-power-level-tidemarks-group-no-actions;
          description
            "Actual signal channel power on a lane.
             This is the signal power detected for a particular frequency.
             In contrast, actual lane power refers to total power
             at the receiver for this lane.";
        }
        container threshold-defaults {
          config false;
          uses coherent-device-otsi-lane-power-default-thresholds-group;
          uses coherent-device-otsi-lane-power-channel-default-thresholds-group;
          description
            "Lane power default thresholds";
        }
        container threshold-overrides {
          config false;
          uses coherent-device-otsi-lane-power-provisioned-thresholds-group;
          uses otsi-lane-power-channel-provisioned-thresholds-group;
          description
            "Lane power provisioned thresholds";
        }
        description
          "";
      }
      description
        "Per lane power levels and theshold management.";
    }
    description
      "";
  }
}
