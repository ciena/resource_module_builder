module ciena-6500r-osrp-rls-ra-osrp {
  namespace "urn:ciena:params:xml:ns:yang:ciena-6500r-osrp-rls-ra-osrp";
  prefix osrp;

  import ciena-osrp-osrp-node {
    prefix ciena-osrp-osrp-node;
  }

  import ciena-osrp-osrp-link {
    prefix ciena-osrp-osrp-link;
  }

  import ciena-osrp-dtl {
    prefix ciena-osrp-dtl;
  }

  import ciena-osrp-dtl-set {
    prefix ciena-osrp-dtl-set;
  }

  import ciena-osrp-snc {
    prefix ciena-osrp-snc;
  }

  import ciena-osrp-snc-group {
    prefix ciena-osrp-snc-group;
  }

  import ciena-osrp-osrp-network-topology {
    prefix ciena-osrp-osrp-network-topology;
  }

  import ciena-common-yang {
    prefix yang;
  }

  import ciena-6500r-osrp-rls-ra-types {
    prefix ciena-6500r-osrp-rls-ra-types;
  }

  import ciena-common-version {
    prefix ciena-common-version;
  }

  organization
    "Ciena Corporation";
  contact
    "Web URL: http://www.ciena.com/
     Postal:  7035 Ridge Road
              Hanover, Maryland 21076
              U.S.A.
     Phone:   +1 800-921-1144
     Fax:     +1 410-694-5750";
  description
    "This module describes Ciena's OSRP object model for the 6500r platform";

  revision 2021-03-01 {
    ciena-common-version:string "1.1.0";
    description
      "Removed ciena-osrp-osrp-alarm under mount point.";
  }
  revision 2020-11-05 {
    ciena-common-version:string "1.0.1";
    description
      "ciena-osrp-osrp-network-topology is mounted as config false.";
  }
  revision 2019-11-26 {
    ciena-common-version:string "1.0.0";
    description
      "Initial revision.";
  }

  list osrp {
    key "node-name";
    description
      "Configuration data and operational data of OSRP objects";
    leaf node-name {
      type ciena-6500r-osrp-rls-ra-types:osrp-node-name;
      description
        "OSRP node name";
    }

    container object {
      yang:mount-start "ciena-osrp-osrp-node";
      yang:mount-end "ciena-osrp-osrp-node";
      yang:mount-start "ciena-osrp-osrp-link";
      yang:mount-end "ciena-osrp-osrp-link";
      yang:mount-start "ciena-osrp-dtl";
      yang:mount-end "ciena-osrp-dtl";
      yang:mount-start "ciena-osrp-dtl-set";
      yang:mount-end "ciena-osrp-dtl-set";
      yang:mount-start "ciena-osrp-snc";
      yang:mount-end "ciena-osrp-snc";
      yang:mount-start "ciena-osrp-snc-group";
      yang:mount-end "ciena-osrp-snc-group";
      yang:mount-start "ciena-osrp-osrp-network-topology";
      yang:mount-end "ciena-osrp-osrp-network-topology";
      uses ciena-osrp-osrp-node:ciena-osrp-osrp-node-mount-actions;

      uses ciena-osrp-osrp-node:ciena-osrp-osrp-node-mount;

      uses ciena-osrp-osrp-link:ciena-osrp-osrp-link-mount-actions;

      uses ciena-osrp-osrp-link:ciena-osrp-osrp-link-mount;

      uses ciena-osrp-dtl:ciena-osrp-dtl-mount-actions;

      uses ciena-osrp-dtl:ciena-osrp-dtl-mount;

      uses ciena-osrp-dtl-set:ciena-osrp-dtl-set-mount-actions;

      uses ciena-osrp-dtl-set:ciena-osrp-dtl-set-mount;

      uses ciena-osrp-snc:ciena-osrp-snc-mount-actions;

      uses ciena-osrp-snc:ciena-osrp-snc-mount;

      uses ciena-osrp-snc-group:ciena-osrp-snc-group-mount-actions;

      uses ciena-osrp-snc-group:ciena-osrp-snc-group-mount;

      uses ciena-osrp-osrp-network-topology:ciena-osrp-osrp-network-topology-mount-actions;

      uses ciena-osrp-osrp-network-topology:ciena-osrp-osrp-network-topology-mount;
    }
  }
}
