module ciena-common-test-python {
  yang-version 1.1;
  namespace "urn:ciena:params:xml:ns:yang:ciena-common-test-python";
  prefix test-python;

  import ciena-common-yang {
    prefix common-yang;
  }
  import ciena-common-version {
    prefix version;
  }

  organization
    "Ciena Corporation";
  contact
    "Web URL: http://www.ciena.com";
  description
    "Test module for ddy-test-python";

  revision 2024-01-29 {
    description
      "Initial revision";
    version:version "version" {
      version:string "1.0.0";
    }
  }

  container cobra {
    list boa {
      key "number";
      leaf number {
        type uint32;
      }
      anyxml any1;
      anyxml any2;
      leaf snake {
        type string {
          common-yang:stringptr "true";
        }
      }
      leaf viper {
        type boolean;
      }
      container stats {
        leaf weight {
          type uint32;
        }
        leaf length {
          type uint32;
        }
      }
    }
  }
}
