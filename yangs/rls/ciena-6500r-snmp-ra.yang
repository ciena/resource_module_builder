module ciena-6500r-snmp-ra {
  namespace "urn:ciena:params:xml:ns:yang:ciena-6500r-snmp-ra";
  prefix snmp-ra;

  import ciena-common-yang {
    prefix ciena-common-yang;
  }
  import ietf-inet-types {
    prefix ietf;
  }
  import CPL-ALM-MIB {
    prefix cpl-alm;
  }
  import ciena-6500r-types {
    prefix ciena-6500r-types;
  }
  import ciena-common-version {
    prefix ciena-common-version;
  }
  import ciena-pro-alarm {
    prefix alarm;
  }
  import ciena-pro-software {
    prefix software-mgr;
  }
  import ciena-pro-optical-types {
    prefix ciena-pro-optical-types;
  }
  import ciena-6500r-otdr {
    prefix otdr;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's RLS SNMP resource adaptor data model.";

  revision 2023-07-06 {
    description
      "Changed type to mandatory in snmp-operate-raman-calibration.";
    ciena-common-version:string "1.4.3";
  }
  revision 2023-06-27 {
    description
      "Add type to snmp-operate-raman-calibration.";
    ciena-common-version:string "1.4.2";
  }
  revision 2023-02-27 {
    description
      "Add custom-read-func enum for Timed OPM Input powers (opmEnhFlexChannelSurvInputTimedPowers).";
    ciena-common-version:string "1.4.1";
  }
  revision 2023-02-08 {
    description
      "change the enum YES-with-header under the array-member leaf to YES-with-timestamp";
    ciena-common-version:string "1.4.0";
  }
  revision 2023-01-30 {
    description
      "Add a new enum YES-with-header to the array-member leaf";
    ciena-common-version:string "1.3.0";
  }
  revision 2022-11-30 {
    description
      "Add snmp-post-oid container";
    ciena-common-version:string "1.2.0";
  }
  revision 2022-11-23 {
    description
      "Added snmp-start-otdr-trace, snmp-stop-otdr-trace rpcs.";
    ciena-common-version:string "1.1.0";
  }
  revision 2022-11-09 {
    description
      "Add facility to alarm-mappings";
    ciena-common-version:string "1.0.29";
  }
  revision 2022-06-01 {
    description
      "Add cache-incarnation-number, last-cache-timestamp, cadence to global-perf-stats";
    ciena-common-version:string "1.0.28";
  }
  revision 2022-05-27 {
    description
      "Add snmp-diagnose-equipment rpc";
    ciena-common-version:string "1.0.27";
  }
  revision 2022-04-25 {
    description
      "Add custom-read-func enum for protection switch state.";
    ciena-common-version:string "1.0.26";
  }
  revision 2022-04-14 {
    description
      "Add custom-read, custom-write functions for line-input.";
    ciena-common-version:string "1.0.25";
  }
  revision 2022-03-04 {
    description
      "Add custom-read function enum secondsToFormattedUptime.";
    ciena-common-version:string "1.0.24";
  }
  revision 2022-03-02 {
    description
      "Add custom read function for time-of-day.";
    ciena-common-version:string "1.0.23";
  }
  revision 2021-09-23 {
    description
      "Add hardware-accuracy-range container to the oidlist.";
    ciena-common-version:string "1.0.22";
  }
  revision 2021-09-17 {
    description
      "Add upgrade-operational-state to card data and ignore-upgrade-state global flag";
    ciena-common-version:string "1.0.21";
  }
  revision 2021-09-16 {
    description
      "Add custom-read-func portLedFlash,
       add physical-reference-index to alarm in alarm-map";
    ciena-common-version:string "1.0.20";
  }
  revision 2021-08-09 {
    description
      "Add lamp-flash rpc";
    ciena-common-version:string "1.0.19";
  }
  revision 2021-08-06 {
    description
      "Add per card and global performance-statistics";
    ciena-common-version:string "1.0.18";
  }
  revision 2021-07-28 {
    description
      "Add physical-references to snmp-maps";
    ciena-common-version:string "1.0.17";
  }
  revision 2021-05-28 {
    description
      "Add custom handlers for OTDR HW port select";
    ciena-common-version:string "1.0.16";
  }
  revision 2021-05-19 {
    description
      "Add secure-erase rpc.";
    ciena-common-version:string "1.0.15";
  }
  revision 2021-05-11 {
    description
      "Add additional-info.";
    ciena-common-version:string "1.0.14";
  }
  revision 2021-05-04 {
    description
      "Add optically-ready and photonic-ready leafs.";
    ciena-common-version:string "1.0.13";
  }
  revision 2021-03-23 {
    description
      "Adding alarm-level.";
    ciena-common-version:string "1.0.12";
  }
  revision 2020-11-17 {
    description
      "Adding alarm-template-name.";
    ciena-common-version:string "1.0.11";
  }
  revision 2020-11-16 {
    description
      "Adding custom read handler to support OTDR trace resonse event status.";
    ciena-common-version:string "1.0.10";
  }
  revision 2020-11-04 {
    description
      "Add RPC to set alarm shutoff disabled and timer.";
    ciena-common-version:string "1.0.9";
  }
  revision 2020-08-19 {
    description
      "Adding custom read handler to support OTDR trace event comment.";
    ciena-common-version:string "1.0.8";
  }
  revision 2020-08-07 {
    description
      "Adding custom read handler to convert timestamp of the last CV signal received successfully to yang time.";
    ciena-common-version:string "1.0.7";
  }
  revision 2020-08-01 {
    description
      "Adding custom read and write handler enums for IP addresses";
    ciena-common-version:string "1.0.6";
  }
  revision 2020-03-16 {
    description
      "Adding custom read handler enum for handing temperatures as well as age";
    ciena-common-version:string "1.0.4";
  }
  revision 2020-03-05 {
    description
      "Removing restart type and time.";
    ciena-common-version:string "1.0.5";
  }
  revision 2020-03-05 {
    description
      "Adding custom read handler enum for converting pluggable config leaf to inventory, adding restart type and time.";
    ciena-common-version:string "1.0.3";
  }
  revision 2020-02-12 {
    description
      "Expanding facility/name to 64 chars to accomodate things long named facilities like DGFF which contain 2 keys.";
    ciena-common-version:string "1.0.2";
  }
  revision 2020-02-10 {
    description
      "Raman/OTDR Fiber Types and trimming string lengths.";
    ciena-common-version:string "1.0.1";
  }
  revision 2020-01-06 {
    description
      "Added return codes for RPCs.";
  }
  revision 2019-10-03 {
    description
      "Added home-directory.";
  }
  revision 2019-06-06 {
    description
      "Added Lamp Test RPC.";
  }
  revision 2019-05-10 {
    description
      "Added additional info to the alarm mappings";
    ciena-common-version:string "1.0.0";
  }
  revision 2018-01-01 {
    description
      "Initial revision";
  }

  grouping cadence-grouping {
    leaf cadence {
      type enumeration {
        enum persistent {
          description
            "Persistent data, no need to collect on a given cadence";
        }
        enum one-second {
          description
            "Data that needs to be collected on a per second cadence, should be limited to control based values";
        }
        enum fifteen-second {
          description
            "Lower priority attributes that should be refreshed less often (15s)";
        }
        enum thirty-second {
          description
            "Lower priority attributes that should be refreshed less often (30s)";
        }
        enum on-demand {
          description
            "Non cachable attributes, something that we only want to retrieve on demand (for example OTDR)";
        }
      }
    }
  }

  grouping oid-map {
    leaf facility {
      type string {
        length "1..64";
      }
      description
        "The facility type optmon/amp/whatever etc it is we relate to will be used to generate a desc";
    }
    list facilities {
      key "name";
      leaf name {
        type string {
          length "1..64";
        }
        description
          "The name of the optmon/amp/whatever it is we relate to";
      }
      leaf instance {
        type string {
          length "1..32";
        }
        description
          "Indicates the SNMP instance for a given OID.";
      }
      list oids {
        key "parameter";
        leaf oid {
          type string {
            length "1..60";
          }
          description
            "The OID used to query an SNMP capable card, keep in sync with SNMP_RA_MAX_OID_STR_LEN";
        }
        leaf parameter {
          type string {
            length "1..64";
          }
          description
            "The name of the parameter which maps to the OID. For example current-power for an optmon facility";
        }
        leaf access {
          type enumeration {
            enum READONLY {
              description
                "We can only read this value";
            }
            enum READWRITE {
              description
                "We can read and write to this value generically";
            }
          }
          description
            "Can we read/write or just read this OID";
        }
        leaf instance {
          type string {
            length "1..32";
          }
          description
            "Indicates the SNMP sub-instance for a given OID.";
        }
        leaf custom-read-func {
          type enumeration {
            enum opmEnhFlexChannelSurvInputPowers {
              description
                "Enhanced OPM message";
            }
            enum wsdSliceAttenArray {
              description
                "WSD slice attenuation array get function";
            }
            enum wsdSliceSwSelArray {
              description
                "WSD switch selector get function";
            }
            enum wsdSliceLineSwSelArray {
              description
                "WSD Line Switch Selector get function";
            }
            enum cvRxPortSequencing {
              description
                "CV port sequencing Rx get function";
            }
            enum cvTxPortSequencing {
              description
                "CV port sequencing Tx get function";
            }
            enum groupOtdrTraceEventType {
              description
                "OTDR trace event type";
            }
            enum groupOtdrTraceEventDistance {
              description
                "OTDR trace event distance";
            }
            enum groupOtdrTraceEventReflectionValue {
              description
                "OTDR trace event reflection value";
            }
            enum groupOtdrTraceEventLossValue {
              description
                "OTDR trace event loss value";
            }
            enum groupOtdrProvFiberType {
              description
                "OTDR fiber type provisioning";
            }
            enum ramanfacProvFiberType {
              description
                "Raman fiber type provisioning";
            }
            enum subslotConfigToInventory {
              description
                "Custom handler to convert incoming subslot config set to an inventory response";
            }
            enum miscDataCurrAndAvgTemp {
              description
                "Custom handler to convert response to both current and average temperature leafs.";
            }
            enum minutesToFormattedUptime {
              description
                "Custom handler to convert incoming elapsed time in minutes to DDDD:HH:MM:SS";
            }
            enum cvTxTlvIpV4Addr {
              description
                "Custom handler to convert IPv4 address from binary (octets) to human readable ASCII format";
            }
            enum cvRxTlvIpV4Addr {
              description
                "Custom handler to convert IPv4 address from binary (octets) to human readable ASCII format";
            }
            enum cvTxTlvIpV6Addr {
              description
                "Custom handler to convert IPv6 address from binary (octets) to human readable ASCII format";
            }
            enum cvRxTlvIpV6Addr {
              description
                "Custom handler to convert IPv6 address from binary (octets) to human readable ASCII format";
            }
            enum cvSurvRxTimestamp {
              description
                "Custom handler to convert timestamp of the last CV signal received successfully to Epoch time";
            }
            enum groupOtdrTraceEventComment {
              description
                "OTDR trace event comment";
            }
            enum groupOtdrEventStatus {
              description
                "Bit field showing the OTDR reflection and loss events status.";
            }
            enum groupOtdrHwPortSelect {
              description
                "This refers to the configured hardware OTDR port selection.";
            }
            enum groupOtdrHwActualPortSelect {
              description
                "This refers to the current hardware OTDR port selection.";
            }
            enum portLedFlash {
              description
                "This refers to the port led is being flashed or not.";
            }
            enum timeOfDay {
              description
                "Custom handler to convert incoming timestamp to IETF format";
            }
            enum secondsToFormattedUptime {
              description
                "Custom handler to convert incoming elapsed time in seconds to DDDD:HH:MM:SS";
            }
            enum lineInput {
              description
                "Custom handler to invert incoming line input flag for get";
            }
            enum protSwitchState {
              description
                "Custom handler to update the protection switch state and the corressponding links states.";
            }
            enum opmEnhFlexChannelSurvInputTimedPowers {
              description
                "Custom handler to handle Timed Enhanced OPM Input Powers message";
            }
          }
          description
            "If we need a special function to define how to unpack an snmp response define it here";
        }
        leaf custom-write-func {
          type enumeration {
            enum wsdSliceAttenArray {
              description
                "WSD slice attenuation array set function";
            }
            enum wsdSliceSwSelArray {
              description
                "WSD switch selector set function";
            }
            enum wsdSliceLineSwSelArray {
              description
                "WSD Line Switch Selector set function";
            }
            enum cvRxPortSequencing {
              description
                "CV Rx port sequencing set function";
            }
            enum cvTxPortSequencing {
              description
                "CV Tx port sequencing set function";
            }
            enum groupOtdrProvFiberType {
              description
                "OTDR fiber type provisioning";
            }
            enum ramanfacProvFiberType {
              description
                "Raman fiber type provisioning";
            }
            enum cvTxTlvIpV4Addr {
              description
                "Custom handler to convert IPv4 address from ASCII to binary (octets)";
            }
            enum cvTxTlvIpV6Addr {
              description
                "Custom handler to convert IPv6 address from ASCII to binary (octets)";
            }
            enum groupOtdrHwPortSelect {
              description
                "This refers to the configured hardware OTDR port selection state.";
            }
            enum lineInput {
              description
                "Custom handler to invert outgoing line input flag for set";
            }
          }
          description
            "If we need a special function to define how to build a set message do so here";
        }
        leaf scaling-factor {
          type uint16;
          description
            "Indicates scaling factor as defined in the mib";
        }
        leaf type-def {
          type string {
            length "1..4";
          }
          description
            "Indicates string representation of the data type of this OID (i.e. -i for integer)";
        }
        leaf array-member {
          type enumeration {
            enum YES {
              description
                "Is an array member";
            }
            enum NO {
              description
                "Not an array member";
            }
            enum YES-with-timestamp {
              description
                "Is an array member with a header that will hold the timestamp";
            }
          }
          description
            "Is this oid a member of an array, or is it only retrievable individually, or a member of an array with a timestamp in the header";
        }
        leaf array-instance {
          type string {
            length "1..32";
          }
          description
            "Indicates the SNMP instance for an array";
        }
        uses cadence-grouping;
        leaf size {
          type uint16;
          description
            "Size of the SNMP-Response we can use this to determine how many OIDs to pack into our GET message";
        }
        container hardware-accuracy-range {
          leaf min {
            type int32;
            description
              "The minimum value the hardware can accurately report";
          }
          leaf max {
            type int32;
            description
              "The maximum value the hardware can accurately report";
          }
        }
        description
          "List of OIDs supported and all their specific parameters.";
      }
    }
  }

  grouping snmp-maps {
    leaf alarm-object {
      type cpl-alm:AlarmObjectName;
      description
        "The SNMP alarm object identifier.";
    }
    leaf instance {
      type uint32;
      description
        "Indicates the SNMP instance number for a SNMP object.";
    }
    leaf owner {
      type string {
        length "1..512";
      }
    }
    leaf oid-mapping {
      type instance-identifier;
      description
        "Mapping between OIDs, name, type and instance";
    }
    leaf alarm-mapping {
      type string {
        length "1..512";
      }
      description
        "Mapping between SNMP alarms and diagnostic";
    }
    leaf-list physical-references {
      type instance-identifier;
      ordered-by user;
      description
        "List of instance identifiers that provide additional identification criteria
         to identify physical components related to or impacted by an alarm.";
    }
  }

  grouping alarm-map {
    leaf type {
      type string {
        length "1..512";
      }
      description
        "Name of that alarm-mapping";
    }
    leaf facility {
      type string {
        length "1..64";
      }
      description
        "The type of facility, e.g. optmons/amps/whatever. Must match the exact name of the related facility.";
    }
    leaf diagPath {
      type string {
        length "1..512";
      }
      description
        "The name of the optmon/amp/whatever it is we relate to";
    }
    list alarm {
      key "alarmId";
      leaf alarmId {
        type cpl-alm:CplAlarmId;
        description
          "The SNMP alarm identification being reported.";
      }
      leaf diagnostic {
        type string {
          length "1..256";
        }
        description
          "The associated SNMP alarm diagnostic attribute. This is used as the name of alarm-template when alarm-template-name is not provided.";
      }
      leaf physical-reference-index {
        type uint8;
        default "1";
        description
          "The index of physical-reference of the alarm. Index value is 1-base.";
      }
      leaf alarm-template-name {
        type string {
          length "1..80";
        }
        description
          "Name of the alarm template to use to raise alarm. When not present, the name of the alarm-template is the attribute
           diagnostic";
      }
      leaf alarm-level {
        type identityref {
          base alarm:alarm-level;
        }
        description
          "Severity level of the alarm. Applicable only for alarm-template using severity-level.";
      }
      leaf additional-info {
        type string {
          length "1..80";
        }
        description
          "Additional info associated to this snmp alarm.";
      }
      description
        "List of SNMP alarms supported and associated diagnostic attribute.";
    }
  }

  grouping card-perf-stats {
    leaf get-failures {
      type uint32;
      description
        "The number of times an SNMP GET message has failed for this card.";
    }
    leaf bulk-set-failures {
      type uint32;
      description
        "The number of times an SNMP bulk SET message has failed for this card.";
    }
    leaf discrete-set-failures {
      type uint32;
      description
        "The number of times an SNMP discrete SET message has failed for this card, discrete SETs are only attempted
         when a bulk SET has failed.";
    }
    leaf heartbeat-failures {
      type uint32;
      description
        "The number of times the heartbeat to this card has gone down.";
    }
  }

  grouping global-perf-stats {
    leaf dropped-snmp-packets {
      type uint32;
      description
        "The total number of SNMP packets dropped by the system.";
    }
    leaf dropped-trap-packets-external {
      type uint32;
      description
        "The number of trap packets dropped by snmp-card-ra's external socket, the socket bound to snmp-port-trap.";
    }
    leaf dropped-trap-packets-internal {
      type uint32;
      description
        "The number of trap packets dropped by snmp-card-ra internal messaging.";
    }
  }

  container snmp-ra {
    list card {
      key "name";
      leaf name {
        type ciena-6500r-types:object-name;
        description
          "The name of the card.";
      }
      leaf present {
        type boolean;
        default "false";
        description
          "Reflects the physical presence of the card.";
      }
      leaf hb-retries {
        type uint16;
        config false;
        default "0";
        description
          "Keeps track of the heartbeat retries to the card.";
      }
      leaf max-hb-retries {
        type uint16;
        default "5";
        description
          "Maximum heartbeat attempts to the card.";
      }
      leaf communication-up {
        type boolean;
        config false;
        default "false";
        description
          "Indicates if communication to the card is possible.";
      }
      leaf optically-ready {
        type boolean;
        config false;
        default "false";
        description
          "Indicates if the card is optically ready.";
      }
      leaf photonic-ready {
        type boolean;
        config false;
        default "false";
        description
          "Indicates if the card is photonic ready.
           photonic-ready = communication-up && optically-ready";
      }
      leaf ip-address {
        type ietf:ip-address;
        description
          "The IP address used to access the card.";
      }
      leaf port {
        type ietf:port-number;
        description
          "The comms port used to access the card.";
      }
      leaf port-trap {
        type ietf:port-number;
        description
          "The comms port used to access the card.";
      }
      leaf home-directory {
        type string {
          length "1..512";
        }
        description
          "The card home directory.
           When specified, files associated to the card (e.g. the CCT SN.BIN file...)
           can be accessed on the CTM at this directory location.";
      }
      leaf upgrade-operational-state {
        type software-mgr:upgrade-op-state;
        description
          "Card reported upgrade state, when state is not idle, config SET messages to the card will be blocked";
        config false;
      }
      leaf cache-incarnation-number {
        type uint32;
        description
          "Incarnation number that will be incremented every time the cache is updated.";
        config false;
      }
      leaf last-cache-timestamp {
        type uint64;
        description
          "Timestamp of when the last caching cycle was complete, in epoch time.";
        config false;
      }
      uses cadence-grouping;
      list oid-mappings {
        key "facility";
        uses oid-map;
        description
          "Mapping between OIDs, name, type and instance";
      }
      list snmp-mappings {
        key "alarm-object instance";
        uses snmp-maps;
        description
          "OID and alarm mappings for object types and instances";
      }
      list alarm-mappings {
        key "type";
        uses alarm-map;
        description
          "Alarm mappings";
      }
      anyxml data {
        description
          "This data tree represents data on the card. Pushing configuration data to this node will attempt to send that configuration data to the node. Querying this node will get the config from the device";
      }
      container performance-statistics {
        uses card-perf-stats;
        description
          "snmp-card-ra performance statistics per card";
        config false;
      }
    }
    leaf snmp-port-trap {
      type ietf:port-number;
      description
        "The comms port used to listen for snmp trap.";
    }
    leaf ignore-upgrade-state {
      type boolean;
      description
        "Set to true to ignore the upgrade-operation-state of a card, and always send config changes,
          default behaviour, is to only send config changes when upgrade-operational-state is idle";
    }
    container performance-statistics {
      uses global-perf-stats;
      description
        "snmp-card-ra global performance statistics";
      config false;
    }
  }
  container snmp-post-oid {
    leaf post-oid-custom-write {
      type enumeration {
        enum wsdCtrlMsgSyncStatus {
          description
            "Custom handler to send a WsdCtrlMsg as the last OID when sending a set message containing Wsd OIDs";
        }
      }
    }
    description
      "Allow adding extra OIDs to the end of a set message, before the set message is sent to a card";
  }

  rpc snmp-restart {
    input {
      leaf resource {
        type instance-identifier;
        mandatory true;
        description
          "Resource to restart";
      }
      leaf restart-type {
        type enumeration {
          enum warm {
            value 1;
          }
          enum cold {
            value 2;
          }
        }
        mandatory true;
      }
    }
    output {
      uses ciena-common-yang:rpc-result-common;
    }
  }

  rpc snmp-protection-switch {
    input {
      leaf resource {
        type instance-identifier;
        mandatory true;
        description
          "Operate on protection switch";
      }
      leaf switch-action {
        type enumeration {
          enum release {
            value 1;
          }
          enum manual {
            value 2;
          }
          enum force {
            value 3;
          }
          enum lockout {
            value 4;
          }
        }
        mandatory true;
      }
    }
    output {
      uses ciena-common-yang:rpc-result-common;
    }
  }

  rpc snmp-reraise-alarms {
    input {
      leaf resource {
        type instance-identifier;
        mandatory true;
        description
          "Resource to trigger a reraise of alarms";
      }
    }
    output {
      uses ciena-common-yang:rpc-result-common;
    }
  }

  rpc snmp-reraise-protection-switch-events {
    input {
      leaf resource {
        type instance-identifier;
        mandatory true;
        description
          "Resource to trigger a reraise of switch events";
      }
    }
    output {
      uses ciena-common-yang:rpc-result-common;
    }
  }

  rpc snmp-lamp-test {
    input {
      leaf resource {
        type instance-identifier;
        mandatory true;
        description
          "Resource to trigger a lamp test";
      }
    }
    output {
      uses ciena-common-yang:rpc-result-common;
    }
  }

  rpc snmp-lamp-flash {
    input {
      leaf resource {
        type instance-identifier;
        mandatory true;
        description
          "Resource to trigger a lamp flash";
      }
      leaf test-action {
        type enumeration {
          enum start {
            value 1;
          }
          enum stop {
            value 2;
          }
        }
      }
    }
    output {
      uses ciena-common-yang:rpc-result-common;
    }
  }

  rpc snmp-refresh-tod {
    input {
      leaf resource {
        type instance-identifier;
        mandatory true;
        description
          "Resource to trigger a refresh of the time of day.";
      }
    }
    output {
      uses ciena-common-yang:rpc-result-common;
    }
  }

  notification snmp-trap {
    description
      "This notification contains an single snmp-trap translated into bifrost facilities.";
    leaf name {
      type ciena-6500r-types:object-name;
      description
        "The name of the card. Match the name of the slot in slot-mgr.";
    }
    leaf fac-mapping {
      type ciena-6500r-types:object-name;
      description
        "It is basically the type of facility. Set by the snmp-mappings::alarm-mapping.";
    }
    leaf owner {
      type ciena-6500r-types:object-name;
      description
        "Owner, aka the facility instance (not the snmp instance). Set by the snmp-mappings::owner.";
    }
    leaf diagnostic {
      type ciena-6500r-types:object-name;
      description
        "Diagnostic. Set by the alarm-mappings::alarm::diagnostic.";
    }
    leaf state {
      type boolean;
      description
        "Alarm state: true/false";
    }
    leaf alarm-template-name {
      type string {
        length "1..80";
      }
      description
        "Name of the alarm template to use to raise alarm. When not present, the name of the alarm-template is the attribute
         diagnostic";
    }
    leaf alarm-level {
      type identityref {
        base alarm:alarm-level;
      }
      description
        "Severity level as reported in alarm-mappings.";
    }
    leaf additional-info {
      type string {
        length "1..255";
      }
      description
        "Additional info coming either from snmp (card) or alarm-mappings, the latter being appended to the former.";
    }
  }

  rpc snmp-operate-raman-calibration {
    input {
      leaf resource {
        type instance-identifier;
        mandatory true;
        description
          "Instance of a raman object";
      }
      leaf type {
        type enumeration {
          enum manual {
            description
              "Manual calibration";
          }
          enum software {
            description
              "Software calibration";
          }
        }
        mandatory true;
        description
          "Raman calibration request type";
      }
    }
    output {
      uses ciena-common-yang:rpc-result-common;
    }
  }

  rpc snmp-set-automatic-shutoff-disabled {
    input {
      leaf resource {
        type instance-identifier;
        mandatory true;
        description
          "Instance of an amp object";
      }
      leaf also-disabled {
        type boolean;
        description
          "Alarm state: true/false";
      }
      leaf timer {
        type uint8;
        units "minutes";
        default "5";
        description
          "Duration of time in minutes to put card in ALSO Disabled state when the ALSO Disabled flag is set.
           Accepted range should be 0 - 60 minutes";
      }
    }
    output {
      uses ciena-common-yang:rpc-result-common;
    }
  }

  rpc snmp-secure-erase {
    input {
      leaf slot {
        type ciena-6500r-types:object-name;
        mandatory true;
        description
          "The name of the slot.";
      }
      leaf operation {
        type enumeration {
          enum erase {
            value 1;
          }
          enum erase-all {
            value 2;
          }
        }
        description
          "Indicates whether or not the secure erase applies to subslot and pluggables cards on the host card.";
        mandatory true;
      }
      leaf reboot {
        type boolean;
        default "false";
        description
          "Indicates whether or not the card will restart after the secure erase";
      }
    }
    output {
      uses ciena-common-yang:rpc-result-common;
    }
  }

  rpc snmp-diagnose-equipment {
    input {
      leaf resource {
        type instance-identifier;
        mandatory true;
        description
          "Resource to trigger a diagnose equipment to re-evaluate alarm";
      }
    }
    output {
      uses ciena-common-yang:rpc-result-common;
    }
  }

  rpc snmp-start-otdr-trace {
    description
      "Instructs a card to start an OTDR trace measurement.";
    input {
      leaf resource {
        type instance-identifier;
        mandatory true;
        description
          "Resource to start otdr trace";
      }
      leaf trace-type {
        type otdr:card-if-trace-type_t;
        mandatory true;
        description
          "The type of trace to be measured";
      }
      leaf launch-power {
        type otdr:launch-power_t;
        description
          "The type of launch power";
      }
      leaf event-range {
        type uint32 {
          range "0..128000";
        }
        units "m";
        description
          "OTDR Event Range (m)";
      }
      leaf insertion-loss {
        type ciena-pro-optical-types:loss-dB-1-precision;
        description
          "Aggregate insertion loss in the launch path";
      }
    }
    output {
      uses ciena-common-yang:rpc-result-common;
    }
  }

  rpc snmp-stop-otdr-trace {
    description
      "Instructs a card to stop an OTDR trace measurement.";
    input {
      leaf resource {
        type instance-identifier;
        mandatory true;
        description
          "Resource to stop otdr trace";
      }
    }
    output {
      uses ciena-common-yang:rpc-result-common;
    }
  }
}
