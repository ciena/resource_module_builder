module ciena-6500-cct {
  yang-version 1.1;
  namespace "urn:ciena:params:xml:ns:yang:ciena-6500-cct";
  prefix cct;

  import ietf-yang-types {
    prefix yang;
  }

  import ciena-6500r-types {
    prefix common-types;
  }

  import ciena-common-version {
    prefix ciena-common-version;
  }

  import ciena-pro-cct {
    ciena-common-version:string "0.1.0";
    prefix ciena-pro-cct;
  }

  organization
    "Ciena Corporation";
  contact
    "Web URL: http://www.ciena.com/
     Postal:  7035 Ridge Road
              Hanover, Maryland 21076
              U.S.A.
     Phone:   +1 800-921-1144
     Fax:     +1 410-694-5750";
  description
    "This module describes Ciena's 6500 platform Card Calibration Table (CCT) Service.";

  revision 2020-09-14 {
    ciena-common-version:string "0.1.0";
    description
      "Use ciena-pro-cct";
  }
  revision 2020-03-02 {
    ciena-common-version:string "0.0.2";
    description
      "Add parent-link ports under edfa";
  }
  revision 2019-11-19 {
    ciena-common-version:string "0.0.1";
    description
      "Added top-offset field in noise-figures";
  }
  revision 2019-06-06 {
    description
      "Initial revision";
  }

  grouping ciena-6500-cct-mount {
    list ccts {
      key "name";
      uses ciena-pro-cct:cct-data;
    }
  }

  grouping ciena-6500-cct-mount-actions;

  uses ciena-6500-cct-mount;
}
