module CIENA-6500R-INVENTORY-PROTECTION-GROUP-MIB {
  namespace "urn:ietf:params:xml:ns:yang:smiv2:CIENA-6500R-INVENTORY-PROTECTION-GROUP-MIB";
  prefix ciena-6500r-inventory;

  import CIENA-6500R-INVENTORY-MIB {
    prefix ciena-6500r;
  }
  import CIENA-PRO-TYPES-MIB {
    prefix ciena-pro;
  }
  import SNMPv2-TC {
    prefix smiv2;
  }

  organization
    "Ciena Corporation";
  contact
    "Web URL: http://www.ciena.com/
     Postal:  7035 Ridge Road
     Hanover, Maryland 21076
     U.S.A.
     Phone:   +1 800-921-1144
     Fax:    Inventory +1 410-694-5750";
  description
    "This modules describes Ciena's 6500r platform protection model.";

  revision 2020-09-30 {
    description
      "Initial revision.";
  }

  typedef PgStandard {
    type enumeration {
      enum g8731 {
        value 1;
      }
    }
    description
      "Standard used on Remote Equipment.";
  }

  typedef PgSwitchState {
    type enumeration {
      enum pending {
        value 0;
      }
      enum standby {
        value 1;
      }
      enum working {
        value 2;
      }
    }
    description
      "State of the switch.";
  }

  typedef PgSwitchStatus {
    type enumeration {
      enum pending {
        value 0;
      }
      enum idle {
        value 1;
      }
      enum complete {
        value 2;
      }
      enum fail {
        value 3;
      }
      enum deny {
        value 4;
      }
      enum completeRevertive {
        value 5;
      }
    }
    description
      "Switch status.";
  }

  typedef PgSwitchReason {
    type enumeration {
      enum pending {
        value 0;
      }
      enum signalOk {
        value 1;
      }
      enum manual {
        value 2;
      }
      enum forced {
        value 3;
      }
      enum lockout {
        value 4;
      }
      enum remote {
        value 5;
      }
      enum signalFail {
        value 6;
      }
      enum waitToRestore {
        value 7;
      }
    }
    description
      "State of the switch.";
  }

  container cienaRlsInventoryProtectionGrpMIB {
    list rlsInventoryPgEntry {
      config false;
      key "rlsInventoryPgSlotName rlsInventoryPgName";
      description
        "";
      leaf rlsInventoryPgSlotName {
        type ciena-pro:DisplayString32;
        config false;
        description
          "Slot Name.";
      }
      leaf rlsInventoryPgName {
        type ciena-pro:DisplayString32;
        config false;
        description
          "protection group identification.";
      }
      leaf rlsInventoryPgStandard {
        type ciena-6500r-inventory:PgStandard;
        config false;
        description
          "Standard used on Remote Equipment.";
      }
      leaf rlsInventoryPgRevertive {
        type smiv2:TruthValue;
        config false;
        description
          "Revertive behavior of the module. If True, then
           automatically revert after protection switch once the
           fault is restored.";
      }
      leaf rlsInventoryPgLossOfElectricalPower {
        type smiv2:TruthValue;
        config false;
        description
          "Indicates how the switch should react when there is a loss of power.
           By default (FALSE), the switch should stay where it is. When enabled
           (TRUE) it indicates the switch should go back to its default position (Switch 1).";
      }
      leaf rlsInventoryPgWaitToRestore {
        type int32 {
          range "0..60";
        }
        units "Minutes";
        config false;
        description
          "The time that must elapse before an APS path
           that has recovered from an signal failure (SF) or signal
           degradation (SD) condition can be used again to transport
           the normal traffic signal. During this time period, an SF or
           SD condition shall override the wait-to-restore time period.
           This leaf can only take effect when the revertive leaf
           equals true.";
      }
      leaf rlsInventoryPgBidirectSwitch {
        type smiv2:TruthValue;
        config false;
        description
          "Indicates how the switch should react when there is a bidirect switch.
           By default (TRUE).";
      }
      leaf rlsInventoryPgHoldOff {
        type int32 {
          range "0..65535";
        }
        config false;
        description
          "The time that must elapse before.";
      }
      leaf rlsInventoryPgDiagProtectionSwitchComplete {
        type smiv2:TruthValue;
        config false;
        description
          "Protection Switch Complete.";
      }
      leaf rlsInventoryPgAlarmAdditionalInfo {
        type ciena-pro:DisplayString128;
        config false;
        description
          "Additional info associated to a raised alarm.";
      }
    }
    config false;
    list rlsInventoryPgSwitchEntry {
      config false;
      key "rlsInventoryPgSwitchSlotName
           rlsInventoryPgSwitchPgName rlsInventoryPgSwitchName";
      description
        "";
      leaf rlsInventoryPgSwitchSlotName {
        type ciena-pro:DisplayString32;
        config false;
        description
          "Slot Name.";
      }
      leaf rlsInventoryPgSwitchPgName {
        type ciena-pro:DisplayString32;
        config false;
        description
          "protection group identification.";
      }
      leaf rlsInventoryPgSwitchName {
        type ciena-pro:DisplayString32;
        config false;
        description
          "switch group identification.";
      }
      leaf rlsInventoryPgSwitchState {
        type ciena-6500r-inventory:PgSwitchState;
        config false;
        description
          "State of the switch.";
      }
      leaf rlsInventoryPgSwitchStatus {
        type ciena-6500r-inventory:PgSwitchStatus;
        config false;
        description
          "Switch status.";
      }
      leaf rlsInventoryPgSwitchReason {
        type ciena-6500r-inventory:PgSwitchReason;
        config false;
        description
          "Switch reason.";
      }
    }
  }
}
