module ciena-pro-coherent-device-interface-diagnostics-types {
  namespace "urn:ciena:ns:yang:coherent-device-interface-diagnostics-types";
  prefix coherent-device-interface-diagnostics-types;

  import ciena-common-version {
    prefix version;
  }

  organization
    "Ciena Corporation";
  contact
    "Web URL: http://www.ciena.com/
     Postal:  7035 Ridge Road
              Hanover, Maryland 21076
              U.S.A.
     Phone:   +1 800-921-1144
     Fax:     +1 410-694-5750";
  description
    "Interface diagnostic data definitions for coherent devices.";

  revision 2024-01-01 {
    description
      "Initial version.";
    version:version "version" {
      version:string "1.0.0";
    }
    reference
      "1.0.0";
  }

  grouping coherent-device-interface-diagnostics-group {
    container diagnostics {
      leaf rx-to-tx-loopback {
        type boolean;
        default "false";
        description
          "An rx-to-tx loopback is enabled on the media-interface of the device.
           At this location the signal received from the fiber on the media-interface is returned
           toward the fiber.";
      }
      leaf tx-to-rx-loopback {
        type boolean;
        default "false";
        description
          "A tx-to-rx loopback is enabled on the media-interface of the device.
           At this location the signal received from the system on the host-interface is returned
           toward the system.";
      }
      description
        "";
    }
    description
      "";
  }
}
