module ciena-common-test {
  yang-version 1.1;
  namespace "urn:ciena:params:xml:ns:yang:ciena-common-test";
  prefix test;

  import ciena-common-test-list {
    prefix ciena-common-test-list;
  }
  import ciena-common-exceptions {
    prefix ciena-common-exceptions;
  }
  import ciena-common-recording-agent {
    prefix recording;
  }
  import ciena-common-yang {
    prefix ciena-common-yang;
  }
  import ciena-ddf {
    prefix ddf;
  }

  organization
    "Ciena Corporation";
  contact
    "Web URL: http://www.ciena.com";
  description
    "Test module";

  revision 2023-11-01 {
    description
      "Adding white with some simple leaf, container and list";
  }
  revision 2023-10-17 {
    description
      "Adding nested-list-two to nested-list";
  }
  revision 2023-09-18 {
    description
      "Adding new leaf and leaf-list target-node-test of type target-node for testing.";
  }
  revision 2023-09-07 {
    description
      "Add list of list to test list scenarios for to-pointers.";
  }
  revision 2023-08-09 {
    description
      "Adding new container string-based-return-code-list for testing.";
  }
  revision 2023-07-31 {
    description
      "Adding new identities for testing";
  }
  revision 2023-07-14 {
    description
      "Add RPC for generic client-side activations";
  }
  revision 2023-07-13 {
    description
      "Adding nested-list3 inside nested-list2";
  }
  revision 2023-07-10 {
    description
      "Adding nested-list2 with simpler keys";
  }
  revision 2023-03-31 {
    description
      "Adding new rpc and containers for encryption test case";
  }
  revision 2023-03-13 {
    description
      "Adding new rpc and container for deadline";
  }
  revision 2023-02-07 {
    description
      "Adding containers and lists for encryption test";
  }
  revision 2023-01-27 {
    description
      "Adding new container for enum with colon case";
  }
  revision 2022-12-21 {
    description
      "Add a container that gets augmented by a container and then the augmented
       container is then augmented by the same module that augments the
       container. Based on a real case from Waveserver.";
  }
  revision 2022-11-24 {
    description
      "Adding new container for enum with colon case";
  }
  revision 2022-11-18 {
    description
      "Adding encryption leaves";
  }
  revision 2022-03-24 {
    description
      "Introducing the Blue-Yellow component for testing. The Red-Blue component was
       too invasive: The get handler is sneaky and does things behind the scene
       that modifies the information. So introducing the Blue-Yellow component, which
       will be kept untouched, like it should always have been.";
  }
  revision 2021-05-21 {
    description
      "Adding keys only list";
  }
  revision 2021-02-09 {
    description
      "Adding root level instance id";
  }
  revision 2021-01-18 {
    description
      "Change 'mandatory' in abc_group";
  }
  revision 2018-01-01 {
    description
      "Initial revision";
  }

  identity complete-transaction {
    base recording:recording-type;
    description
      "handler for complete-transaction";
  }

  grouping ciena-common-test-mount-data {
    container string-based-return-code-list {
      config false;
      description
        "List of errors in case of command failure";
      list return-code-list {
        leaf instance {
          type string {
            ciena-common-yang:stringptr "true";
          }
          description
            "The instance to which the error code applies.";
        }
        leaf error {
          type string;
        }
      }
    }
    uses red-blue-group;
    uses blue-yellow-group;
    container white {
      uses abc_group;
      container cont1 {
        uses abc_group;
      }
      container cont2 {
        uses abc_group;
      }
      container cont3 {
        uses abc_group;
      }
      container cont4 {
        uses abc_group;
      }
      list list1 {
        key "k";
        leaf k {
          type uint8;
        }
        uses abc_group;
      }
    }
    container validation-test {
      uses abc_validate_group;
    }
    container to-pointer-test {
      container a {
        leaf string-test {
          type string;
        }
      }
    }
    list to-pointer-test2 {
      key "first-key";
      leaf first-key {
        type uint8;
      }
      list second-list {
        key "second-key";
        leaf second-key {
          type uint8;
        }
        leaf second-string {
          type string;
        }
        container second-container {
          leaf second-container-string {
            type string;
          }
        }
      }
    }
    container nested-container {
      container cone {
        leaf a {
          type uint8;
          default "1";
        }
        leaf b {
          type uint8;
          default "2";
        }
        leaf c {
          type uint8;
          default "3";
        }
      }
      container ctwo {
        config false;
        leaf d {
          type uint8;
        }
        leaf e {
          type uint8;
        }
        leaf f {
          type uint8;
        }
      }
    }
    container read-only {
      config false;
      uses red-blue-group;
      container name {
        container collision {
          leaf test {
            type uint8;
          }
          container child1 {
            container child2 {
              leaf test {
                type uint8;
              }
            }
          }
        }
      }
      container name-collision {
        leaf test {
          type uint8;
        }
        container child1 {
          container child2 {
            leaf test {
              type uint8;
            }
          }
        }
      }
    }
    container remove-via-deviation {
      uses red-blue-group;
    }
    uses ordered-lists-group;
    container simple-deadline-test {
      uses deadline-group;
    }
    container simple-test-container {
      ciena-common-yang:containerptr "true";
      list keys-only-list {
        key "name";
        leaf name {
          type string;
        }
      }
      leaf other-attribute {
        type string;
      }
      container leaf-test {
        leaf string-test {
          ciena-common-yang:encrypt "string-test-encrypted";
          ciena-common-yang:encrypt-path "/ciena-common-test/simple-test-container/leaf-test";
          type string;
        }
        leaf string-test-encrypted {
          type string {
            ciena-common-yang:stringptr "true";
          }
          ciena-common-yang:decrypt "string-test";
          ciena-common-yang:decrypt-path "/ciena-common-test/simple-test-container/leaf-test";
        }
        leaf uint8-test {
          type uint8;
        }
      }
      container presence-test {
        presence "presense test container";
      }
      container presence-test-2 {
        choice start-time {
          mandatory true;
          container immediate {
            presence "Start the measurement session immediately.";
          }
          leaf relative {
            type string;
          }
          leaf absolute {
            type string;
          }
        }
      }
      list outter {
        key "index";
        leaf index {
          type uint8;
        }
        min-elements 2;
        max-elements 3;
        list inner {
          key "name";
          leaf name {
            type string;
          }
          max-elements 2;
          leaf value {
            type uint16;
          }
        }
        leaf-list boolean-leaf-list {
          type boolean;
          max-elements 3;
          min-elements 2;
        }
        leaf mode {
          type uint8 {
            range "0..10";
          }
        }
      }
      list first {
        key "key1 key2";
        leaf key1 {
          type uint8;
        }
        leaf key2 {
          type string;
        }
        list second {
          key "key1 key2";
          leaf key1 {
            type uint8;
          }
          leaf key2 {
            type string;
          }
          list third {
            key "key1";
            leaf key1 {
              type uint8;
            }
            container red {
              container blue {
                leaf a {
                  type string;
                }
                leaf b {
                  type string;
                }
              }
              leaf yellow-leaf {
                type string;
              }
              anyxml config;
            }
          }
        }
      }
    }
    container list-keys {
      list bits-key {
        key "bit";
        leaf bit {
          type bits {
            bit x;
            bit y;
            bit z;
          }
        }
      }
    }
    container identity-test {
      leaf base-test {
        type identityref {
          base test:crypto-alg;
        }
      }
      leaf mid-level-test {
        type identityref {
          base test:des;
        }
      }
      leaf top-test {
        type identityref {
          base test:des3;
        }
      }
      leaf external-test {
        type identityref {
          base ciena-common-yang:error-does-not-exist;
        }
      }
    }
    container encryption-test-container {
      container container-generate-at-abs-path-enc {
        ciena-common-yang:decrypt "container-generate-at-abs-path";
        ciena-common-yang:decrypt-path "/ciena-common-test/encryption-test-container";
        leaf a {
          type string {
            ciena-common-yang:stringptr "true";
          }
          ciena-common-yang:decrypt "a";
          ciena-common-yang:decrypt-path "/ciena-common-test/encryption-test-container/container-generate-at-abs-path";
        }
        container b {
          ciena-common-yang:decrypt "b";
          ciena-common-yang:decrypt-path "/ciena-common-test/encryption-test-container/container-generate-at-abs-path";
          leaf c {
            type string {
              ciena-common-yang:stringptr "true";
            }
            ciena-common-yang:decrypt "c";
            ciena-common-yang:decrypt-path "/ciena-common-test/encryption-test-container/container-generate-at-abs-path/b";
          }
        }
        config false;
      }
      list encryption-mount-test {
        key "name";
        leaf name {
          type string;
        }
        container data {
          ciena-common-yang:mount-start "ciena-common-test";
          container string-based-return-code-list {
            config false;
            description
              "List of errors in case of command failure";
            list return-code-list {
              leaf instance {
                type string {
                  ciena-common-yang:stringptr "true";
                }
                description
                  "The instance to which the error code applies.";
              }
              leaf error {
                type string;
              }
            }
          }
          uses red-blue-group;
          uses blue-yellow-group;
          container white {
            uses abc_group;
            container cont1 {
              uses abc_group;
            }
            container cont2 {
              uses abc_group;
            }
            container cont3 {
              uses abc_group;
            }
            container cont4 {
              uses abc_group;
            }
            list list1 {
              key "k";
              leaf k {
                type uint8;
              }
              uses abc_group;
            }
          }
          container validation-test {
            uses abc_validate_group;
          }
          container to-pointer-test {
            container a {
              leaf string-test {
                type string;
              }
            }
          }
          list to-pointer-test2 {
            key "first-key";
            leaf first-key {
              type uint8;
            }
            list second-list {
              key "second-key";
              leaf second-key {
                type uint8;
              }
              leaf second-string {
                type string;
              }
              container second-container {
                leaf second-container-string {
                  type string;
                }
              }
            }
          }
          container nested-container {
            container cone {
              leaf a {
                type uint8;
                default "1";
              }
              leaf b {
                type uint8;
                default "2";
              }
              leaf c {
                type uint8;
                default "3";
              }
            }
            container ctwo {
              config false;
              leaf d {
                type uint8;
              }
              leaf e {
                type uint8;
              }
              leaf f {
                type uint8;
              }
            }
          }
          container read-only {
            config false;
            uses red-blue-group;
            container name {
              container collision {
                leaf test {
                  type uint8;
                }
                container child1 {
                  container child2 {
                    leaf test {
                      type uint8;
                    }
                  }
                }
              }
            }
            container name-collision {
              leaf test {
                type uint8;
              }
              container child1 {
                container child2 {
                  leaf test {
                    type uint8;
                  }
                }
              }
            }
          }
          container remove-via-deviation {
            uses red-blue-group;
          }
          uses ordered-lists-group;
          container simple-deadline-test {
            uses deadline-group;
          }
          container simple-test-container {
            ciena-common-yang:containerptr "true";
            list keys-only-list {
              key "name";
              leaf name {
                type string;
              }
            }
            leaf other-attribute {
              type string;
            }
            container leaf-test {
              leaf string-test {
                ciena-common-yang:encrypt "string-test-encrypted";
                ciena-common-yang:encrypt-path "/ciena-common-test/simple-test-container/leaf-test";
                type string;
              }
              leaf string-test-encrypted {
                type string {
                  ciena-common-yang:stringptr "true";
                }
                ciena-common-yang:decrypt "string-test";
                ciena-common-yang:decrypt-path "/ciena-common-test/simple-test-container/leaf-test";
              }
              leaf uint8-test {
                type uint8;
              }
            }
            container presence-test {
              presence "presense test container";
            }
            container presence-test-2 {
              choice start-time {
                mandatory true;
                container immediate {
                  presence "Start the measurement session immediately.";
                }
                leaf relative {
                  type string;
                }
                leaf absolute {
                  type string;
                }
              }
            }
            list outter {
              key "index";
              leaf index {
                type uint8;
              }
              min-elements 2;
              max-elements 3;
              list inner {
                key "name";
                leaf name {
                  type string;
                }
                max-elements 2;
                leaf value {
                  type uint16;
                }
              }
              leaf-list boolean-leaf-list {
                type boolean;
                max-elements 3;
                min-elements 2;
              }
              leaf mode {
                type uint8 {
                  range "0..10";
                }
              }
            }
            list first {
              key "key1 key2";
              leaf key1 {
                type uint8;
              }
              leaf key2 {
                type string;
              }
              list second {
                key "key1 key2";
                leaf key1 {
                  type uint8;
                }
                leaf key2 {
                  type string;
                }
                list third {
                  key "key1";
                  leaf key1 {
                    type uint8;
                  }
                  container red {
                    container blue {
                      leaf a {
                        type string;
                      }
                      leaf b {
                        type string;
                      }
                    }
                    leaf yellow-leaf {
                      type string;
                    }
                    anyxml config;
                  }
                }
              }
            }
          }
          container list-keys {
            list bits-key {
              key "bit";
              leaf bit {
                type bits {
                  bit x;
                  bit y;
                  bit z;
                }
              }
            }
          }
          container identity-test {
            leaf base-test {
              type identityref {
                base test:crypto-alg;
              }
            }
            leaf mid-level-test {
              type identityref {
                base test:des;
              }
            }
            leaf top-test {
              type identityref {
                base test:des3;
              }
            }
            leaf external-test {
              type identityref {
                base ciena-common-yang:error-does-not-exist;
              }
            }
          }
          container encryption-test-container {
            container container-generate-at-abs-path-enc {
              ciena-common-yang:decrypt "container-generate-at-abs-path";
              ciena-common-yang:decrypt-path "/ciena-common-test/encryption-test-container";
              leaf a {
                type string {
                  ciena-common-yang:stringptr "true";
                }
                ciena-common-yang:decrypt "a";
                ciena-common-yang:decrypt-path "/ciena-common-test/encryption-test-container/container-generate-at-abs-path";
              }
              container b {
                ciena-common-yang:decrypt "b";
                ciena-common-yang:decrypt-path "/ciena-common-test/encryption-test-container/container-generate-at-abs-path";
                leaf c {
                  type string {
                    ciena-common-yang:stringptr "true";
                  }
                  ciena-common-yang:decrypt "c";
                  ciena-common-yang:decrypt-path "/ciena-common-test/encryption-test-container/container-generate-at-abs-path/b";
                }
              }
              config false;
            }
            list encryption-mount-test {
              key "name";
              leaf name {
                type string;
              }
              container data {
                ciena-common-yang:mount-start "ciena-common-test";
                ciena-common-yang:mount-end "ciena-common-test";
              }
            }
            list instance {
              key "name";
              leaf name {
                type string;
              }
              container result {
                ciena-common-yang:encrypt "container-1";
                ciena-common-yang:encrypt-path "/ciena-common-test/encryption-test-container/instance";
                list amp {
                  ciena-common-yang:encrypt "amp";
                  ciena-common-yang:encrypt-path "/ciena-common-test/encryption-test-container/instance/container-1";
                  key "amp_name";
                  leaf amp_name {
                    ciena-common-yang:encrypt "amp_name";
                    ciena-common-yang:encrypt-path "/ciena-common-test/encryption-test-container/instance/container-1/amp";
                    type string;
                  }
                  list measurement-no-power {
                    ciena-common-yang:encrypt "measurement-no-power";
                    ciena-common-yang:encrypt-path "/ciena-common-test/encryption-test-container/instance/container-1/amp";
                    description
                      "Power measurements of span measured with all channels blocked.";
                    key "index";
                    leaf index {
                      ciena-common-yang:encrypt "index";
                      ciena-common-yang:encrypt-path "/ciena-common-test/encryption-test-container/instance/container-1/amp/measurement-no-power";
                      type uint8;
                    }
                    leaf in-current-power {
                      ciena-common-yang:encrypt "in-current-power";
                      ciena-common-yang:encrypt-path "/ciena-common-test/encryption-test-container/instance/container-1/amp/measurement-no-power";
                      type decimal64 {
                        fraction-digits 1;
                      }
                    }
                    leaf in-min-power {
                      ciena-common-yang:encrypt "in-min-power";
                      ciena-common-yang:encrypt-path "/ciena-common-test/encryption-test-container/instance/container-1/amp/measurement-no-power";
                      type decimal64 {
                        fraction-digits 1;
                      }
                    }
                    config false;
                  }
                }
              }
              container container-1 {
                ciena-common-yang:decrypt "result";
                ciena-common-yang:decrypt-path "/ciena-common-test/encryption-test-container/instance";
                list amp {
                  ciena-common-yang:decrypt "amp";
                  ciena-common-yang:decrypt-path "/ciena-common-test/encryption-test-container/instance/result";
                  key "amp_name";
                  leaf amp_name {
                    type string {
                      ciena-common-yang:stringptr "true";
                    }
                    ciena-common-yang:decrypt "amp_name";
                    ciena-common-yang:decrypt-path "/ciena-common-test/encryption-test-container/instance/result/amp";
                  }
                  list measurement-no-power {
                    ciena-common-yang:decrypt "measurement-no-power";
                    ciena-common-yang:decrypt-path "/ciena-common-test/encryption-test-container/instance/result/amp";
                    key "index";
                    leaf index {
                      type string {
                        ciena-common-yang:stringptr "true";
                      }
                      ciena-common-yang:decrypt "index";
                      ciena-common-yang:decrypt-path "/ciena-common-test/encryption-test-container/instance/result/amp/measurement-no-power";
                    }
                    leaf in-current-power {
                      type string {
                        ciena-common-yang:stringptr "true";
                      }
                      ciena-common-yang:decrypt "in-current-power";
                      ciena-common-yang:decrypt-path "/ciena-common-test/encryption-test-container/instance/result/amp/measurement-no-power";
                    }
                    leaf in-min-power {
                      type string {
                        ciena-common-yang:stringptr "true";
                      }
                      ciena-common-yang:decrypt "in-min-power";
                      ciena-common-yang:decrypt-path "/ciena-common-test/encryption-test-container/instance/result/amp/measurement-no-power";
                    }
                    config false;
                  }
                }
              }
              list some-other-list {
                key "name";
                leaf name {
                  type string;
                }
                leaf measurement {
                  type uint8;
                }
              }
            }
            list key-in-grouping {
              ciena-common-yang:encrypt "key-in-grouping-encrypted";
              ciena-common-yang:encrypt-path "/ciena-common-test/encryption-test-container";
              description
                "test list key leaf definition can be provided by grouping";
              key "name";
              leaf name {
                ciena-common-yang:encrypt "name";
                ciena-common-yang:encrypt-path "/ciena-common-test/encryption-test-container/key-in-grouping-encrypted";
                type string;
              }
              leaf stats {
                ciena-common-yang:encrypt "stats";
                ciena-common-yang:encrypt-path "/ciena-common-test/encryption-test-container/key-in-grouping-encrypted";
                type uint32;
              }
            }
            list key-in-grouping-encrypted {
              ciena-common-yang:decrypt "key-in-grouping";
              ciena-common-yang:decrypt-path "/ciena-common-test/encryption-test-container";
              key "name";
              leaf name {
                type string {
                  ciena-common-yang:stringptr "true";
                }
                ciena-common-yang:decrypt "name";
                ciena-common-yang:decrypt-path "/ciena-common-test/encryption-test-container/key-in-grouping";
              }
              leaf stats {
                type string {
                  ciena-common-yang:stringptr "true";
                }
                ciena-common-yang:decrypt "stats";
                ciena-common-yang:decrypt-path "/ciena-common-test/encryption-test-container/key-in-grouping";
              }
            }
            list list-enc-generate-with-renamed-leaves {
              ciena-common-yang:encrypt "list-enc-generate-with-renamed-leaves-enc";
              ciena-common-yang:encrypt-path "/ciena-common-test/encryption-test-container";
              description
                "test list encryption with nested containers and leaves renamed";
              key "name";
              leaf name {
                ciena-common-yang:encrypt "name";
                ciena-common-yang:encrypt-path "/ciena-common-test/encryption-test-container/list-enc-generate-with-renamed-leaves-enc";
                type string;
              }
              leaf aaa {
                ciena-common-yang:encrypt "aaa-enc";
                ciena-common-yang:encrypt-path "/ciena-common-test/encryption-test-container/list-enc-generate-with-renamed-leaves-enc";
                type uint8;
                ciena-common-yang:sensitive "true";
              }
              container ddd {
                ciena-common-yang:encrypt "ddd-enc";
                ciena-common-yang:encrypt-path "/ciena-common-test/encryption-test-container/list-enc-generate-with-renamed-leaves-enc";
                leaf eee {
                  ciena-common-yang:encrypt "eee-enc";
                  ciena-common-yang:encrypt-path "/ciena-common-test/encryption-test-container/list-enc-generate-with-renamed-leaves-enc/ddd-enc";
                  type uint8;
                }
                leaf fff {
                  ciena-common-yang:encrypt "fff";
                  ciena-common-yang:encrypt-path "/ciena-common-test/encryption-test-container/list-enc-generate-with-renamed-leaves-enc/ddd-enc";
                  type uint8;
                }
                config false;
              }
            }
            list list-enc-generate-with-renamed-leaves-enc {
              ciena-common-yang:decrypt "list-enc-generate-with-renamed-leaves";
              ciena-common-yang:decrypt-path "/ciena-common-test/encryption-test-container";
              key "name";
              leaf name {
                type string {
                  ciena-common-yang:stringptr "true";
                }
                ciena-common-yang:decrypt "name";
                ciena-common-yang:decrypt-path "/ciena-common-test/encryption-test-container/list-enc-generate-with-renamed-leaves";
              }
              leaf aaa-enc {
                type string {
                  ciena-common-yang:stringptr "true";
                }
                ciena-common-yang:decrypt "aaa";
                ciena-common-yang:decrypt-path "/ciena-common-test/encryption-test-container/list-enc-generate-with-renamed-leaves";
                ciena-common-yang:sensitive "true";
              }
              container ddd-enc {
                ciena-common-yang:decrypt "ddd";
                ciena-common-yang:decrypt-path "/ciena-common-test/encryption-test-container/list-enc-generate-with-renamed-leaves";
                leaf eee-enc {
                  type string {
                    ciena-common-yang:stringptr "true";
                  }
                  ciena-common-yang:decrypt "eee";
                  ciena-common-yang:decrypt-path "/ciena-common-test/encryption-test-container/list-enc-generate-with-renamed-leaves/ddd";
                }
                leaf fff {
                  type string {
                    ciena-common-yang:stringptr "true";
                  }
                  ciena-common-yang:decrypt "fff";
                  ciena-common-yang:decrypt-path "/ciena-common-test/encryption-test-container/list-enc-generate-with-renamed-leaves/ddd";
                }
                config false;
              }
            }
            list list-generate-with-enc-path-for-leaves {
              ciena-common-yang:encrypt "list-generate-with-enc-path-for-leaves-enc";
              ciena-common-yang:encrypt-path "/ciena-common-test/encryption-test-container";
              description
                "test list encryption with some leaves having encryption-path and encryption-relative-path information";
              key "index";
              leaf index {
                ciena-common-yang:encrypt "index-enc";
                ciena-common-yang:encrypt-path "/ciena-common-test/encryption-test-container/list-generate-with-enc-path-for-leaves-enc";
                type uint8;
              }
              leaf ggg {
                ciena-common-yang:encrypt "ggg";
                ciena-common-yang:encrypt-path "/ciena-common-test/encryption-test-container/list-generate-with-enc-path-for-leaves-enc";
                type uint8;
              }
              container hhh {
                ciena-common-yang:encrypt "hhh";
                ciena-common-yang:encrypt-path "/ciena-common-test/encryption-test-container/list-generate-with-enc-path-for-leaves-enc";
                leaf iii {
                  ciena-common-yang:encrypt "iii-enc";
                  ciena-common-yang:encrypt-path "/ciena-common-test/encryption-test-container/list-generate-with-enc-path-for-leaves-enc/hhh";
                  type uint8;
                }
                leaf jjj {
                  ciena-common-yang:encrypt "none-existing-leaf";
                  ciena-common-yang:encrypt-path "/ciena-common-test/encryption-test-container/A/B";
                  type uint8;
                  ciena-common-yang:sensitive "true";
                }
                leaf kkk {
                  ciena-common-yang:encrypt "none-existing-leaf-2";
                  ciena-common-yang:encrypt-path "/ciena-common-test/encryption-test-container/A/B";
                  type uint8;
                  config false;
                  ciena-common-yang:sensitive "true";
                }
              }
            }
            list list-generate-with-enc-path-for-leaves-enc {
              ciena-common-yang:decrypt "list-generate-with-enc-path-for-leaves";
              ciena-common-yang:decrypt-path "/ciena-common-test/encryption-test-container";
              key "index-enc";
              leaf index-enc {
                type string {
                  ciena-common-yang:stringptr "true";
                }
                ciena-common-yang:decrypt "index";
                ciena-common-yang:decrypt-path "/ciena-common-test/encryption-test-container/list-generate-with-enc-path-for-leaves";
              }
              leaf ggg {
                type string {
                  ciena-common-yang:stringptr "true";
                }
                ciena-common-yang:decrypt "ggg";
                ciena-common-yang:decrypt-path "/ciena-common-test/encryption-test-container/list-generate-with-enc-path-for-leaves";
              }
              container hhh {
                ciena-common-yang:decrypt "hhh";
                ciena-common-yang:decrypt-path "/ciena-common-test/encryption-test-container/list-generate-with-enc-path-for-leaves";
                leaf iii-enc {
                  type string {
                    ciena-common-yang:stringptr "true";
                  }
                  ciena-common-yang:decrypt "iii";
                  ciena-common-yang:decrypt-path "/ciena-common-test/encryption-test-container/list-generate-with-enc-path-for-leaves/hhh";
                }
              }
            }
            container A {
              container B {
                leaf none-existing-leaf {
                  ciena-common-yang:decrypt "jjj";
                  ciena-common-yang:decrypt-path "/ciena-common-test/encryption-test-container/list-generate-with-enc-path-for-leaves/hhh";
                  type string {
                    ciena-common-yang:stringptr "true";
                  }
                  ciena-common-yang:sensitive "true";
                }
                leaf none-existing-leaf-2 {
                  ciena-common-yang:decrypt "kkk";
                  ciena-common-yang:decrypt-path "/ciena-common-test/encryption-test-container/list-generate-with-enc-path-for-leaves/hhh";
                  type string {
                    ciena-common-yang:stringptr "true";
                  }
                  ciena-common-yang:sensitive "true";
                  config false;
                }
                leaf y {
                  type string {
                    ciena-common-yang:stringptr "true";
                  }
                }
                leaf z {
                  type uint8;
                }
              }
            }
            container container-generate-as-sibling {
              ciena-common-yang:encrypt "container-generate-as-sibling-enc";
              ciena-common-yang:encrypt-path "/ciena-common-test/encryption-test-container";
              description
                "test simple container encryption default generating as siblings";
              leaf a {
                ciena-common-yang:encrypt "a";
                ciena-common-yang:encrypt-path "/ciena-common-test/encryption-test-container/container-generate-as-sibling-enc";
                type uint8;
              }
              container b {
                ciena-common-yang:encrypt "b";
                ciena-common-yang:encrypt-path "/ciena-common-test/encryption-test-container/container-generate-as-sibling-enc";
                leaf c {
                  ciena-common-yang:encrypt "c";
                  ciena-common-yang:encrypt-path "/ciena-common-test/encryption-test-container/container-generate-as-sibling-enc/b";
                  type uint8;
                }
              }
            }
            container container-generate-as-sibling-enc {
              ciena-common-yang:decrypt "container-generate-as-sibling";
              ciena-common-yang:decrypt-path "/ciena-common-test/encryption-test-container";
              leaf a {
                type string {
                  ciena-common-yang:stringptr "true";
                }
                ciena-common-yang:decrypt "a";
                ciena-common-yang:decrypt-path "/ciena-common-test/encryption-test-container/container-generate-as-sibling";
              }
              container b {
                ciena-common-yang:decrypt "b";
                ciena-common-yang:decrypt-path "/ciena-common-test/encryption-test-container/container-generate-as-sibling";
                leaf c {
                  type string {
                    ciena-common-yang:stringptr "true";
                  }
                  ciena-common-yang:decrypt "c";
                  ciena-common-yang:decrypt-path "/ciena-common-test/encryption-test-container/container-generate-as-sibling/b";
                }
              }
            }
            container X {
              container Z {
                container container-generate-at-relative-path {
                  ciena-common-yang:encrypt "container-generate-at-relative-path-enc";
                  ciena-common-yang:encrypt-path "/ciena-common-test/encryption-test-container/K";
                  description
                    "test container encryption with encrypt-relative-path information";
                  container red {
                    ciena-common-yang:encrypt "red";
                    ciena-common-yang:encrypt-path "/ciena-common-test/encryption-test-container/K/container-generate-at-relative-path-enc";
                    container blue {
                      ciena-common-yang:encrypt "blue";
                      ciena-common-yang:encrypt-path "/ciena-common-test/encryption-test-container/K/container-generate-at-relative-path-enc/red";
                      leaf a {
                        ciena-common-yang:encrypt "a";
                        ciena-common-yang:encrypt-path "/ciena-common-test/encryption-test-container/K/container-generate-at-relative-path-enc/red/blue";
                        type uint8;
                      }
                      leaf b {
                        ciena-common-yang:encrypt "b";
                        ciena-common-yang:encrypt-path "/ciena-common-test/encryption-test-container/K/container-generate-at-relative-path-enc/red/blue";
                        type uint8;
                        default "22";
                      }
                      leaf c {
                        ciena-common-yang:encrypt "c";
                        ciena-common-yang:encrypt-path "/ciena-common-test/encryption-test-container/K/container-generate-at-relative-path-enc/red/blue";
                        type uint8;
                        default "44";
                      }
                      leaf d {
                        ciena-common-yang:encrypt "d";
                        ciena-common-yang:encrypt-path "/ciena-common-test/encryption-test-container/K/container-generate-at-relative-path-enc/red/blue";
                        type uint8;
                        default "88";
                      }
                    }
                  }
                  leaf a {
                    ciena-common-yang:encrypt "a";
                    ciena-common-yang:encrypt-path "/ciena-common-test/encryption-test-container/K/container-generate-at-relative-path-enc";
                    type uint8;
                  }
                  container b {
                    ciena-common-yang:encrypt "b";
                    ciena-common-yang:encrypt-path "/ciena-common-test/encryption-test-container/K/container-generate-at-relative-path-enc";
                    container red {
                      ciena-common-yang:encrypt "red";
                      ciena-common-yang:encrypt-path "/ciena-common-test/encryption-test-container/K/container-generate-at-relative-path-enc/b";
                      container blue {
                        ciena-common-yang:encrypt "blue";
                        ciena-common-yang:encrypt-path "/ciena-common-test/encryption-test-container/K/container-generate-at-relative-path-enc/b/red";
                        leaf a {
                          ciena-common-yang:encrypt "a";
                          ciena-common-yang:encrypt-path "/ciena-common-test/encryption-test-container/K/container-generate-at-relative-path-enc/b/red/blue";
                          type uint8;
                        }
                        leaf b {
                          ciena-common-yang:encrypt "b";
                          ciena-common-yang:encrypt-path "/ciena-common-test/encryption-test-container/K/container-generate-at-relative-path-enc/b/red/blue";
                          type uint8;
                          default "22";
                        }
                        leaf c {
                          ciena-common-yang:encrypt "c";
                          ciena-common-yang:encrypt-path "/ciena-common-test/encryption-test-container/K/container-generate-at-relative-path-enc/b/red/blue";
                          type uint8;
                          default "44";
                        }
                        leaf d {
                          ciena-common-yang:encrypt "d";
                          ciena-common-yang:encrypt-path "/ciena-common-test/encryption-test-container/K/container-generate-at-relative-path-enc/b/red/blue";
                          type uint8;
                          default "88";
                        }
                      }
                    }
                    leaf c {
                      ciena-common-yang:encrypt "c";
                      ciena-common-yang:encrypt-path "/ciena-common-test/encryption-test-container/K/container-generate-at-relative-path-enc/b";
                      type uint8;
                    }
                  }
                  config false;
                }
              }
            }
            container K {
              container container-generate-at-relative-path-enc {
                ciena-common-yang:decrypt "container-generate-at-relative-path";
                ciena-common-yang:decrypt-path "/ciena-common-test/encryption-test-container/X/Z";
                container red {
                  ciena-common-yang:decrypt "red";
                  ciena-common-yang:decrypt-path "/ciena-common-test/encryption-test-container/X/Z/container-generate-at-relative-path";
                  container blue {
                    ciena-common-yang:decrypt "blue";
                    ciena-common-yang:decrypt-path "/ciena-common-test/encryption-test-container/X/Z/container-generate-at-relative-path/red";
                    leaf a {
                      type string {
                        ciena-common-yang:stringptr "true";
                      }
                      ciena-common-yang:decrypt "a";
                      ciena-common-yang:decrypt-path "/ciena-common-test/encryption-test-container/X/Z/container-generate-at-relative-path/red/blue";
                    }
                    leaf b {
                      type string {
                        ciena-common-yang:stringptr "true";
                      }
                      ciena-common-yang:decrypt "b";
                      ciena-common-yang:decrypt-path "/ciena-common-test/encryption-test-container/X/Z/container-generate-at-relative-path/red/blue";
                    }
                    leaf c {
                      type string {
                        ciena-common-yang:stringptr "true";
                      }
                      ciena-common-yang:decrypt "c";
                      ciena-common-yang:decrypt-path "/ciena-common-test/encryption-test-container/X/Z/container-generate-at-relative-path/red/blue";
                    }
                    leaf d {
                      type string {
                        ciena-common-yang:stringptr "true";
                      }
                      ciena-common-yang:decrypt "d";
                      ciena-common-yang:decrypt-path "/ciena-common-test/encryption-test-container/X/Z/container-generate-at-relative-path/red/blue";
                    }
                  }
                }
                leaf a {
                  type string {
                    ciena-common-yang:stringptr "true";
                  }
                  ciena-common-yang:decrypt "a";
                  ciena-common-yang:decrypt-path "/ciena-common-test/encryption-test-container/X/Z/container-generate-at-relative-path";
                }
                container b {
                  ciena-common-yang:decrypt "b";
                  ciena-common-yang:decrypt-path "/ciena-common-test/encryption-test-container/X/Z/container-generate-at-relative-path";
                  container red {
                    ciena-common-yang:decrypt "red";
                    ciena-common-yang:decrypt-path "/ciena-common-test/encryption-test-container/X/Z/container-generate-at-relative-path/b";
                    container blue {
                      ciena-common-yang:decrypt "blue";
                      ciena-common-yang:decrypt-path "/ciena-common-test/encryption-test-container/X/Z/container-generate-at-relative-path/b/red";
                      leaf a {
                        type string {
                          ciena-common-yang:stringptr "true";
                        }
                        ciena-common-yang:decrypt "a";
                        ciena-common-yang:decrypt-path "/ciena-common-test/encryption-test-container/X/Z/container-generate-at-relative-path/b/red/blue";
                      }
                      leaf b {
                        type string {
                          ciena-common-yang:stringptr "true";
                        }
                        ciena-common-yang:decrypt "b";
                        ciena-common-yang:decrypt-path "/ciena-common-test/encryption-test-container/X/Z/container-generate-at-relative-path/b/red/blue";
                      }
                      leaf c {
                        type string {
                          ciena-common-yang:stringptr "true";
                        }
                        ciena-common-yang:decrypt "c";
                        ciena-common-yang:decrypt-path "/ciena-common-test/encryption-test-container/X/Z/container-generate-at-relative-path/b/red/blue";
                      }
                      leaf d {
                        type string {
                          ciena-common-yang:stringptr "true";
                        }
                        ciena-common-yang:decrypt "d";
                        ciena-common-yang:decrypt-path "/ciena-common-test/encryption-test-container/X/Z/container-generate-at-relative-path/b/red/blue";
                      }
                    }
                  }
                  leaf c {
                    type string {
                      ciena-common-yang:stringptr "true";
                    }
                    ciena-common-yang:decrypt "c";
                    ciena-common-yang:decrypt-path "/ciena-common-test/encryption-test-container/X/Z/container-generate-at-relative-path/b";
                  }
                }
                config false;
              }
              leaf l {
                type uint8;
              }
            }
            container container-generate-at-abs-path {
              ciena-common-yang:encrypt "container-generate-at-abs-path-enc";
              ciena-common-yang:encrypt-path "/ciena-common-test/encryption-test-container";
              description
                "test container encryption with absolute path encrypt-path information";
              leaf a {
                ciena-common-yang:encrypt "a";
                ciena-common-yang:encrypt-path "/ciena-common-test/encryption-test-container/container-generate-at-abs-path-enc";
                type uint8;
              }
              container b {
                ciena-common-yang:encrypt "b";
                ciena-common-yang:encrypt-path "/ciena-common-test/encryption-test-container/container-generate-at-abs-path-enc";
                leaf c {
                  ciena-common-yang:encrypt "c";
                  ciena-common-yang:encrypt-path "/ciena-common-test/encryption-test-container/container-generate-at-abs-path-enc/b";
                  type uint8;
                }
              }
              config false;
            }
            container encrypt-to-existing-container {
              ciena-common-yang:encrypt "encrypt-to-existing-container-encrypted";
              ciena-common-yang:encrypt-path "/ciena-common-test/encryption-test-container";
              description
                "test container encryption to existing container. no generation will happen.";
              leaf a {
                ciena-common-yang:encrypt "a";
                ciena-common-yang:encrypt-path "/ciena-common-test/encryption-test-container/encrypt-to-existing-container-encrypted";
                type uint8;
              }
            }
            container encrypt-to-existing-container-encrypted {
              ciena-common-yang:decrypt "encrypt-to-existing-container";
              ciena-common-yang:decrypt-path "/ciena-common-test/encryption-test-container";
              leaf a {
                ciena-common-yang:decrypt "a";
                ciena-common-yang:decrypt-path "/ciena-common-test/encryption-test-container/encrypt-to-existing-container";
                type string {
                  ciena-common-yang:stringptr "true";
                }
              }
            }
            container outter-container {
              ciena-common-yang:encrypt "outter-container-enc";
              ciena-common-yang:encrypt-path "/ciena-common-test/encryption-test-container";
              description
                "simple nested container test";
              leaf aaa {
                ciena-common-yang:encrypt "aaa";
                ciena-common-yang:encrypt-path "/ciena-common-test/encryption-test-container/outter-container-enc";
                type uint8;
              }
              container middle-container {
                ciena-common-yang:encrypt "middle-container";
                ciena-common-yang:encrypt-path "/ciena-common-test/encryption-test-container/outter-container-enc";
                leaf bbb {
                  ciena-common-yang:encrypt "bbb";
                  ciena-common-yang:encrypt-path "/ciena-common-test/encryption-test-container/outter-container-enc/middle-container";
                  type uint8;
                }
                container inner-container {
                  ciena-common-yang:encrypt "inner-container";
                  ciena-common-yang:encrypt-path "/ciena-common-test/encryption-test-container/outter-container-enc/middle-container";
                  leaf ccc {
                    ciena-common-yang:encrypt "ccc";
                    ciena-common-yang:encrypt-path "/ciena-common-test/encryption-test-container/outter-container-enc/middle-container/inner-container";
                    type uint8;
                  }
                }
              }
            }
            container outter-container-enc {
              ciena-common-yang:decrypt "outter-container";
              ciena-common-yang:decrypt-path "/ciena-common-test/encryption-test-container";
              leaf aaa {
                type string {
                  ciena-common-yang:stringptr "true";
                }
                ciena-common-yang:decrypt "aaa";
                ciena-common-yang:decrypt-path "/ciena-common-test/encryption-test-container/outter-container";
              }
              container middle-container {
                ciena-common-yang:decrypt "middle-container";
                ciena-common-yang:decrypt-path "/ciena-common-test/encryption-test-container/outter-container";
                leaf bbb {
                  type string {
                    ciena-common-yang:stringptr "true";
                  }
                  ciena-common-yang:decrypt "bbb";
                  ciena-common-yang:decrypt-path "/ciena-common-test/encryption-test-container/outter-container/middle-container";
                }
                container inner-container {
                  ciena-common-yang:decrypt "inner-container";
                  ciena-common-yang:decrypt-path "/ciena-common-test/encryption-test-container/outter-container/middle-container";
                  leaf ccc {
                    type string {
                      ciena-common-yang:stringptr "true";
                    }
                    ciena-common-yang:decrypt "ccc";
                    ciena-common-yang:decrypt-path "/ciena-common-test/encryption-test-container/outter-container/middle-container/inner-container";
                  }
                }
              }
            }
            container one-to-two-container {
              ciena-common-yang:encrypt "one-to-two-container-enc";
              ciena-common-yang:encrypt-path "/ciena-common-test/encryption-test-container";
              description
                "error scenario test: leaves under one container encrypted to two containers
                 is not fully supported, the leaves for one container will be missing";
              leaf aaa {
                ciena-common-yang:encrypt "aaa";
                ciena-common-yang:encrypt-path "/ciena-common-test/encryption-test-container/one-to-two-container-enc";
                type uint8;
              }
              leaf-list bbb {
                ciena-common-yang:encrypt "bbb";
                ciena-common-yang:encrypt-path "/ciena-common-test/encryption-test-container/one-to-two-container-other";
                type uint8;
              }
              container inner-container {
                ciena-common-yang:encrypt "inner-container";
                ciena-common-yang:encrypt-path "/ciena-common-test/encryption-test-container/one-to-two-container-enc";
                leaf-list ccc {
                  ciena-common-yang:encrypt "ccc";
                  ciena-common-yang:encrypt-path "/ciena-common-test/encryption-test-container/one-to-two-container-enc/inner-container";
                  type uint8;
                }
                leaf ddd {
                  ciena-common-yang:encrypt "ddd";
                  ciena-common-yang:encrypt-path "/ciena-common-test/encryption-test-container/one-to-two-container-other";
                  type uint8;
                }
              }
            }
            container one-to-two-container-enc {
              ciena-common-yang:decrypt "one-to-two-container";
              ciena-common-yang:decrypt-path "/ciena-common-test/encryption-test-container";
              leaf aaa {
                type string {
                  ciena-common-yang:stringptr "true";
                }
                ciena-common-yang:decrypt "aaa";
                ciena-common-yang:decrypt-path "/ciena-common-test/encryption-test-container/one-to-two-container";
              }
              container inner-container {
                ciena-common-yang:decrypt "inner-container";
                ciena-common-yang:decrypt-path "/ciena-common-test/encryption-test-container/one-to-two-container";
                leaf-list ccc {
                  type string {
                    ciena-common-yang:stringptr "true";
                  }
                  ciena-common-yang:decrypt "ccc";
                  ciena-common-yang:decrypt-path "/ciena-common-test/encryption-test-container/one-to-two-container/inner-container";
                }
              }
            }
            container one-to-two-container-other {
              leaf-list bbb {
                ciena-common-yang:decrypt "bbb";
                ciena-common-yang:decrypt-path "/ciena-common-test/encryption-test-container/one-to-two-container";
                type string {
                  ciena-common-yang:stringptr "true";
                }
              }
              leaf ddd {
                ciena-common-yang:decrypt "ddd";
                ciena-common-yang:decrypt-path "/ciena-common-test/encryption-test-container/one-to-two-container/inner-container";
                type string {
                  ciena-common-yang:stringptr "true";
                }
              }
              leaf fff {
                type uint8;
              }
            }
            list nested-list {
              ciena-common-yang:encrypt "nested-list-enc";
              ciena-common-yang:encrypt-path "/ciena-common-test/encryption-test-container";
              description
                "test nested list encryption";
              key "name";
              leaf name {
                ciena-common-yang:encrypt "name";
                ciena-common-yang:encrypt-path "/ciena-common-test/encryption-test-container/nested-list-enc";
                type stringptr;
              }
              leaf aaa {
                ciena-common-yang:encrypt "aaa";
                ciena-common-yang:encrypt-path "/ciena-common-test/encryption-test-container/nested-list-enc";
                type uint8;
              }
              list inner-list {
                ciena-common-yang:encrypt "inner-list";
                ciena-common-yang:encrypt-path "/ciena-common-test/encryption-test-container/nested-list-enc";
                key "index";
                leaf index {
                  ciena-common-yang:encrypt "index";
                  ciena-common-yang:encrypt-path "/ciena-common-test/encryption-test-container/nested-list-enc/inner-list";
                  type uint8;
                }
                leaf-list ccc {
                  ciena-common-yang:encrypt "ccc";
                  ciena-common-yang:encrypt-path "/ciena-common-test/encryption-test-container/nested-list-enc/inner-list";
                  type string;
                }
              }
            }
            list nested-list-enc {
              ciena-common-yang:decrypt "nested-list";
              ciena-common-yang:decrypt-path "/ciena-common-test/encryption-test-container";
              key "name";
              leaf name {
                type string {
                  ciena-common-yang:stringptr "true";
                }
                ciena-common-yang:decrypt "name";
                ciena-common-yang:decrypt-path "/ciena-common-test/encryption-test-container/nested-list";
              }
              leaf aaa {
                type string {
                  ciena-common-yang:stringptr "true";
                }
                ciena-common-yang:decrypt "aaa";
                ciena-common-yang:decrypt-path "/ciena-common-test/encryption-test-container/nested-list";
              }
              list inner-list {
                ciena-common-yang:decrypt "inner-list";
                ciena-common-yang:decrypt-path "/ciena-common-test/encryption-test-container/nested-list";
                key "index";
                leaf index {
                  type string {
                    ciena-common-yang:stringptr "true";
                  }
                  ciena-common-yang:decrypt "index";
                  ciena-common-yang:decrypt-path "/ciena-common-test/encryption-test-container/nested-list/inner-list";
                }
                leaf-list ccc {
                  type string {
                    ciena-common-yang:stringptr "true";
                  }
                  ciena-common-yang:decrypt "ccc";
                  ciena-common-yang:decrypt-path "/ciena-common-test/encryption-test-container/nested-list/inner-list";
                }
              }
            }
            container other {
              leaf ccc {
                type string;
              }
            }
            container user-defined-leaves {
              description
                "selected leaves encryption container";
              leaf a {
                ciena-common-yang:encrypt "x";
                ciena-common-yang:encrypt-path "/ciena-common-test/encryption-test-container/user-defined-leaves-encrypted";
                type string;
              }
              leaf b {
                type string;
              }
            }
            container user-defined-leaves-encrypted {
              leaf x {
                ciena-common-yang:decrypt "a";
                ciena-common-yang:decrypt-path "/ciena-common-test/encryption-test-container/user-defined-leaves";
                type string;
              }
            }
            list nested-list-leaf-encryption {
              key "name";
              leaf name {
                type string;
              }
              leaf x {
                ciena-common-yang:encrypt "x-enc";
                ciena-common-yang:encrypt-path "/ciena-common-test/encryption-test-container/nested-list-leaf-encryption";
                type string;
              }
              leaf x-enc {
                type string {
                  ciena-common-yang:stringptr "true";
                }
                ciena-common-yang:decrypt "x";
                ciena-common-yang:decrypt-path "/ciena-common-test/encryption-test-container/nested-list-leaf-encryption";
              }
              list inner {
                key "index";
                leaf index {
                  type uint8;
                }
                leaf u {
                  ciena-common-yang:encrypt "u-enc";
                  ciena-common-yang:encrypt-path "/ciena-common-test/encryption-test-container/nested-list-leaf-encryption/inner";
                  type string;
                }
                leaf u-enc {
                  type string {
                    ciena-common-yang:stringptr "true";
                  }
                  ciena-common-yang:decrypt "u";
                  ciena-common-yang:decrypt-path "/ciena-common-test/encryption-test-container/nested-list-leaf-encryption/inner";
                }
              }
            }
            list encryption-list-test {
              key "key1 key2";
              leaf key1 {
                type stringptr;
              }
              leaf key2 {
                type typetest;
              }
              container leaf-list-test {
                leaf-list binary-test {
                  ciena-common-yang:encrypt "binary-test-encrypted";
                  ciena-common-yang:encrypt-path "/ciena-common-test/encryption-test-container/encryption-list-test/leaf-list-test";
                  type binary;
                }
                leaf-list binary-test-encrypted {
                  type string {
                    ciena-common-yang:stringptr "true";
                  }
                  ciena-common-yang:decrypt "binary-test";
                  ciena-common-yang:decrypt-path "/ciena-common-test/encryption-test-container/encryption-list-test/leaf-list-test";
                }
                leaf-list bits-test {
                  ciena-common-yang:encrypt "bits-test-encrypted";
                  ciena-common-yang:encrypt-path "/ciena-common-test/encryption-test-container/encryption-list-test/leaf-list-test";
                  type bits {
                    bit disable-nagle {
                      position 0;
                    }
                    bit auto-sense-speed {
                      position 1;
                    }
                  }
                }
                leaf-list bits-test-encrypted {
                  type string {
                    ciena-common-yang:stringptr "true";
                  }
                  ciena-common-yang:decrypt "bits-test";
                  ciena-common-yang:decrypt-path "/ciena-common-test/encryption-test-container/encryption-list-test/leaf-list-test";
                }
                leaf-list boolean-test {
                  ciena-common-yang:encrypt "boolean-test-encrypted";
                  ciena-common-yang:encrypt-path "/ciena-common-test/encryption-test-container/encryption-list-test/leaf-list-test";
                  type boolean;
                }
                leaf-list boolean-test-encrypted {
                  type string {
                    ciena-common-yang:stringptr "true";
                  }
                  ciena-common-yang:decrypt "boolean-test";
                  ciena-common-yang:decrypt-path "/ciena-common-test/encryption-test-container/encryption-list-test/leaf-list-test";
                }
                leaf-list decimal64-test {
                  ciena-common-yang:encrypt "decimal64-test-encrypted";
                  ciena-common-yang:encrypt-path "/ciena-common-test/encryption-test-container/encryption-list-test/leaf-list-test";
                  type decimal64 {
                    fraction-digits 10;
                  }
                }
                leaf-list decimal64-test-encrypted {
                  type string {
                    ciena-common-yang:stringptr "true";
                  }
                  ciena-common-yang:decrypt "decimal64-test";
                  ciena-common-yang:decrypt-path "/ciena-common-test/encryption-test-container/encryption-list-test/leaf-list-test";
                }
                leaf-list empty-test {
                  ciena-common-yang:encrypt "empty-test-encrypted";
                  ciena-common-yang:encrypt-path "/ciena-common-test/encryption-test-container/encryption-list-test/leaf-list-test";
                  type empty;
                }
                leaf-list empty-test-encrypted {
                  type string {
                    ciena-common-yang:stringptr "true";
                  }
                  ciena-common-yang:decrypt "empty-test";
                  ciena-common-yang:decrypt-path "/ciena-common-test/encryption-test-container/encryption-list-test/leaf-list-test";
                }
                leaf-list enumeration-test {
                  ciena-common-yang:encrypt "enumeration-test-encrypted";
                  ciena-common-yang:encrypt-path "/ciena-common-test/encryption-test-container/encryption-list-test/leaf-list-test";
                  type enumeration {
                    enum test-a;
                    enum test-b;
                    enum test-c;
                    enum map;
                  }
                }
                leaf-list enumeration-test-encrypted {
                  type string {
                    ciena-common-yang:stringptr "true";
                  }
                  ciena-common-yang:decrypt "enumeration-test";
                  ciena-common-yang:decrypt-path "/ciena-common-test/encryption-test-container/encryption-list-test/leaf-list-test";
                }
                leaf-list identityref-test {
                  ciena-common-yang:encrypt "identityref-test-encrypted";
                  ciena-common-yang:encrypt-path "/ciena-common-test/encryption-test-container/encryption-list-test/leaf-list-test";
                  type identityref {
                    base test:crypto-alg;
                  }
                }
                leaf-list identityref-test-encrypted {
                  type string {
                    ciena-common-yang:stringptr "true";
                  }
                  ciena-common-yang:decrypt "identityref-test";
                  ciena-common-yang:decrypt-path "/ciena-common-test/encryption-test-container/encryption-list-test/leaf-list-test";
                }
                leaf-list instance-identifier-test {
                  ciena-common-yang:encrypt "instance-identifier-test-encrypted";
                  ciena-common-yang:encrypt-path "/ciena-common-test/encryption-test-container/encryption-list-test/leaf-list-test";
                  type instance-identifier;
                }
                leaf-list instance-identifier-test-encrypted {
                  type string {
                    ciena-common-yang:stringptr "true";
                  }
                  ciena-common-yang:decrypt "instance-identifier-test";
                  ciena-common-yang:decrypt-path "/ciena-common-test/encryption-test-container/encryption-list-test/leaf-list-test";
                }
                leaf-list leafref-test {
                  ciena-common-yang:encrypt "leafref-test-encrypted";
                  ciena-common-yang:encrypt-path "/ciena-common-test/encryption-test-container/encryption-list-test/leaf-list-test";
                  type leafref {
                    path "/test:red/test:blue/test:b";
                  }
                }
                leaf-list leafref-test-encrypted {
                  type string {
                    ciena-common-yang:stringptr "true";
                  }
                  ciena-common-yang:decrypt "leafref-test";
                  ciena-common-yang:decrypt-path "/ciena-common-test/encryption-test-container/encryption-list-test/leaf-list-test";
                }
                leaf-list stringptr-test {
                  ciena-common-yang:encrypt "stringptr-test-encrypted";
                  ciena-common-yang:encrypt-path "/ciena-common-test/encryption-test-container/encryption-list-test/leaf-list-test";
                  type stringptr;
                }
                leaf-list stringptr-test-encrypted {
                  type string {
                    ciena-common-yang:stringptr "true";
                  }
                  ciena-common-yang:decrypt "stringptr-test";
                  ciena-common-yang:decrypt-path "/ciena-common-test/encryption-test-container/encryption-list-test/leaf-list-test";
                }
                leaf-list string-test {
                  ciena-common-yang:encrypt "string-test-encrypted";
                  ciena-common-yang:encrypt-path "/ciena-common-test/encryption-test-container/encryption-list-test/leaf-list-test";
                  type string;
                }
                leaf-list string-test-encrypted {
                  type string {
                    ciena-common-yang:stringptr "true";
                  }
                  ciena-common-yang:decrypt "string-test";
                  ciena-common-yang:decrypt-path "/ciena-common-test/encryption-test-container/encryption-list-test/leaf-list-test";
                }
                leaf-list uint8-test {
                  ciena-common-yang:encrypt "uint8-test-encrypted";
                  ciena-common-yang:encrypt-path "/ciena-common-test/encryption-test-container/encryption-list-test/leaf-list-test";
                  type uint8;
                }
                leaf-list uint8-test-encrypted {
                  type string {
                    ciena-common-yang:stringptr "true";
                  }
                  ciena-common-yang:decrypt "uint8-test";
                  ciena-common-yang:decrypt-path "/ciena-common-test/encryption-test-container/encryption-list-test/leaf-list-test";
                }
                leaf-list union-test {
                  ciena-common-yang:encrypt "union-test-encrypted";
                  ciena-common-yang:encrypt-path "/ciena-common-test/encryption-test-container/encryption-list-test/leaf-list-test";
                  type union {
                    type int32;
                    type enumeration {
                      enum unbounded;
                    }
                  }
                }
                leaf-list union-test-encrypted {
                  type string {
                    ciena-common-yang:stringptr "true";
                  }
                  ciena-common-yang:decrypt "union-test";
                  ciena-common-yang:decrypt-path "/ciena-common-test/encryption-test-container/encryption-list-test/leaf-list-test";
                }
              }
              container leaf-test {
                leaf binary-test {
                  ciena-common-yang:encrypt "binary-test-encrypted";
                  ciena-common-yang:encrypt-path "/ciena-common-test/encryption-test-container/encryption-list-test/leaf-test";
                  type binary;
                  ciena-common-yang:sensitive "true";
                }
                leaf binary-test-encrypted {
                  type string {
                    ciena-common-yang:stringptr "true";
                  }
                  ciena-common-yang:decrypt "binary-test";
                  ciena-common-yang:decrypt-path "/ciena-common-test/encryption-test-container/encryption-list-test/leaf-test";
                  ciena-common-yang:sensitive "true";
                }
                leaf bits-test {
                  ciena-common-yang:encrypt "bits-test-encrypted";
                  ciena-common-yang:encrypt-path "/ciena-common-test/encryption-test-container/encryption-list-test/leaf-test";
                  ciena-common-yang:sensitive "true";
                  type bits {
                    bit apple {
                      position 0;
                    }
                    bit orange {
                      position 1;
                    }
                    bit banana {
                      position 2;
                    }
                  }
                }
                leaf bits-test-encrypted {
                  type string {
                    ciena-common-yang:stringptr "true";
                  }
                  ciena-common-yang:decrypt "bits-test";
                  ciena-common-yang:decrypt-path "/ciena-common-test/encryption-test-container/encryption-list-test/leaf-test";
                  ciena-common-yang:sensitive "true";
                }
                leaf offset-bits-test {
                  ciena-common-yang:encrypt "offset-bits-test-encrypted";
                  ciena-common-yang:encrypt-path "/ciena-common-test/encryption-test-container/encryption-list-test/leaf-test";
                  ciena-common-yang:sensitive "true";
                  type bits {
                    bit apple {
                      position 3;
                    }
                    bit orange {
                      position 5;
                    }
                    bit banana {
                      position 7;
                    }
                  }
                }
                leaf offset-bits-test-encrypted {
                  type string {
                    ciena-common-yang:stringptr "true";
                  }
                  ciena-common-yang:decrypt "offset-bits-test";
                  ciena-common-yang:decrypt-path "/ciena-common-test/encryption-test-container/encryption-list-test/leaf-test";
                  ciena-common-yang:sensitive "true";
                }
                leaf boolean-test {
                  ciena-common-yang:encrypt "boolean-test-encrypted";
                  ciena-common-yang:encrypt-path "/ciena-common-test/encryption-test-container/encryption-list-test/leaf-test";
                  ciena-common-yang:sensitive "true";
                  type boolean;
                }
                leaf boolean-test-encrypted {
                  type string {
                    ciena-common-yang:stringptr "true";
                  }
                  ciena-common-yang:decrypt "boolean-test";
                  ciena-common-yang:decrypt-path "/ciena-common-test/encryption-test-container/encryption-list-test/leaf-test";
                  ciena-common-yang:sensitive "true";
                }
                leaf decimal64-test {
                  ciena-common-yang:encrypt "decimal64-test-encrypted";
                  ciena-common-yang:encrypt-path "/ciena-common-test/encryption-test-container/encryption-list-test/leaf-test";
                  ciena-common-yang:sensitive "true";
                  type decimal64 {
                    fraction-digits 2;
                  }
                }
                leaf decimal64-test-encrypted {
                  type string {
                    ciena-common-yang:stringptr "true";
                  }
                  ciena-common-yang:decrypt "decimal64-test";
                  ciena-common-yang:decrypt-path "/ciena-common-test/encryption-test-container/encryption-list-test/leaf-test";
                  ciena-common-yang:sensitive "true";
                }
                leaf empty-test {
                  ciena-common-yang:encrypt "empty-test-encrypted";
                  ciena-common-yang:encrypt-path "/ciena-common-test/encryption-test-container/encryption-list-test/leaf-test";
                  ciena-common-yang:sensitive "true";
                  type empty;
                }
                leaf empty-test-encrypted {
                  type string {
                    ciena-common-yang:stringptr "true";
                  }
                  ciena-common-yang:decrypt "empty-test";
                  ciena-common-yang:decrypt-path "/ciena-common-test/encryption-test-container/encryption-list-test/leaf-test";
                  ciena-common-yang:sensitive "true";
                }
                leaf enumeration-test {
                  ciena-common-yang:encrypt "enumeration-test-encrypted";
                  ciena-common-yang:encrypt-path "/ciena-common-test/encryption-test-container/encryption-list-test/leaf-test";
                  ciena-common-yang:sensitive "true";
                  type enumeration {
                    enum test-1;
                    enum test-2;
                    enum test-3;
                  }
                }
                leaf enumeration-test-encrypted {
                  type string {
                    ciena-common-yang:stringptr "true";
                  }
                  ciena-common-yang:decrypt "enumeration-test";
                  ciena-common-yang:decrypt-path "/ciena-common-test/encryption-test-container/encryption-list-test/leaf-test";
                  ciena-common-yang:sensitive "true";
                }
                leaf enumeration-extended-test {
                  ciena-common-yang:encrypt "enumeration-extended-test-encrypted";
                  ciena-common-yang:encrypt-path "/ciena-common-test/encryption-test-container/encryption-list-test/leaf-test";
                  ciena-common-yang:sensitive "true";
                  type enumeration {
                    enum forty-one {
                      value 41;
                    }
                    enum ten {
                      value 10;
                    }
                    enum seven {
                      value 7;
                    }
                  }
                }
                leaf enumeration-extended-test-encrypted {
                  type string {
                    ciena-common-yang:stringptr "true";
                  }
                  ciena-common-yang:decrypt "enumeration-extended-test";
                  ciena-common-yang:decrypt-path "/ciena-common-test/encryption-test-container/encryption-list-test/leaf-test";
                  ciena-common-yang:sensitive "true";
                }
                leaf identityref-test {
                  ciena-common-yang:encrypt "identifyref-test-encrypted";
                  ciena-common-yang:encrypt-path "/ciena-common-test/encryption-test-container/encryption-list-test/leaf-test";
                  ciena-common-yang:sensitive "true";
                  type identityref {
                    base test:crypto-alg;
                  }
                }
                leaf identifyref-test-encrypted {
                  type string {
                    ciena-common-yang:stringptr "true";
                  }
                  ciena-common-yang:decrypt "identityref-test";
                  ciena-common-yang:decrypt-path "/ciena-common-test/encryption-test-container/encryption-list-test/leaf-test";
                  ciena-common-yang:sensitive "true";
                }
                leaf instance-identifier-test {
                  ciena-common-yang:encrypt "instance-identifier-test-encrypted";
                  ciena-common-yang:encrypt-path "/ciena-common-test/encryption-test-container/encryption-list-test/leaf-test";
                  ciena-common-yang:sensitive "true";
                  type instance-identifier;
                }
                leaf instance-identifier-test-encrypted {
                  type string {
                    ciena-common-yang:stringptr "true";
                  }
                  ciena-common-yang:decrypt "instance-identifier-test";
                  ciena-common-yang:decrypt-path "/ciena-common-test/encryption-test-container/encryption-list-test/leaf-test";
                  ciena-common-yang:sensitive "true";
                }
                leaf int64-test {
                  ciena-common-yang:encrypt "int64-test-encrypted";
                  ciena-common-yang:encrypt-path "/ciena-common-test/encryption-test-container/encryption-list-test/leaf-test";
                  ciena-common-yang:sensitive "true";
                  type int64;
                }
                leaf int64-test-encrypted {
                  type string {
                    ciena-common-yang:stringptr "true";
                  }
                  ciena-common-yang:decrypt "int64-test";
                  ciena-common-yang:decrypt-path "/ciena-common-test/encryption-test-container/encryption-list-test/leaf-test";
                  ciena-common-yang:sensitive "true";
                }
                leaf leafref-test {
                  ciena-common-yang:encrypt "leafref-test-encrypted";
                  ciena-common-yang:encrypt-path "/ciena-common-test/encryption-test-container/encryption-list-test/leaf-test";
                  ciena-common-yang:sensitive "true";
                  type leafref {
                    path "/test:red/test:blue/test:c";
                  }
                }
                leaf leafref-test-encrypted {
                  type string {
                    ciena-common-yang:stringptr "true";
                  }
                  ciena-common-yang:decrypt "leafref-test";
                  ciena-common-yang:decrypt-path "/ciena-common-test/encryption-test-container/encryption-list-test/leaf-test";
                  ciena-common-yang:sensitive "true";
                }
                leaf stringptr-test {
                  ciena-common-yang:encrypt "stringptr-test-encrypted";
                  ciena-common-yang:encrypt-path "/ciena-common-test/encryption-test-container/encryption-list-test/leaf-test";
                  ciena-common-yang:sensitive "true";
                  type string {
                    ciena-common-yang:stringptr "true";
                  }
                }
                leaf stringptr-test-encrypted {
                  type string {
                    ciena-common-yang:stringptr "true";
                  }
                  ciena-common-yang:decrypt "stringptr-test";
                  ciena-common-yang:decrypt-path "/ciena-common-test/encryption-test-container/encryption-list-test/leaf-test";
                  ciena-common-yang:sensitive "true";
                }
                leaf string-test {
                  ciena-common-yang:encrypt "string-test-encrypted";
                  ciena-common-yang:encrypt-path "/ciena-common-test/encryption-test-container/encryption-list-test/leaf-test";
                  ciena-common-yang:sensitive "true";
                  type string {
                    length "0..15";
                  }
                }
                leaf string-test-encrypted {
                  type string {
                    ciena-common-yang:stringptr "true";
                  }
                  ciena-common-yang:decrypt "string-test";
                  ciena-common-yang:decrypt-path "/ciena-common-test/encryption-test-container/encryption-list-test/leaf-test";
                  ciena-common-yang:sensitive "true";
                }
                leaf union-test {
                  ciena-common-yang:encrypt "union-test-encrypted";
                  ciena-common-yang:encrypt-path "/ciena-common-test/encryption-test-container/encryption-list-test/leaf-test";
                  type union {
                    type int32;
                    type enumeration {
                      enum unbounded;
                    }
                  }
                  ciena-common-yang:sensitive "true";
                }
                leaf union-test-encrypted {
                  type string {
                    ciena-common-yang:stringptr "true";
                  }
                  ciena-common-yang:decrypt "union-test";
                  ciena-common-yang:decrypt-path "/ciena-common-test/encryption-test-container/encryption-list-test/leaf-test";
                  ciena-common-yang:sensitive "true";
                }
              }
            }
          }
          action toggle-sleep {
            input {
              leaf sleep {
                type boolean;
              }
            }
          }
          uses grouping-test;
          action rpc-test-empty;
          action rpc-test-no-output {
            input {
              leaf input-test {
                type string;
              }
            }
          }
          action rpc-test-no-input {
            output {
              leaf input-test {
                type string;
              }
            }
          }
          action rpc-test {
            input {
              uses grouping-no-action-test;
            }
            output {
              uses grouping-no-action-test;
            }
          }
          action rpc-trigger-encryption-set {
            input {
              leaf path {
                type instance-identifier;
              }
            }
          }
          notification notification-test {
            uses red-blue-group;
          }
          notification encryption-notification-test {
            container X {
              leaf y {
                ciena-common-yang:encrypt "y-encrypted";
                ciena-common-yang:encrypt-path "/ciena-common-test/encryption-notification-test/X";
                type string;
              }
              leaf y-encrypted {
                type string {
                  ciena-common-yang:stringptr "true";
                }
                ciena-common-yang:decrypt "y";
                ciena-common-yang:decrypt-path "/ciena-common-test/encryption-notification-test/X";
              }
            }
          }
          action stack-push {
            description
              "Push into thread specific stack";
            input {
              leaf attr {
                type string;
                default "ddy_stack_test";
              }
              leaf recursive {
                type uint64;
                default "10";
              }
              leaf multistack {
                type uint64;
                default "0";
              }
            }
            output {
              leaf pass {
                type boolean;
              }
            }
          }
          action stack-pop {
            description
              "Pop from thread specific stack";
            input {
              leaf attr {
                type string;
                default "ddy_stack_test";
              }
              leaf recursive {
                type uint64;
                default "10";
              }
              leaf multistack {
                type uint64;
                default "0";
              }
            }
            output {
              leaf pass {
                type boolean;
              }
              leaf-list pop {
                type string;
              }
            }
          }
          action stack-get {
            description
              "Get pushed data for an attribute";
            input {
              leaf attr {
                type string;
                default "ddy_stack_test";
              }
              leaf recursive {
                type uint64;
                default "10";
              }
              leaf multistack {
                type uint64;
                default "0";
              }
            }
            output {
              leaf pass {
                type boolean;
              }
              leaf-list get {
                type string;
              }
            }
          }
          action stack-merge {
            description
              "Merge thread specific stacks";
            input {
              leaf attr {
                type string;
                default "ddy_stack_test";
              }
              leaf count {
                type uint64;
                default "0";
              }
              leaf all {
                type boolean;
              }
            }
            output {
              leaf pass {
                type boolean;
              }
            }
          }
          action return-code-set {
            description
              "Set the return code in the response";
            input {
              leaf return-code {
                type identityref {
                  base ciena-common-yang:error-code;
                }
              }
            }
            output {
              leaf pass {
                type boolean;
              }
            }
          }
          action validate-test {
            description
              "Set the return code in the response";
            input {
              uses abc_validate_group;
              container sub-group {
                uses abc_validate_group;
              }
            }
            output {
              uses ciena-common-yang:rpc-result-common;
            }
          }
          action test-deadline-timeout {
            description
              "Take input as timeout and handler will wait till this time
                based on test scenario type and return pass as true/false.";
            input {
              uses deadline-group;
            }
            output {
              leaf pass {
                type boolean;
              }
            }
          }
          container mount_test_a {
            list b {
              key "name";
              leaf name {
                type string;
              }
              anyxml c;
              container anyxml-mount {
                ciena-common-yang:mount-start "ciena-common-test";
                ciena-common-yang:mount-end "ciena-common-test";
              }
              anydata d;
              container anydata-mount {
                ciena-common-yang:mount-start "ciena-common-test";
                ciena-common-yang:mount-end "ciena-common-test";
              }
            }
          }
          container mount_test_b {
            list b {
              key "name";
              leaf name {
                type string;
              }
              anyxml c;
              container anyxml-mount {
                ciena-common-yang:mount-start "ciena-common-test-list";
                uses ciena-common-test-list:ciena-common-test-list-mount-data;
                uses ciena-common-test-list:ciena-common-test-list-mount-actions-notifs;
                ciena-common-yang:mount-end "ciena-common-test-list";
              }
            }
          }
          container i_love_big_data {
            list big_list {
              key "name";
              leaf name {
                type uint64;
              }
              leaf some_data {
                type decimal64 {
                  fraction-digits 10;
                }
              }
            }
          }
          container i_love_instance_id_for_keys {
            list some_list {
              key "instance_id_name";
              leaf instance_id_name {
                type instance-identifier;
              }
              leaf some_data {
                type decimal64 {
                  fraction-digits 10;
                }
              }
              container some_container {
                description
                  "Dummy container to have same context as parent";
                list sub_list {
                  description
                    "Another keyed list to have instance-id in parent context";
                  key "some_sub_key";
                  leaf some_sub_key {
                    type uint32;
                  }
                  leaf some_sub_leaf {
                    type uint32;
                  }
                }
              }
            }
          }
          container test-restconf-a {
            leaf b {
              type string;
            }
            leaf c {
              type uint8;
            }
            leaf awesome-wildcard-field {
              type string;
            }
            list d {
              key "name";
              leaf name {
                type string;
              }
              leaf test-state {
                type boolean;
              }
              container awesome-wildcard-field {
                leaf awesome-wildcard-field {
                  type boolean;
                }
                leaf awesome-wildcard-field-not {
                  type string;
                }
              }
              list e {
                key "index";
                leaf index {
                  type uint8;
                }
                leaf name {
                  type string;
                }
                list awesome-wildcard-field {
                  key "awesome-wildcard-field";
                  leaf awesome-wildcard-field {
                    type uint8;
                  }
                }
              }
            }
          }
          container test-colon-container {
            leaf enumeration-test {
              ciena-common-yang:sensitive "true";
              type enumeration {
                enum "1:n Mux type";
                enum "2:n Mux type";
                enum "3:n Mux type";
              }
            }
          }
          container multi-augment;
          container ddy-test-server-config {
            leaf handle-complete-transaction {
              type enumeration {
                enum none {
                  description
                    "complete-transaction not handled at all";
                }
                enum local {
                  description
                    "complete-transaction bound to local service";
                }
                enum service {
                  description
                    "complete-transaction bound to ddy-test-server";
                }
              }
              default "none";
            }
          }
          action client-activations {
            description
              "Sometimes you are testing something and you just need a simple way to execute a task.";
            input {
              leaf number {
                description
                  "This number can be used to call a specific function.";
                type uint64;
              }
            }
          }
          ciena-common-yang:mount-end "ciena-common-test";
        }
      }
      list instance {
        key "name";
        leaf name {
          type string;
        }
        container result {
          ciena-common-yang:encrypt "container-1";
          ciena-common-yang:encrypt-path "/ciena-common-test/encryption-test-container/instance";
          list amp {
            ciena-common-yang:encrypt "amp";
            ciena-common-yang:encrypt-path "/ciena-common-test/encryption-test-container/instance/container-1";
            key "amp_name";
            leaf amp_name {
              ciena-common-yang:encrypt "amp_name";
              ciena-common-yang:encrypt-path "/ciena-common-test/encryption-test-container/instance/container-1/amp";
              type string;
            }
            list measurement-no-power {
              ciena-common-yang:encrypt "measurement-no-power";
              ciena-common-yang:encrypt-path "/ciena-common-test/encryption-test-container/instance/container-1/amp";
              description
                "Power measurements of span measured with all channels blocked.";
              key "index";
              leaf index {
                ciena-common-yang:encrypt "index";
                ciena-common-yang:encrypt-path "/ciena-common-test/encryption-test-container/instance/container-1/amp/measurement-no-power";
                type uint8;
              }
              leaf in-current-power {
                ciena-common-yang:encrypt "in-current-power";
                ciena-common-yang:encrypt-path "/ciena-common-test/encryption-test-container/instance/container-1/amp/measurement-no-power";
                type decimal64 {
                  fraction-digits 1;
                }
              }
              leaf in-min-power {
                ciena-common-yang:encrypt "in-min-power";
                ciena-common-yang:encrypt-path "/ciena-common-test/encryption-test-container/instance/container-1/amp/measurement-no-power";
                type decimal64 {
                  fraction-digits 1;
                }
              }
              config false;
            }
          }
        }
        container container-1 {
          ciena-common-yang:decrypt "result";
          ciena-common-yang:decrypt-path "/ciena-common-test/encryption-test-container/instance";
          list amp {
            ciena-common-yang:decrypt "amp";
            ciena-common-yang:decrypt-path "/ciena-common-test/encryption-test-container/instance/result";
            key "amp_name";
            leaf amp_name {
              type string {
                ciena-common-yang:stringptr "true";
              }
              ciena-common-yang:decrypt "amp_name";
              ciena-common-yang:decrypt-path "/ciena-common-test/encryption-test-container/instance/result/amp";
            }
            list measurement-no-power {
              ciena-common-yang:decrypt "measurement-no-power";
              ciena-common-yang:decrypt-path "/ciena-common-test/encryption-test-container/instance/result/amp";
              key "index";
              leaf index {
                type string {
                  ciena-common-yang:stringptr "true";
                }
                ciena-common-yang:decrypt "index";
                ciena-common-yang:decrypt-path "/ciena-common-test/encryption-test-container/instance/result/amp/measurement-no-power";
              }
              leaf in-current-power {
                type string {
                  ciena-common-yang:stringptr "true";
                }
                ciena-common-yang:decrypt "in-current-power";
                ciena-common-yang:decrypt-path "/ciena-common-test/encryption-test-container/instance/result/amp/measurement-no-power";
              }
              leaf in-min-power {
                type string {
                  ciena-common-yang:stringptr "true";
                }
                ciena-common-yang:decrypt "in-min-power";
                ciena-common-yang:decrypt-path "/ciena-common-test/encryption-test-container/instance/result/amp/measurement-no-power";
              }
              config false;
            }
          }
        }
        list some-other-list {
          key "name";
          leaf name {
            type string;
          }
          leaf measurement {
            type uint8;
          }
        }
      }
      list key-in-grouping {
        ciena-common-yang:encrypt "key-in-grouping-encrypted";
        ciena-common-yang:encrypt-path "/ciena-common-test/encryption-test-container";
        description
          "test list key leaf definition can be provided by grouping";
        key "name";
        leaf name {
          ciena-common-yang:encrypt "name";
          ciena-common-yang:encrypt-path "/ciena-common-test/encryption-test-container/key-in-grouping-encrypted";
          type string;
        }
        leaf stats {
          ciena-common-yang:encrypt "stats";
          ciena-common-yang:encrypt-path "/ciena-common-test/encryption-test-container/key-in-grouping-encrypted";
          type uint32;
        }
      }
      list key-in-grouping-encrypted {
        ciena-common-yang:decrypt "key-in-grouping";
        ciena-common-yang:decrypt-path "/ciena-common-test/encryption-test-container";
        key "name";
        leaf name {
          type string {
            ciena-common-yang:stringptr "true";
          }
          ciena-common-yang:decrypt "name";
          ciena-common-yang:decrypt-path "/ciena-common-test/encryption-test-container/key-in-grouping";
        }
        leaf stats {
          type string {
            ciena-common-yang:stringptr "true";
          }
          ciena-common-yang:decrypt "stats";
          ciena-common-yang:decrypt-path "/ciena-common-test/encryption-test-container/key-in-grouping";
        }
      }
      list list-enc-generate-with-renamed-leaves {
        ciena-common-yang:encrypt "list-enc-generate-with-renamed-leaves-enc";
        ciena-common-yang:encrypt-path "/ciena-common-test/encryption-test-container";
        description
          "test list encryption with nested containers and leaves renamed";
        key "name";
        leaf name {
          ciena-common-yang:encrypt "name";
          ciena-common-yang:encrypt-path "/ciena-common-test/encryption-test-container/list-enc-generate-with-renamed-leaves-enc";
          type string;
        }
        leaf aaa {
          ciena-common-yang:encrypt "aaa-enc";
          ciena-common-yang:encrypt-path "/ciena-common-test/encryption-test-container/list-enc-generate-with-renamed-leaves-enc";
          type uint8;
          ciena-common-yang:sensitive "true";
        }
        container ddd {
          ciena-common-yang:encrypt "ddd-enc";
          ciena-common-yang:encrypt-path "/ciena-common-test/encryption-test-container/list-enc-generate-with-renamed-leaves-enc";
          leaf eee {
            ciena-common-yang:encrypt "eee-enc";
            ciena-common-yang:encrypt-path "/ciena-common-test/encryption-test-container/list-enc-generate-with-renamed-leaves-enc/ddd-enc";
            type uint8;
          }
          leaf fff {
            ciena-common-yang:encrypt "fff";
            ciena-common-yang:encrypt-path "/ciena-common-test/encryption-test-container/list-enc-generate-with-renamed-leaves-enc/ddd-enc";
            type uint8;
          }
          config false;
        }
      }
      list list-enc-generate-with-renamed-leaves-enc {
        ciena-common-yang:decrypt "list-enc-generate-with-renamed-leaves";
        ciena-common-yang:decrypt-path "/ciena-common-test/encryption-test-container";
        key "name";
        leaf name {
          type string {
            ciena-common-yang:stringptr "true";
          }
          ciena-common-yang:decrypt "name";
          ciena-common-yang:decrypt-path "/ciena-common-test/encryption-test-container/list-enc-generate-with-renamed-leaves";
        }
        leaf aaa-enc {
          type string {
            ciena-common-yang:stringptr "true";
          }
          ciena-common-yang:decrypt "aaa";
          ciena-common-yang:decrypt-path "/ciena-common-test/encryption-test-container/list-enc-generate-with-renamed-leaves";
          ciena-common-yang:sensitive "true";
        }
        container ddd-enc {
          ciena-common-yang:decrypt "ddd";
          ciena-common-yang:decrypt-path "/ciena-common-test/encryption-test-container/list-enc-generate-with-renamed-leaves";
          leaf eee-enc {
            type string {
              ciena-common-yang:stringptr "true";
            }
            ciena-common-yang:decrypt "eee";
            ciena-common-yang:decrypt-path "/ciena-common-test/encryption-test-container/list-enc-generate-with-renamed-leaves/ddd";
          }
          leaf fff {
            type string {
              ciena-common-yang:stringptr "true";
            }
            ciena-common-yang:decrypt "fff";
            ciena-common-yang:decrypt-path "/ciena-common-test/encryption-test-container/list-enc-generate-with-renamed-leaves/ddd";
          }
          config false;
        }
      }
      list list-generate-with-enc-path-for-leaves {
        ciena-common-yang:encrypt "list-generate-with-enc-path-for-leaves-enc";
        ciena-common-yang:encrypt-path "/ciena-common-test/encryption-test-container";
        description
          "test list encryption with some leaves having encryption-path and encryption-relative-path information";
        key "index";
        leaf index {
          ciena-common-yang:encrypt "index-enc";
          ciena-common-yang:encrypt-path "/ciena-common-test/encryption-test-container/list-generate-with-enc-path-for-leaves-enc";
          type uint8;
        }
        leaf ggg {
          ciena-common-yang:encrypt "ggg";
          ciena-common-yang:encrypt-path "/ciena-common-test/encryption-test-container/list-generate-with-enc-path-for-leaves-enc";
          type uint8;
        }
        container hhh {
          ciena-common-yang:encrypt "hhh";
          ciena-common-yang:encrypt-path "/ciena-common-test/encryption-test-container/list-generate-with-enc-path-for-leaves-enc";
          leaf iii {
            ciena-common-yang:encrypt "iii-enc";
            ciena-common-yang:encrypt-path "/ciena-common-test/encryption-test-container/list-generate-with-enc-path-for-leaves-enc/hhh";
            type uint8;
          }
          leaf jjj {
            ciena-common-yang:encrypt "none-existing-leaf";
            ciena-common-yang:encrypt-path "/ciena-common-test/encryption-test-container/A/B";
            type uint8;
            ciena-common-yang:sensitive "true";
          }
          leaf kkk {
            ciena-common-yang:encrypt "none-existing-leaf-2";
            ciena-common-yang:encrypt-path "/ciena-common-test/encryption-test-container/A/B";
            type uint8;
            config false;
            ciena-common-yang:sensitive "true";
          }
        }
      }
      list list-generate-with-enc-path-for-leaves-enc {
        ciena-common-yang:decrypt "list-generate-with-enc-path-for-leaves";
        ciena-common-yang:decrypt-path "/ciena-common-test/encryption-test-container";
        key "index-enc";
        leaf index-enc {
          type string {
            ciena-common-yang:stringptr "true";
          }
          ciena-common-yang:decrypt "index";
          ciena-common-yang:decrypt-path "/ciena-common-test/encryption-test-container/list-generate-with-enc-path-for-leaves";
        }
        leaf ggg {
          type string {
            ciena-common-yang:stringptr "true";
          }
          ciena-common-yang:decrypt "ggg";
          ciena-common-yang:decrypt-path "/ciena-common-test/encryption-test-container/list-generate-with-enc-path-for-leaves";
        }
        container hhh {
          ciena-common-yang:decrypt "hhh";
          ciena-common-yang:decrypt-path "/ciena-common-test/encryption-test-container/list-generate-with-enc-path-for-leaves";
          leaf iii-enc {
            type string {
              ciena-common-yang:stringptr "true";
            }
            ciena-common-yang:decrypt "iii";
            ciena-common-yang:decrypt-path "/ciena-common-test/encryption-test-container/list-generate-with-enc-path-for-leaves/hhh";
          }
        }
      }
      container A {
        container B {
          leaf none-existing-leaf {
            ciena-common-yang:decrypt "jjj";
            ciena-common-yang:decrypt-path "/ciena-common-test/encryption-test-container/list-generate-with-enc-path-for-leaves/hhh";
            type string {
              ciena-common-yang:stringptr "true";
            }
            ciena-common-yang:sensitive "true";
          }
          leaf none-existing-leaf-2 {
            ciena-common-yang:decrypt "kkk";
            ciena-common-yang:decrypt-path "/ciena-common-test/encryption-test-container/list-generate-with-enc-path-for-leaves/hhh";
            type string {
              ciena-common-yang:stringptr "true";
            }
            ciena-common-yang:sensitive "true";
            config false;
          }
          leaf y {
            type string {
              ciena-common-yang:stringptr "true";
            }
          }
          leaf z {
            type uint8;
          }
        }
      }
      container container-generate-as-sibling {
        ciena-common-yang:encrypt "container-generate-as-sibling-enc";
        ciena-common-yang:encrypt-path "/ciena-common-test/encryption-test-container";
        description
          "test simple container encryption default generating as siblings";
        leaf a {
          ciena-common-yang:encrypt "a";
          ciena-common-yang:encrypt-path "/ciena-common-test/encryption-test-container/container-generate-as-sibling-enc";
          type uint8;
        }
        container b {
          ciena-common-yang:encrypt "b";
          ciena-common-yang:encrypt-path "/ciena-common-test/encryption-test-container/container-generate-as-sibling-enc";
          leaf c {
            ciena-common-yang:encrypt "c";
            ciena-common-yang:encrypt-path "/ciena-common-test/encryption-test-container/container-generate-as-sibling-enc/b";
            type uint8;
          }
        }
      }
      container container-generate-as-sibling-enc {
        ciena-common-yang:decrypt "container-generate-as-sibling";
        ciena-common-yang:decrypt-path "/ciena-common-test/encryption-test-container";
        leaf a {
          type string {
            ciena-common-yang:stringptr "true";
          }
          ciena-common-yang:decrypt "a";
          ciena-common-yang:decrypt-path "/ciena-common-test/encryption-test-container/container-generate-as-sibling";
        }
        container b {
          ciena-common-yang:decrypt "b";
          ciena-common-yang:decrypt-path "/ciena-common-test/encryption-test-container/container-generate-as-sibling";
          leaf c {
            type string {
              ciena-common-yang:stringptr "true";
            }
            ciena-common-yang:decrypt "c";
            ciena-common-yang:decrypt-path "/ciena-common-test/encryption-test-container/container-generate-as-sibling/b";
          }
        }
      }
      container X {
        container Z {
          container container-generate-at-relative-path {
            ciena-common-yang:encrypt "container-generate-at-relative-path-enc";
            ciena-common-yang:encrypt-path "/ciena-common-test/encryption-test-container/K";
            description
              "test container encryption with encrypt-relative-path information";
            container red {
              ciena-common-yang:encrypt "red";
              ciena-common-yang:encrypt-path "/ciena-common-test/encryption-test-container/K/container-generate-at-relative-path-enc";
              container blue {
                ciena-common-yang:encrypt "blue";
                ciena-common-yang:encrypt-path "/ciena-common-test/encryption-test-container/K/container-generate-at-relative-path-enc/red";
                leaf a {
                  ciena-common-yang:encrypt "a";
                  ciena-common-yang:encrypt-path "/ciena-common-test/encryption-test-container/K/container-generate-at-relative-path-enc/red/blue";
                  type uint8;
                }
                leaf b {
                  ciena-common-yang:encrypt "b";
                  ciena-common-yang:encrypt-path "/ciena-common-test/encryption-test-container/K/container-generate-at-relative-path-enc/red/blue";
                  type uint8;
                  default "22";
                }
                leaf c {
                  ciena-common-yang:encrypt "c";
                  ciena-common-yang:encrypt-path "/ciena-common-test/encryption-test-container/K/container-generate-at-relative-path-enc/red/blue";
                  type uint8;
                  default "44";
                }
                leaf d {
                  ciena-common-yang:encrypt "d";
                  ciena-common-yang:encrypt-path "/ciena-common-test/encryption-test-container/K/container-generate-at-relative-path-enc/red/blue";
                  type uint8;
                  default "88";
                }
              }
            }
            leaf a {
              ciena-common-yang:encrypt "a";
              ciena-common-yang:encrypt-path "/ciena-common-test/encryption-test-container/K/container-generate-at-relative-path-enc";
              type uint8;
            }
            container b {
              ciena-common-yang:encrypt "b";
              ciena-common-yang:encrypt-path "/ciena-common-test/encryption-test-container/K/container-generate-at-relative-path-enc";
              container red {
                ciena-common-yang:encrypt "red";
                ciena-common-yang:encrypt-path "/ciena-common-test/encryption-test-container/K/container-generate-at-relative-path-enc/b";
                container blue {
                  ciena-common-yang:encrypt "blue";
                  ciena-common-yang:encrypt-path "/ciena-common-test/encryption-test-container/K/container-generate-at-relative-path-enc/b/red";
                  leaf a {
                    ciena-common-yang:encrypt "a";
                    ciena-common-yang:encrypt-path "/ciena-common-test/encryption-test-container/K/container-generate-at-relative-path-enc/b/red/blue";
                    type uint8;
                  }
                  leaf b {
                    ciena-common-yang:encrypt "b";
                    ciena-common-yang:encrypt-path "/ciena-common-test/encryption-test-container/K/container-generate-at-relative-path-enc/b/red/blue";
                    type uint8;
                    default "22";
                  }
                  leaf c {
                    ciena-common-yang:encrypt "c";
                    ciena-common-yang:encrypt-path "/ciena-common-test/encryption-test-container/K/container-generate-at-relative-path-enc/b/red/blue";
                    type uint8;
                    default "44";
                  }
                  leaf d {
                    ciena-common-yang:encrypt "d";
                    ciena-common-yang:encrypt-path "/ciena-common-test/encryption-test-container/K/container-generate-at-relative-path-enc/b/red/blue";
                    type uint8;
                    default "88";
                  }
                }
              }
              leaf c {
                ciena-common-yang:encrypt "c";
                ciena-common-yang:encrypt-path "/ciena-common-test/encryption-test-container/K/container-generate-at-relative-path-enc/b";
                type uint8;
              }
            }
            config false;
          }
        }
      }
      container K {
        container container-generate-at-relative-path-enc {
          ciena-common-yang:decrypt "container-generate-at-relative-path";
          ciena-common-yang:decrypt-path "/ciena-common-test/encryption-test-container/X/Z";
          container red {
            ciena-common-yang:decrypt "red";
            ciena-common-yang:decrypt-path "/ciena-common-test/encryption-test-container/X/Z/container-generate-at-relative-path";
            container blue {
              ciena-common-yang:decrypt "blue";
              ciena-common-yang:decrypt-path "/ciena-common-test/encryption-test-container/X/Z/container-generate-at-relative-path/red";
              leaf a {
                type string {
                  ciena-common-yang:stringptr "true";
                }
                ciena-common-yang:decrypt "a";
                ciena-common-yang:decrypt-path "/ciena-common-test/encryption-test-container/X/Z/container-generate-at-relative-path/red/blue";
              }
              leaf b {
                type string {
                  ciena-common-yang:stringptr "true";
                }
                ciena-common-yang:decrypt "b";
                ciena-common-yang:decrypt-path "/ciena-common-test/encryption-test-container/X/Z/container-generate-at-relative-path/red/blue";
              }
              leaf c {
                type string {
                  ciena-common-yang:stringptr "true";
                }
                ciena-common-yang:decrypt "c";
                ciena-common-yang:decrypt-path "/ciena-common-test/encryption-test-container/X/Z/container-generate-at-relative-path/red/blue";
              }
              leaf d {
                type string {
                  ciena-common-yang:stringptr "true";
                }
                ciena-common-yang:decrypt "d";
                ciena-common-yang:decrypt-path "/ciena-common-test/encryption-test-container/X/Z/container-generate-at-relative-path/red/blue";
              }
            }
          }
          leaf a {
            type string {
              ciena-common-yang:stringptr "true";
            }
            ciena-common-yang:decrypt "a";
            ciena-common-yang:decrypt-path "/ciena-common-test/encryption-test-container/X/Z/container-generate-at-relative-path";
          }
          container b {
            ciena-common-yang:decrypt "b";
            ciena-common-yang:decrypt-path "/ciena-common-test/encryption-test-container/X/Z/container-generate-at-relative-path";
            container red {
              ciena-common-yang:decrypt "red";
              ciena-common-yang:decrypt-path "/ciena-common-test/encryption-test-container/X/Z/container-generate-at-relative-path/b";
              container blue {
                ciena-common-yang:decrypt "blue";
                ciena-common-yang:decrypt-path "/ciena-common-test/encryption-test-container/X/Z/container-generate-at-relative-path/b/red";
                leaf a {
                  type string {
                    ciena-common-yang:stringptr "true";
                  }
                  ciena-common-yang:decrypt "a";
                  ciena-common-yang:decrypt-path "/ciena-common-test/encryption-test-container/X/Z/container-generate-at-relative-path/b/red/blue";
                }
                leaf b {
                  type string {
                    ciena-common-yang:stringptr "true";
                  }
                  ciena-common-yang:decrypt "b";
                  ciena-common-yang:decrypt-path "/ciena-common-test/encryption-test-container/X/Z/container-generate-at-relative-path/b/red/blue";
                }
                leaf c {
                  type string {
                    ciena-common-yang:stringptr "true";
                  }
                  ciena-common-yang:decrypt "c";
                  ciena-common-yang:decrypt-path "/ciena-common-test/encryption-test-container/X/Z/container-generate-at-relative-path/b/red/blue";
                }
                leaf d {
                  type string {
                    ciena-common-yang:stringptr "true";
                  }
                  ciena-common-yang:decrypt "d";
                  ciena-common-yang:decrypt-path "/ciena-common-test/encryption-test-container/X/Z/container-generate-at-relative-path/b/red/blue";
                }
              }
            }
            leaf c {
              type string {
                ciena-common-yang:stringptr "true";
              }
              ciena-common-yang:decrypt "c";
              ciena-common-yang:decrypt-path "/ciena-common-test/encryption-test-container/X/Z/container-generate-at-relative-path/b";
            }
          }
          config false;
        }
        leaf l {
          type uint8;
        }
      }
      container container-generate-at-abs-path {
        ciena-common-yang:encrypt "container-generate-at-abs-path-enc";
        ciena-common-yang:encrypt-path "/ciena-common-test/encryption-test-container";
        description
          "test container encryption with absolute path encrypt-path information";
        leaf a {
          ciena-common-yang:encrypt "a";
          ciena-common-yang:encrypt-path "/ciena-common-test/encryption-test-container/container-generate-at-abs-path-enc";
          type uint8;
        }
        container b {
          ciena-common-yang:encrypt "b";
          ciena-common-yang:encrypt-path "/ciena-common-test/encryption-test-container/container-generate-at-abs-path-enc";
          leaf c {
            ciena-common-yang:encrypt "c";
            ciena-common-yang:encrypt-path "/ciena-common-test/encryption-test-container/container-generate-at-abs-path-enc/b";
            type uint8;
          }
        }
        config false;
      }
      container encrypt-to-existing-container {
        ciena-common-yang:encrypt "encrypt-to-existing-container-encrypted";
        ciena-common-yang:encrypt-path "/ciena-common-test/encryption-test-container";
        description
          "test container encryption to existing container. no generation will happen.";
        leaf a {
          ciena-common-yang:encrypt "a";
          ciena-common-yang:encrypt-path "/ciena-common-test/encryption-test-container/encrypt-to-existing-container-encrypted";
          type uint8;
        }
      }
      container encrypt-to-existing-container-encrypted {
        ciena-common-yang:decrypt "encrypt-to-existing-container";
        ciena-common-yang:decrypt-path "/ciena-common-test/encryption-test-container";
        leaf a {
          ciena-common-yang:decrypt "a";
          ciena-common-yang:decrypt-path "/ciena-common-test/encryption-test-container/encrypt-to-existing-container";
          type string {
            ciena-common-yang:stringptr "true";
          }
        }
      }
      container outter-container {
        ciena-common-yang:encrypt "outter-container-enc";
        ciena-common-yang:encrypt-path "/ciena-common-test/encryption-test-container";
        description
          "simple nested container test";
        leaf aaa {
          ciena-common-yang:encrypt "aaa";
          ciena-common-yang:encrypt-path "/ciena-common-test/encryption-test-container/outter-container-enc";
          type uint8;
        }
        container middle-container {
          ciena-common-yang:encrypt "middle-container";
          ciena-common-yang:encrypt-path "/ciena-common-test/encryption-test-container/outter-container-enc";
          leaf bbb {
            ciena-common-yang:encrypt "bbb";
            ciena-common-yang:encrypt-path "/ciena-common-test/encryption-test-container/outter-container-enc/middle-container";
            type uint8;
          }
          container inner-container {
            ciena-common-yang:encrypt "inner-container";
            ciena-common-yang:encrypt-path "/ciena-common-test/encryption-test-container/outter-container-enc/middle-container";
            leaf ccc {
              ciena-common-yang:encrypt "ccc";
              ciena-common-yang:encrypt-path "/ciena-common-test/encryption-test-container/outter-container-enc/middle-container/inner-container";
              type uint8;
            }
          }
        }
      }
      container outter-container-enc {
        ciena-common-yang:decrypt "outter-container";
        ciena-common-yang:decrypt-path "/ciena-common-test/encryption-test-container";
        leaf aaa {
          type string {
            ciena-common-yang:stringptr "true";
          }
          ciena-common-yang:decrypt "aaa";
          ciena-common-yang:decrypt-path "/ciena-common-test/encryption-test-container/outter-container";
        }
        container middle-container {
          ciena-common-yang:decrypt "middle-container";
          ciena-common-yang:decrypt-path "/ciena-common-test/encryption-test-container/outter-container";
          leaf bbb {
            type string {
              ciena-common-yang:stringptr "true";
            }
            ciena-common-yang:decrypt "bbb";
            ciena-common-yang:decrypt-path "/ciena-common-test/encryption-test-container/outter-container/middle-container";
          }
          container inner-container {
            ciena-common-yang:decrypt "inner-container";
            ciena-common-yang:decrypt-path "/ciena-common-test/encryption-test-container/outter-container/middle-container";
            leaf ccc {
              type string {
                ciena-common-yang:stringptr "true";
              }
              ciena-common-yang:decrypt "ccc";
              ciena-common-yang:decrypt-path "/ciena-common-test/encryption-test-container/outter-container/middle-container/inner-container";
            }
          }
        }
      }
      container one-to-two-container {
        ciena-common-yang:encrypt "one-to-two-container-enc";
        ciena-common-yang:encrypt-path "/ciena-common-test/encryption-test-container";
        description
          "error scenario test: leaves under one container encrypted to two containers
           is not fully supported, the leaves for one container will be missing";
        leaf aaa {
          ciena-common-yang:encrypt "aaa";
          ciena-common-yang:encrypt-path "/ciena-common-test/encryption-test-container/one-to-two-container-enc";
          type uint8;
        }
        leaf-list bbb {
          ciena-common-yang:encrypt "bbb";
          ciena-common-yang:encrypt-path "/ciena-common-test/encryption-test-container/one-to-two-container-other";
          type uint8;
        }
        container inner-container {
          ciena-common-yang:encrypt "inner-container";
          ciena-common-yang:encrypt-path "/ciena-common-test/encryption-test-container/one-to-two-container-enc";
          leaf-list ccc {
            ciena-common-yang:encrypt "ccc";
            ciena-common-yang:encrypt-path "/ciena-common-test/encryption-test-container/one-to-two-container-enc/inner-container";
            type uint8;
          }
          leaf ddd {
            ciena-common-yang:encrypt "ddd";
            ciena-common-yang:encrypt-path "/ciena-common-test/encryption-test-container/one-to-two-container-other";
            type uint8;
          }
        }
      }
      container one-to-two-container-enc {
        ciena-common-yang:decrypt "one-to-two-container";
        ciena-common-yang:decrypt-path "/ciena-common-test/encryption-test-container";
        leaf aaa {
          type string {
            ciena-common-yang:stringptr "true";
          }
          ciena-common-yang:decrypt "aaa";
          ciena-common-yang:decrypt-path "/ciena-common-test/encryption-test-container/one-to-two-container";
        }
        container inner-container {
          ciena-common-yang:decrypt "inner-container";
          ciena-common-yang:decrypt-path "/ciena-common-test/encryption-test-container/one-to-two-container";
          leaf-list ccc {
            type string {
              ciena-common-yang:stringptr "true";
            }
            ciena-common-yang:decrypt "ccc";
            ciena-common-yang:decrypt-path "/ciena-common-test/encryption-test-container/one-to-two-container/inner-container";
          }
        }
      }
      container one-to-two-container-other {
        leaf-list bbb {
          ciena-common-yang:decrypt "bbb";
          ciena-common-yang:decrypt-path "/ciena-common-test/encryption-test-container/one-to-two-container";
          type string {
            ciena-common-yang:stringptr "true";
          }
        }
        leaf ddd {
          ciena-common-yang:decrypt "ddd";
          ciena-common-yang:decrypt-path "/ciena-common-test/encryption-test-container/one-to-two-container/inner-container";
          type string {
            ciena-common-yang:stringptr "true";
          }
        }
        leaf fff {
          type uint8;
        }
      }
      list nested-list {
        ciena-common-yang:encrypt "nested-list-enc";
        ciena-common-yang:encrypt-path "/ciena-common-test/encryption-test-container";
        description
          "test nested list encryption";
        key "name";
        leaf name {
          ciena-common-yang:encrypt "name";
          ciena-common-yang:encrypt-path "/ciena-common-test/encryption-test-container/nested-list-enc";
          type stringptr;
        }
        leaf aaa {
          ciena-common-yang:encrypt "aaa";
          ciena-common-yang:encrypt-path "/ciena-common-test/encryption-test-container/nested-list-enc";
          type uint8;
        }
        list inner-list {
          ciena-common-yang:encrypt "inner-list";
          ciena-common-yang:encrypt-path "/ciena-common-test/encryption-test-container/nested-list-enc";
          key "index";
          leaf index {
            ciena-common-yang:encrypt "index";
            ciena-common-yang:encrypt-path "/ciena-common-test/encryption-test-container/nested-list-enc/inner-list";
            type uint8;
          }
          leaf-list ccc {
            ciena-common-yang:encrypt "ccc";
            ciena-common-yang:encrypt-path "/ciena-common-test/encryption-test-container/nested-list-enc/inner-list";
            type string;
          }
        }
      }
      list nested-list-enc {
        ciena-common-yang:decrypt "nested-list";
        ciena-common-yang:decrypt-path "/ciena-common-test/encryption-test-container";
        key "name";
        leaf name {
          type string {
            ciena-common-yang:stringptr "true";
          }
          ciena-common-yang:decrypt "name";
          ciena-common-yang:decrypt-path "/ciena-common-test/encryption-test-container/nested-list";
        }
        leaf aaa {
          type string {
            ciena-common-yang:stringptr "true";
          }
          ciena-common-yang:decrypt "aaa";
          ciena-common-yang:decrypt-path "/ciena-common-test/encryption-test-container/nested-list";
        }
        list inner-list {
          ciena-common-yang:decrypt "inner-list";
          ciena-common-yang:decrypt-path "/ciena-common-test/encryption-test-container/nested-list";
          key "index";
          leaf index {
            type string {
              ciena-common-yang:stringptr "true";
            }
            ciena-common-yang:decrypt "index";
            ciena-common-yang:decrypt-path "/ciena-common-test/encryption-test-container/nested-list/inner-list";
          }
          leaf-list ccc {
            type string {
              ciena-common-yang:stringptr "true";
            }
            ciena-common-yang:decrypt "ccc";
            ciena-common-yang:decrypt-path "/ciena-common-test/encryption-test-container/nested-list/inner-list";
          }
        }
      }
      container other {
        leaf ccc {
          type string;
        }
      }
      container user-defined-leaves {
        description
          "selected leaves encryption container";
        leaf a {
          ciena-common-yang:encrypt "x";
          ciena-common-yang:encrypt-path "/ciena-common-test/encryption-test-container/user-defined-leaves-encrypted";
          type string;
        }
        leaf b {
          type string;
        }
      }
      container user-defined-leaves-encrypted {
        leaf x {
          ciena-common-yang:decrypt "a";
          ciena-common-yang:decrypt-path "/ciena-common-test/encryption-test-container/user-defined-leaves";
          type string;
        }
      }
      list nested-list-leaf-encryption {
        key "name";
        leaf name {
          type string;
        }
        leaf x {
          ciena-common-yang:encrypt "x-enc";
          ciena-common-yang:encrypt-path "/ciena-common-test/encryption-test-container/nested-list-leaf-encryption";
          type string;
        }
        leaf x-enc {
          type string {
            ciena-common-yang:stringptr "true";
          }
          ciena-common-yang:decrypt "x";
          ciena-common-yang:decrypt-path "/ciena-common-test/encryption-test-container/nested-list-leaf-encryption";
        }
        list inner {
          key "index";
          leaf index {
            type uint8;
          }
          leaf u {
            ciena-common-yang:encrypt "u-enc";
            ciena-common-yang:encrypt-path "/ciena-common-test/encryption-test-container/nested-list-leaf-encryption/inner";
            type string;
          }
          leaf u-enc {
            type string {
              ciena-common-yang:stringptr "true";
            }
            ciena-common-yang:decrypt "u";
            ciena-common-yang:decrypt-path "/ciena-common-test/encryption-test-container/nested-list-leaf-encryption/inner";
          }
        }
      }
      list encryption-list-test {
        key "key1 key2";
        leaf key1 {
          type stringptr;
        }
        leaf key2 {
          type typetest;
        }
        container leaf-list-test {
          leaf-list binary-test {
            ciena-common-yang:encrypt "binary-test-encrypted";
            ciena-common-yang:encrypt-path "/ciena-common-test/encryption-test-container/encryption-list-test/leaf-list-test";
            type binary;
          }
          leaf-list binary-test-encrypted {
            type string {
              ciena-common-yang:stringptr "true";
            }
            ciena-common-yang:decrypt "binary-test";
            ciena-common-yang:decrypt-path "/ciena-common-test/encryption-test-container/encryption-list-test/leaf-list-test";
          }
          leaf-list bits-test {
            ciena-common-yang:encrypt "bits-test-encrypted";
            ciena-common-yang:encrypt-path "/ciena-common-test/encryption-test-container/encryption-list-test/leaf-list-test";
            type bits {
              bit disable-nagle {
                position 0;
              }
              bit auto-sense-speed {
                position 1;
              }
            }
          }
          leaf-list bits-test-encrypted {
            type string {
              ciena-common-yang:stringptr "true";
            }
            ciena-common-yang:decrypt "bits-test";
            ciena-common-yang:decrypt-path "/ciena-common-test/encryption-test-container/encryption-list-test/leaf-list-test";
          }
          leaf-list boolean-test {
            ciena-common-yang:encrypt "boolean-test-encrypted";
            ciena-common-yang:encrypt-path "/ciena-common-test/encryption-test-container/encryption-list-test/leaf-list-test";
            type boolean;
          }
          leaf-list boolean-test-encrypted {
            type string {
              ciena-common-yang:stringptr "true";
            }
            ciena-common-yang:decrypt "boolean-test";
            ciena-common-yang:decrypt-path "/ciena-common-test/encryption-test-container/encryption-list-test/leaf-list-test";
          }
          leaf-list decimal64-test {
            ciena-common-yang:encrypt "decimal64-test-encrypted";
            ciena-common-yang:encrypt-path "/ciena-common-test/encryption-test-container/encryption-list-test/leaf-list-test";
            type decimal64 {
              fraction-digits 10;
            }
          }
          leaf-list decimal64-test-encrypted {
            type string {
              ciena-common-yang:stringptr "true";
            }
            ciena-common-yang:decrypt "decimal64-test";
            ciena-common-yang:decrypt-path "/ciena-common-test/encryption-test-container/encryption-list-test/leaf-list-test";
          }
          leaf-list empty-test {
            ciena-common-yang:encrypt "empty-test-encrypted";
            ciena-common-yang:encrypt-path "/ciena-common-test/encryption-test-container/encryption-list-test/leaf-list-test";
            type empty;
          }
          leaf-list empty-test-encrypted {
            type string {
              ciena-common-yang:stringptr "true";
            }
            ciena-common-yang:decrypt "empty-test";
            ciena-common-yang:decrypt-path "/ciena-common-test/encryption-test-container/encryption-list-test/leaf-list-test";
          }
          leaf-list enumeration-test {
            ciena-common-yang:encrypt "enumeration-test-encrypted";
            ciena-common-yang:encrypt-path "/ciena-common-test/encryption-test-container/encryption-list-test/leaf-list-test";
            type enumeration {
              enum test-a;
              enum test-b;
              enum test-c;
              enum map;
            }
          }
          leaf-list enumeration-test-encrypted {
            type string {
              ciena-common-yang:stringptr "true";
            }
            ciena-common-yang:decrypt "enumeration-test";
            ciena-common-yang:decrypt-path "/ciena-common-test/encryption-test-container/encryption-list-test/leaf-list-test";
          }
          leaf-list identityref-test {
            ciena-common-yang:encrypt "identityref-test-encrypted";
            ciena-common-yang:encrypt-path "/ciena-common-test/encryption-test-container/encryption-list-test/leaf-list-test";
            type identityref {
              base test:crypto-alg;
            }
          }
          leaf-list identityref-test-encrypted {
            type string {
              ciena-common-yang:stringptr "true";
            }
            ciena-common-yang:decrypt "identityref-test";
            ciena-common-yang:decrypt-path "/ciena-common-test/encryption-test-container/encryption-list-test/leaf-list-test";
          }
          leaf-list instance-identifier-test {
            ciena-common-yang:encrypt "instance-identifier-test-encrypted";
            ciena-common-yang:encrypt-path "/ciena-common-test/encryption-test-container/encryption-list-test/leaf-list-test";
            type instance-identifier;
          }
          leaf-list instance-identifier-test-encrypted {
            type string {
              ciena-common-yang:stringptr "true";
            }
            ciena-common-yang:decrypt "instance-identifier-test";
            ciena-common-yang:decrypt-path "/ciena-common-test/encryption-test-container/encryption-list-test/leaf-list-test";
          }
          leaf-list leafref-test {
            ciena-common-yang:encrypt "leafref-test-encrypted";
            ciena-common-yang:encrypt-path "/ciena-common-test/encryption-test-container/encryption-list-test/leaf-list-test";
            type leafref {
              path "/test:red/test:blue/test:b";
            }
          }
          leaf-list leafref-test-encrypted {
            type string {
              ciena-common-yang:stringptr "true";
            }
            ciena-common-yang:decrypt "leafref-test";
            ciena-common-yang:decrypt-path "/ciena-common-test/encryption-test-container/encryption-list-test/leaf-list-test";
          }
          leaf-list stringptr-test {
            ciena-common-yang:encrypt "stringptr-test-encrypted";
            ciena-common-yang:encrypt-path "/ciena-common-test/encryption-test-container/encryption-list-test/leaf-list-test";
            type stringptr;
          }
          leaf-list stringptr-test-encrypted {
            type string {
              ciena-common-yang:stringptr "true";
            }
            ciena-common-yang:decrypt "stringptr-test";
            ciena-common-yang:decrypt-path "/ciena-common-test/encryption-test-container/encryption-list-test/leaf-list-test";
          }
          leaf-list string-test {
            ciena-common-yang:encrypt "string-test-encrypted";
            ciena-common-yang:encrypt-path "/ciena-common-test/encryption-test-container/encryption-list-test/leaf-list-test";
            type string;
          }
          leaf-list string-test-encrypted {
            type string {
              ciena-common-yang:stringptr "true";
            }
            ciena-common-yang:decrypt "string-test";
            ciena-common-yang:decrypt-path "/ciena-common-test/encryption-test-container/encryption-list-test/leaf-list-test";
          }
          leaf-list uint8-test {
            ciena-common-yang:encrypt "uint8-test-encrypted";
            ciena-common-yang:encrypt-path "/ciena-common-test/encryption-test-container/encryption-list-test/leaf-list-test";
            type uint8;
          }
          leaf-list uint8-test-encrypted {
            type string {
              ciena-common-yang:stringptr "true";
            }
            ciena-common-yang:decrypt "uint8-test";
            ciena-common-yang:decrypt-path "/ciena-common-test/encryption-test-container/encryption-list-test/leaf-list-test";
          }
          leaf-list union-test {
            ciena-common-yang:encrypt "union-test-encrypted";
            ciena-common-yang:encrypt-path "/ciena-common-test/encryption-test-container/encryption-list-test/leaf-list-test";
            type union {
              type int32;
              type enumeration {
                enum unbounded;
              }
            }
          }
          leaf-list union-test-encrypted {
            type string {
              ciena-common-yang:stringptr "true";
            }
            ciena-common-yang:decrypt "union-test";
            ciena-common-yang:decrypt-path "/ciena-common-test/encryption-test-container/encryption-list-test/leaf-list-test";
          }
        }
        container leaf-test {
          leaf binary-test {
            ciena-common-yang:encrypt "binary-test-encrypted";
            ciena-common-yang:encrypt-path "/ciena-common-test/encryption-test-container/encryption-list-test/leaf-test";
            type binary;
            ciena-common-yang:sensitive "true";
          }
          leaf binary-test-encrypted {
            type string {
              ciena-common-yang:stringptr "true";
            }
            ciena-common-yang:decrypt "binary-test";
            ciena-common-yang:decrypt-path "/ciena-common-test/encryption-test-container/encryption-list-test/leaf-test";
            ciena-common-yang:sensitive "true";
          }
          leaf bits-test {
            ciena-common-yang:encrypt "bits-test-encrypted";
            ciena-common-yang:encrypt-path "/ciena-common-test/encryption-test-container/encryption-list-test/leaf-test";
            ciena-common-yang:sensitive "true";
            type bits {
              bit apple {
                position 0;
              }
              bit orange {
                position 1;
              }
              bit banana {
                position 2;
              }
            }
          }
          leaf bits-test-encrypted {
            type string {
              ciena-common-yang:stringptr "true";
            }
            ciena-common-yang:decrypt "bits-test";
            ciena-common-yang:decrypt-path "/ciena-common-test/encryption-test-container/encryption-list-test/leaf-test";
            ciena-common-yang:sensitive "true";
          }
          leaf offset-bits-test {
            ciena-common-yang:encrypt "offset-bits-test-encrypted";
            ciena-common-yang:encrypt-path "/ciena-common-test/encryption-test-container/encryption-list-test/leaf-test";
            ciena-common-yang:sensitive "true";
            type bits {
              bit apple {
                position 3;
              }
              bit orange {
                position 5;
              }
              bit banana {
                position 7;
              }
            }
          }
          leaf offset-bits-test-encrypted {
            type string {
              ciena-common-yang:stringptr "true";
            }
            ciena-common-yang:decrypt "offset-bits-test";
            ciena-common-yang:decrypt-path "/ciena-common-test/encryption-test-container/encryption-list-test/leaf-test";
            ciena-common-yang:sensitive "true";
          }
          leaf boolean-test {
            ciena-common-yang:encrypt "boolean-test-encrypted";
            ciena-common-yang:encrypt-path "/ciena-common-test/encryption-test-container/encryption-list-test/leaf-test";
            ciena-common-yang:sensitive "true";
            type boolean;
          }
          leaf boolean-test-encrypted {
            type string {
              ciena-common-yang:stringptr "true";
            }
            ciena-common-yang:decrypt "boolean-test";
            ciena-common-yang:decrypt-path "/ciena-common-test/encryption-test-container/encryption-list-test/leaf-test";
            ciena-common-yang:sensitive "true";
          }
          leaf decimal64-test {
            ciena-common-yang:encrypt "decimal64-test-encrypted";
            ciena-common-yang:encrypt-path "/ciena-common-test/encryption-test-container/encryption-list-test/leaf-test";
            ciena-common-yang:sensitive "true";
            type decimal64 {
              fraction-digits 2;
            }
          }
          leaf decimal64-test-encrypted {
            type string {
              ciena-common-yang:stringptr "true";
            }
            ciena-common-yang:decrypt "decimal64-test";
            ciena-common-yang:decrypt-path "/ciena-common-test/encryption-test-container/encryption-list-test/leaf-test";
            ciena-common-yang:sensitive "true";
          }
          leaf empty-test {
            ciena-common-yang:encrypt "empty-test-encrypted";
            ciena-common-yang:encrypt-path "/ciena-common-test/encryption-test-container/encryption-list-test/leaf-test";
            ciena-common-yang:sensitive "true";
            type empty;
          }
          leaf empty-test-encrypted {
            type string {
              ciena-common-yang:stringptr "true";
            }
            ciena-common-yang:decrypt "empty-test";
            ciena-common-yang:decrypt-path "/ciena-common-test/encryption-test-container/encryption-list-test/leaf-test";
            ciena-common-yang:sensitive "true";
          }
          leaf enumeration-test {
            ciena-common-yang:encrypt "enumeration-test-encrypted";
            ciena-common-yang:encrypt-path "/ciena-common-test/encryption-test-container/encryption-list-test/leaf-test";
            ciena-common-yang:sensitive "true";
            type enumeration {
              enum test-1;
              enum test-2;
              enum test-3;
            }
          }
          leaf enumeration-test-encrypted {
            type string {
              ciena-common-yang:stringptr "true";
            }
            ciena-common-yang:decrypt "enumeration-test";
            ciena-common-yang:decrypt-path "/ciena-common-test/encryption-test-container/encryption-list-test/leaf-test";
            ciena-common-yang:sensitive "true";
          }
          leaf enumeration-extended-test {
            ciena-common-yang:encrypt "enumeration-extended-test-encrypted";
            ciena-common-yang:encrypt-path "/ciena-common-test/encryption-test-container/encryption-list-test/leaf-test";
            ciena-common-yang:sensitive "true";
            type enumeration {
              enum forty-one {
                value 41;
              }
              enum ten {
                value 10;
              }
              enum seven {
                value 7;
              }
            }
          }
          leaf enumeration-extended-test-encrypted {
            type string {
              ciena-common-yang:stringptr "true";
            }
            ciena-common-yang:decrypt "enumeration-extended-test";
            ciena-common-yang:decrypt-path "/ciena-common-test/encryption-test-container/encryption-list-test/leaf-test";
            ciena-common-yang:sensitive "true";
          }
          leaf identityref-test {
            ciena-common-yang:encrypt "identifyref-test-encrypted";
            ciena-common-yang:encrypt-path "/ciena-common-test/encryption-test-container/encryption-list-test/leaf-test";
            ciena-common-yang:sensitive "true";
            type identityref {
              base test:crypto-alg;
            }
          }
          leaf identifyref-test-encrypted {
            type string {
              ciena-common-yang:stringptr "true";
            }
            ciena-common-yang:decrypt "identityref-test";
            ciena-common-yang:decrypt-path "/ciena-common-test/encryption-test-container/encryption-list-test/leaf-test";
            ciena-common-yang:sensitive "true";
          }
          leaf instance-identifier-test {
            ciena-common-yang:encrypt "instance-identifier-test-encrypted";
            ciena-common-yang:encrypt-path "/ciena-common-test/encryption-test-container/encryption-list-test/leaf-test";
            ciena-common-yang:sensitive "true";
            type instance-identifier;
          }
          leaf instance-identifier-test-encrypted {
            type string {
              ciena-common-yang:stringptr "true";
            }
            ciena-common-yang:decrypt "instance-identifier-test";
            ciena-common-yang:decrypt-path "/ciena-common-test/encryption-test-container/encryption-list-test/leaf-test";
            ciena-common-yang:sensitive "true";
          }
          leaf int64-test {
            ciena-common-yang:encrypt "int64-test-encrypted";
            ciena-common-yang:encrypt-path "/ciena-common-test/encryption-test-container/encryption-list-test/leaf-test";
            ciena-common-yang:sensitive "true";
            type int64;
          }
          leaf int64-test-encrypted {
            type string {
              ciena-common-yang:stringptr "true";
            }
            ciena-common-yang:decrypt "int64-test";
            ciena-common-yang:decrypt-path "/ciena-common-test/encryption-test-container/encryption-list-test/leaf-test";
            ciena-common-yang:sensitive "true";
          }
          leaf leafref-test {
            ciena-common-yang:encrypt "leafref-test-encrypted";
            ciena-common-yang:encrypt-path "/ciena-common-test/encryption-test-container/encryption-list-test/leaf-test";
            ciena-common-yang:sensitive "true";
            type leafref {
              path "/test:red/test:blue/test:c";
            }
          }
          leaf leafref-test-encrypted {
            type string {
              ciena-common-yang:stringptr "true";
            }
            ciena-common-yang:decrypt "leafref-test";
            ciena-common-yang:decrypt-path "/ciena-common-test/encryption-test-container/encryption-list-test/leaf-test";
            ciena-common-yang:sensitive "true";
          }
          leaf stringptr-test {
            ciena-common-yang:encrypt "stringptr-test-encrypted";
            ciena-common-yang:encrypt-path "/ciena-common-test/encryption-test-container/encryption-list-test/leaf-test";
            ciena-common-yang:sensitive "true";
            type string {
              ciena-common-yang:stringptr "true";
            }
          }
          leaf stringptr-test-encrypted {
            type string {
              ciena-common-yang:stringptr "true";
            }
            ciena-common-yang:decrypt "stringptr-test";
            ciena-common-yang:decrypt-path "/ciena-common-test/encryption-test-container/encryption-list-test/leaf-test";
            ciena-common-yang:sensitive "true";
          }
          leaf string-test {
            ciena-common-yang:encrypt "string-test-encrypted";
            ciena-common-yang:encrypt-path "/ciena-common-test/encryption-test-container/encryption-list-test/leaf-test";
            ciena-common-yang:sensitive "true";
            type string {
              length "0..15";
            }
          }
          leaf string-test-encrypted {
            type string {
              ciena-common-yang:stringptr "true";
            }
            ciena-common-yang:decrypt "string-test";
            ciena-common-yang:decrypt-path "/ciena-common-test/encryption-test-container/encryption-list-test/leaf-test";
            ciena-common-yang:sensitive "true";
          }
          leaf union-test {
            ciena-common-yang:encrypt "union-test-encrypted";
            ciena-common-yang:encrypt-path "/ciena-common-test/encryption-test-container/encryption-list-test/leaf-test";
            type union {
              type int32;
              type enumeration {
                enum unbounded;
              }
            }
            ciena-common-yang:sensitive "true";
          }
          leaf union-test-encrypted {
            type string {
              ciena-common-yang:stringptr "true";
            }
            ciena-common-yang:decrypt "union-test";
            ciena-common-yang:decrypt-path "/ciena-common-test/encryption-test-container/encryption-list-test/leaf-test";
            ciena-common-yang:sensitive "true";
          }
        }
      }
    }
    uses grouping-test;
    container mount_test_a {
      list b {
        key "name";
        leaf name {
          type string;
        }
        anyxml c;
        container anyxml-mount {
          ciena-common-yang:mount-start "ciena-common-test";
          container string-based-return-code-list {
            config false;
            description
              "List of errors in case of command failure";
            list return-code-list {
              leaf instance {
                type string {
                  ciena-common-yang:stringptr "true";
                }
                description
                  "The instance to which the error code applies.";
              }
              leaf error {
                type string;
              }
            }
          }
          uses red-blue-group;
          uses blue-yellow-group;
          container white {
            uses abc_group;
            container cont1 {
              uses abc_group;
            }
            container cont2 {
              uses abc_group;
            }
            container cont3 {
              uses abc_group;
            }
            container cont4 {
              uses abc_group;
            }
            list list1 {
              key "k";
              leaf k {
                type uint8;
              }
              uses abc_group;
            }
          }
          container validation-test {
            uses abc_validate_group;
          }
          container to-pointer-test {
            container a {
              leaf string-test {
                type string;
              }
            }
          }
          list to-pointer-test2 {
            key "first-key";
            leaf first-key {
              type uint8;
            }
            list second-list {
              key "second-key";
              leaf second-key {
                type uint8;
              }
              leaf second-string {
                type string;
              }
              container second-container {
                leaf second-container-string {
                  type string;
                }
              }
            }
          }
          container nested-container {
            container cone {
              leaf a {
                type uint8;
                default "1";
              }
              leaf b {
                type uint8;
                default "2";
              }
              leaf c {
                type uint8;
                default "3";
              }
            }
            container ctwo {
              config false;
              leaf d {
                type uint8;
              }
              leaf e {
                type uint8;
              }
              leaf f {
                type uint8;
              }
            }
          }
          container read-only {
            config false;
            uses red-blue-group;
            container name {
              container collision {
                leaf test {
                  type uint8;
                }
                container child1 {
                  container child2 {
                    leaf test {
                      type uint8;
                    }
                  }
                }
              }
            }
            container name-collision {
              leaf test {
                type uint8;
              }
              container child1 {
                container child2 {
                  leaf test {
                    type uint8;
                  }
                }
              }
            }
          }
          container remove-via-deviation {
            uses red-blue-group;
          }
          uses ordered-lists-group;
          container simple-deadline-test {
            uses deadline-group;
          }
          container simple-test-container {
            ciena-common-yang:containerptr "true";
            list keys-only-list {
              key "name";
              leaf name {
                type string;
              }
            }
            leaf other-attribute {
              type string;
            }
            container leaf-test {
              leaf string-test {
                ciena-common-yang:encrypt "string-test-encrypted";
                ciena-common-yang:encrypt-path "/ciena-common-test/simple-test-container/leaf-test";
                type string;
              }
              leaf string-test-encrypted {
                type string {
                  ciena-common-yang:stringptr "true";
                }
                ciena-common-yang:decrypt "string-test";
                ciena-common-yang:decrypt-path "/ciena-common-test/simple-test-container/leaf-test";
              }
              leaf uint8-test {
                type uint8;
              }
            }
            container presence-test {
              presence "presense test container";
            }
            container presence-test-2 {
              choice start-time {
                mandatory true;
                container immediate {
                  presence "Start the measurement session immediately.";
                }
                leaf relative {
                  type string;
                }
                leaf absolute {
                  type string;
                }
              }
            }
            list outter {
              key "index";
              leaf index {
                type uint8;
              }
              min-elements 2;
              max-elements 3;
              list inner {
                key "name";
                leaf name {
                  type string;
                }
                max-elements 2;
                leaf value {
                  type uint16;
                }
              }
              leaf-list boolean-leaf-list {
                type boolean;
                max-elements 3;
                min-elements 2;
              }
              leaf mode {
                type uint8 {
                  range "0..10";
                }
              }
            }
            list first {
              key "key1 key2";
              leaf key1 {
                type uint8;
              }
              leaf key2 {
                type string;
              }
              list second {
                key "key1 key2";
                leaf key1 {
                  type uint8;
                }
                leaf key2 {
                  type string;
                }
                list third {
                  key "key1";
                  leaf key1 {
                    type uint8;
                  }
                  container red {
                    container blue {
                      leaf a {
                        type string;
                      }
                      leaf b {
                        type string;
                      }
                    }
                    leaf yellow-leaf {
                      type string;
                    }
                    anyxml config;
                  }
                }
              }
            }
          }
          container list-keys {
            list bits-key {
              key "bit";
              leaf bit {
                type bits {
                  bit x;
                  bit y;
                  bit z;
                }
              }
            }
          }
          container identity-test {
            leaf base-test {
              type identityref {
                base test:crypto-alg;
              }
            }
            leaf mid-level-test {
              type identityref {
                base test:des;
              }
            }
            leaf top-test {
              type identityref {
                base test:des3;
              }
            }
            leaf external-test {
              type identityref {
                base ciena-common-yang:error-does-not-exist;
              }
            }
          }
          container encryption-test-container {
            container container-generate-at-abs-path-enc {
              ciena-common-yang:decrypt "container-generate-at-abs-path";
              ciena-common-yang:decrypt-path "/ciena-common-test/encryption-test-container";
              leaf a {
                type string {
                  ciena-common-yang:stringptr "true";
                }
                ciena-common-yang:decrypt "a";
                ciena-common-yang:decrypt-path "/ciena-common-test/encryption-test-container/container-generate-at-abs-path";
              }
              container b {
                ciena-common-yang:decrypt "b";
                ciena-common-yang:decrypt-path "/ciena-common-test/encryption-test-container/container-generate-at-abs-path";
                leaf c {
                  type string {
                    ciena-common-yang:stringptr "true";
                  }
                  ciena-common-yang:decrypt "c";
                  ciena-common-yang:decrypt-path "/ciena-common-test/encryption-test-container/container-generate-at-abs-path/b";
                }
              }
              config false;
            }
            list encryption-mount-test {
              key "name";
              leaf name {
                type string;
              }
              container data {
                ciena-common-yang:mount-start "ciena-common-test";
                ciena-common-yang:mount-end "ciena-common-test";
              }
            }
            list instance {
              key "name";
              leaf name {
                type string;
              }
              container result {
                ciena-common-yang:encrypt "container-1";
                ciena-common-yang:encrypt-path "/ciena-common-test/encryption-test-container/instance";
                list amp {
                  ciena-common-yang:encrypt "amp";
                  ciena-common-yang:encrypt-path "/ciena-common-test/encryption-test-container/instance/container-1";
                  key "amp_name";
                  leaf amp_name {
                    ciena-common-yang:encrypt "amp_name";
                    ciena-common-yang:encrypt-path "/ciena-common-test/encryption-test-container/instance/container-1/amp";
                    type string;
                  }
                  list measurement-no-power {
                    ciena-common-yang:encrypt "measurement-no-power";
                    ciena-common-yang:encrypt-path "/ciena-common-test/encryption-test-container/instance/container-1/amp";
                    description
                      "Power measurements of span measured with all channels blocked.";
                    key "index";
                    leaf index {
                      ciena-common-yang:encrypt "index";
                      ciena-common-yang:encrypt-path "/ciena-common-test/encryption-test-container/instance/container-1/amp/measurement-no-power";
                      type uint8;
                    }
                    leaf in-current-power {
                      ciena-common-yang:encrypt "in-current-power";
                      ciena-common-yang:encrypt-path "/ciena-common-test/encryption-test-container/instance/container-1/amp/measurement-no-power";
                      type decimal64 {
                        fraction-digits 1;
                      }
                    }
                    leaf in-min-power {
                      ciena-common-yang:encrypt "in-min-power";
                      ciena-common-yang:encrypt-path "/ciena-common-test/encryption-test-container/instance/container-1/amp/measurement-no-power";
                      type decimal64 {
                        fraction-digits 1;
                      }
                    }
                    config false;
                  }
                }
              }
              container container-1 {
                ciena-common-yang:decrypt "result";
                ciena-common-yang:decrypt-path "/ciena-common-test/encryption-test-container/instance";
                list amp {
                  ciena-common-yang:decrypt "amp";
                  ciena-common-yang:decrypt-path "/ciena-common-test/encryption-test-container/instance/result";
                  key "amp_name";
                  leaf amp_name {
                    type string {
                      ciena-common-yang:stringptr "true";
                    }
                    ciena-common-yang:decrypt "amp_name";
                    ciena-common-yang:decrypt-path "/ciena-common-test/encryption-test-container/instance/result/amp";
                  }
                  list measurement-no-power {
                    ciena-common-yang:decrypt "measurement-no-power";
                    ciena-common-yang:decrypt-path "/ciena-common-test/encryption-test-container/instance/result/amp";
                    key "index";
                    leaf index {
                      type string {
                        ciena-common-yang:stringptr "true";
                      }
                      ciena-common-yang:decrypt "index";
                      ciena-common-yang:decrypt-path "/ciena-common-test/encryption-test-container/instance/result/amp/measurement-no-power";
                    }
                    leaf in-current-power {
                      type string {
                        ciena-common-yang:stringptr "true";
                      }
                      ciena-common-yang:decrypt "in-current-power";
                      ciena-common-yang:decrypt-path "/ciena-common-test/encryption-test-container/instance/result/amp/measurement-no-power";
                    }
                    leaf in-min-power {
                      type string {
                        ciena-common-yang:stringptr "true";
                      }
                      ciena-common-yang:decrypt "in-min-power";
                      ciena-common-yang:decrypt-path "/ciena-common-test/encryption-test-container/instance/result/amp/measurement-no-power";
                    }
                    config false;
                  }
                }
              }
              list some-other-list {
                key "name";
                leaf name {
                  type string;
                }
                leaf measurement {
                  type uint8;
                }
              }
            }
            list key-in-grouping {
              ciena-common-yang:encrypt "key-in-grouping-encrypted";
              ciena-common-yang:encrypt-path "/ciena-common-test/encryption-test-container";
              description
                "test list key leaf definition can be provided by grouping";
              key "name";
              leaf name {
                ciena-common-yang:encrypt "name";
                ciena-common-yang:encrypt-path "/ciena-common-test/encryption-test-container/key-in-grouping-encrypted";
                type string;
              }
              leaf stats {
                ciena-common-yang:encrypt "stats";
                ciena-common-yang:encrypt-path "/ciena-common-test/encryption-test-container/key-in-grouping-encrypted";
                type uint32;
              }
            }
            list key-in-grouping-encrypted {
              ciena-common-yang:decrypt "key-in-grouping";
              ciena-common-yang:decrypt-path "/ciena-common-test/encryption-test-container";
              key "name";
              leaf name {
                type string {
                  ciena-common-yang:stringptr "true";
                }
                ciena-common-yang:decrypt "name";
                ciena-common-yang:decrypt-path "/ciena-common-test/encryption-test-container/key-in-grouping";
              }
              leaf stats {
                type string {
                  ciena-common-yang:stringptr "true";
                }
                ciena-common-yang:decrypt "stats";
                ciena-common-yang:decrypt-path "/ciena-common-test/encryption-test-container/key-in-grouping";
              }
            }
            list list-enc-generate-with-renamed-leaves {
              ciena-common-yang:encrypt "list-enc-generate-with-renamed-leaves-enc";
              ciena-common-yang:encrypt-path "/ciena-common-test/encryption-test-container";
              description
                "test list encryption with nested containers and leaves renamed";
              key "name";
              leaf name {
                ciena-common-yang:encrypt "name";
                ciena-common-yang:encrypt-path "/ciena-common-test/encryption-test-container/list-enc-generate-with-renamed-leaves-enc";
                type string;
              }
              leaf aaa {
                ciena-common-yang:encrypt "aaa-enc";
                ciena-common-yang:encrypt-path "/ciena-common-test/encryption-test-container/list-enc-generate-with-renamed-leaves-enc";
                type uint8;
                ciena-common-yang:sensitive "true";
              }
              container ddd {
                ciena-common-yang:encrypt "ddd-enc";
                ciena-common-yang:encrypt-path "/ciena-common-test/encryption-test-container/list-enc-generate-with-renamed-leaves-enc";
                leaf eee {
                  ciena-common-yang:encrypt "eee-enc";
                  ciena-common-yang:encrypt-path "/ciena-common-test/encryption-test-container/list-enc-generate-with-renamed-leaves-enc/ddd-enc";
                  type uint8;
                }
                leaf fff {
                  ciena-common-yang:encrypt "fff";
                  ciena-common-yang:encrypt-path "/ciena-common-test/encryption-test-container/list-enc-generate-with-renamed-leaves-enc/ddd-enc";
                  type uint8;
                }
                config false;
              }
            }
            list list-enc-generate-with-renamed-leaves-enc {
              ciena-common-yang:decrypt "list-enc-generate-with-renamed-leaves";
              ciena-common-yang:decrypt-path "/ciena-common-test/encryption-test-container";
              key "name";
              leaf name {
                type string {
                  ciena-common-yang:stringptr "true";
                }
                ciena-common-yang:decrypt "name";
                ciena-common-yang:decrypt-path "/ciena-common-test/encryption-test-container/list-enc-generate-with-renamed-leaves";
              }
              leaf aaa-enc {
                type string {
                  ciena-common-yang:stringptr "true";
                }
                ciena-common-yang:decrypt "aaa";
                ciena-common-yang:decrypt-path "/ciena-common-test/encryption-test-container/list-enc-generate-with-renamed-leaves";
                ciena-common-yang:sensitive "true";
              }
              container ddd-enc {
                ciena-common-yang:decrypt "ddd";
                ciena-common-yang:decrypt-path "/ciena-common-test/encryption-test-container/list-enc-generate-with-renamed-leaves";
                leaf eee-enc {
                  type string {
                    ciena-common-yang:stringptr "true";
                  }
                  ciena-common-yang:decrypt "eee";
                  ciena-common-yang:decrypt-path "/ciena-common-test/encryption-test-container/list-enc-generate-with-renamed-leaves/ddd";
                }
                leaf fff {
                  type string {
                    ciena-common-yang:stringptr "true";
                  }
                  ciena-common-yang:decrypt "fff";
                  ciena-common-yang:decrypt-path "/ciena-common-test/encryption-test-container/list-enc-generate-with-renamed-leaves/ddd";
                }
                config false;
              }
            }
            list list-generate-with-enc-path-for-leaves {
              ciena-common-yang:encrypt "list-generate-with-enc-path-for-leaves-enc";
              ciena-common-yang:encrypt-path "/ciena-common-test/encryption-test-container";
              description
                "test list encryption with some leaves having encryption-path and encryption-relative-path information";
              key "index";
              leaf index {
                ciena-common-yang:encrypt "index-enc";
                ciena-common-yang:encrypt-path "/ciena-common-test/encryption-test-container/list-generate-with-enc-path-for-leaves-enc";
                type uint8;
              }
              leaf ggg {
                ciena-common-yang:encrypt "ggg";
                ciena-common-yang:encrypt-path "/ciena-common-test/encryption-test-container/list-generate-with-enc-path-for-leaves-enc";
                type uint8;
              }
              container hhh {
                ciena-common-yang:encrypt "hhh";
                ciena-common-yang:encrypt-path "/ciena-common-test/encryption-test-container/list-generate-with-enc-path-for-leaves-enc";
                leaf iii {
                  ciena-common-yang:encrypt "iii-enc";
                  ciena-common-yang:encrypt-path "/ciena-common-test/encryption-test-container/list-generate-with-enc-path-for-leaves-enc/hhh";
                  type uint8;
                }
                leaf jjj {
                  ciena-common-yang:encrypt "none-existing-leaf";
                  ciena-common-yang:encrypt-path "/ciena-common-test/encryption-test-container/A/B";
                  type uint8;
                  ciena-common-yang:sensitive "true";
                }
                leaf kkk {
                  ciena-common-yang:encrypt "none-existing-leaf-2";
                  ciena-common-yang:encrypt-path "/ciena-common-test/encryption-test-container/A/B";
                  type uint8;
                  config false;
                  ciena-common-yang:sensitive "true";
                }
              }
            }
            list list-generate-with-enc-path-for-leaves-enc {
              ciena-common-yang:decrypt "list-generate-with-enc-path-for-leaves";
              ciena-common-yang:decrypt-path "/ciena-common-test/encryption-test-container";
              key "index-enc";
              leaf index-enc {
                type string {
                  ciena-common-yang:stringptr "true";
                }
                ciena-common-yang:decrypt "index";
                ciena-common-yang:decrypt-path "/ciena-common-test/encryption-test-container/list-generate-with-enc-path-for-leaves";
              }
              leaf ggg {
                type string {
                  ciena-common-yang:stringptr "true";
                }
                ciena-common-yang:decrypt "ggg";
                ciena-common-yang:decrypt-path "/ciena-common-test/encryption-test-container/list-generate-with-enc-path-for-leaves";
              }
              container hhh {
                ciena-common-yang:decrypt "hhh";
                ciena-common-yang:decrypt-path "/ciena-common-test/encryption-test-container/list-generate-with-enc-path-for-leaves";
                leaf iii-enc {
                  type string {
                    ciena-common-yang:stringptr "true";
                  }
                  ciena-common-yang:decrypt "iii";
                  ciena-common-yang:decrypt-path "/ciena-common-test/encryption-test-container/list-generate-with-enc-path-for-leaves/hhh";
                }
              }
            }
            container A {
              container B {
                leaf none-existing-leaf {
                  ciena-common-yang:decrypt "jjj";
                  ciena-common-yang:decrypt-path "/ciena-common-test/encryption-test-container/list-generate-with-enc-path-for-leaves/hhh";
                  type string {
                    ciena-common-yang:stringptr "true";
                  }
                  ciena-common-yang:sensitive "true";
                }
                leaf none-existing-leaf-2 {
                  ciena-common-yang:decrypt "kkk";
                  ciena-common-yang:decrypt-path "/ciena-common-test/encryption-test-container/list-generate-with-enc-path-for-leaves/hhh";
                  type string {
                    ciena-common-yang:stringptr "true";
                  }
                  ciena-common-yang:sensitive "true";
                  config false;
                }
                leaf y {
                  type string {
                    ciena-common-yang:stringptr "true";
                  }
                }
                leaf z {
                  type uint8;
                }
              }
            }
            container container-generate-as-sibling {
              ciena-common-yang:encrypt "container-generate-as-sibling-enc";
              ciena-common-yang:encrypt-path "/ciena-common-test/encryption-test-container";
              description
                "test simple container encryption default generating as siblings";
              leaf a {
                ciena-common-yang:encrypt "a";
                ciena-common-yang:encrypt-path "/ciena-common-test/encryption-test-container/container-generate-as-sibling-enc";
                type uint8;
              }
              container b {
                ciena-common-yang:encrypt "b";
                ciena-common-yang:encrypt-path "/ciena-common-test/encryption-test-container/container-generate-as-sibling-enc";
                leaf c {
                  ciena-common-yang:encrypt "c";
                  ciena-common-yang:encrypt-path "/ciena-common-test/encryption-test-container/container-generate-as-sibling-enc/b";
                  type uint8;
                }
              }
            }
            container container-generate-as-sibling-enc {
              ciena-common-yang:decrypt "container-generate-as-sibling";
              ciena-common-yang:decrypt-path "/ciena-common-test/encryption-test-container";
              leaf a {
                type string {
                  ciena-common-yang:stringptr "true";
                }
                ciena-common-yang:decrypt "a";
                ciena-common-yang:decrypt-path "/ciena-common-test/encryption-test-container/container-generate-as-sibling";
              }
              container b {
                ciena-common-yang:decrypt "b";
                ciena-common-yang:decrypt-path "/ciena-common-test/encryption-test-container/container-generate-as-sibling";
                leaf c {
                  type string {
                    ciena-common-yang:stringptr "true";
                  }
                  ciena-common-yang:decrypt "c";
                  ciena-common-yang:decrypt-path "/ciena-common-test/encryption-test-container/container-generate-as-sibling/b";
                }
              }
            }
            container X {
              container Z {
                container container-generate-at-relative-path {
                  ciena-common-yang:encrypt "container-generate-at-relative-path-enc";
                  ciena-common-yang:encrypt-path "/ciena-common-test/encryption-test-container/K";
                  description
                    "test container encryption with encrypt-relative-path information";
                  container red {
                    ciena-common-yang:encrypt "red";
                    ciena-common-yang:encrypt-path "/ciena-common-test/encryption-test-container/K/container-generate-at-relative-path-enc";
                    container blue {
                      ciena-common-yang:encrypt "blue";
                      ciena-common-yang:encrypt-path "/ciena-common-test/encryption-test-container/K/container-generate-at-relative-path-enc/red";
                      leaf a {
                        ciena-common-yang:encrypt "a";
                        ciena-common-yang:encrypt-path "/ciena-common-test/encryption-test-container/K/container-generate-at-relative-path-enc/red/blue";
                        type uint8;
                      }
                      leaf b {
                        ciena-common-yang:encrypt "b";
                        ciena-common-yang:encrypt-path "/ciena-common-test/encryption-test-container/K/container-generate-at-relative-path-enc/red/blue";
                        type uint8;
                        default "22";
                      }
                      leaf c {
                        ciena-common-yang:encrypt "c";
                        ciena-common-yang:encrypt-path "/ciena-common-test/encryption-test-container/K/container-generate-at-relative-path-enc/red/blue";
                        type uint8;
                        default "44";
                      }
                      leaf d {
                        ciena-common-yang:encrypt "d";
                        ciena-common-yang:encrypt-path "/ciena-common-test/encryption-test-container/K/container-generate-at-relative-path-enc/red/blue";
                        type uint8;
                        default "88";
                      }
                    }
                  }
                  leaf a {
                    ciena-common-yang:encrypt "a";
                    ciena-common-yang:encrypt-path "/ciena-common-test/encryption-test-container/K/container-generate-at-relative-path-enc";
                    type uint8;
                  }
                  container b {
                    ciena-common-yang:encrypt "b";
                    ciena-common-yang:encrypt-path "/ciena-common-test/encryption-test-container/K/container-generate-at-relative-path-enc";
                    container red {
                      ciena-common-yang:encrypt "red";
                      ciena-common-yang:encrypt-path "/ciena-common-test/encryption-test-container/K/container-generate-at-relative-path-enc/b";
                      container blue {
                        ciena-common-yang:encrypt "blue";
                        ciena-common-yang:encrypt-path "/ciena-common-test/encryption-test-container/K/container-generate-at-relative-path-enc/b/red";
                        leaf a {
                          ciena-common-yang:encrypt "a";
                          ciena-common-yang:encrypt-path "/ciena-common-test/encryption-test-container/K/container-generate-at-relative-path-enc/b/red/blue";
                          type uint8;
                        }
                        leaf b {
                          ciena-common-yang:encrypt "b";
                          ciena-common-yang:encrypt-path "/ciena-common-test/encryption-test-container/K/container-generate-at-relative-path-enc/b/red/blue";
                          type uint8;
                          default "22";
                        }
                        leaf c {
                          ciena-common-yang:encrypt "c";
                          ciena-common-yang:encrypt-path "/ciena-common-test/encryption-test-container/K/container-generate-at-relative-path-enc/b/red/blue";
                          type uint8;
                          default "44";
                        }
                        leaf d {
                          ciena-common-yang:encrypt "d";
                          ciena-common-yang:encrypt-path "/ciena-common-test/encryption-test-container/K/container-generate-at-relative-path-enc/b/red/blue";
                          type uint8;
                          default "88";
                        }
                      }
                    }
                    leaf c {
                      ciena-common-yang:encrypt "c";
                      ciena-common-yang:encrypt-path "/ciena-common-test/encryption-test-container/K/container-generate-at-relative-path-enc/b";
                      type uint8;
                    }
                  }
                  config false;
                }
              }
            }
            container K {
              container container-generate-at-relative-path-enc {
                ciena-common-yang:decrypt "container-generate-at-relative-path";
                ciena-common-yang:decrypt-path "/ciena-common-test/encryption-test-container/X/Z";
                container red {
                  ciena-common-yang:decrypt "red";
                  ciena-common-yang:decrypt-path "/ciena-common-test/encryption-test-container/X/Z/container-generate-at-relative-path";
                  container blue {
                    ciena-common-yang:decrypt "blue";
                    ciena-common-yang:decrypt-path "/ciena-common-test/encryption-test-container/X/Z/container-generate-at-relative-path/red";
                    leaf a {
                      type string {
                        ciena-common-yang:stringptr "true";
                      }
                      ciena-common-yang:decrypt "a";
                      ciena-common-yang:decrypt-path "/ciena-common-test/encryption-test-container/X/Z/container-generate-at-relative-path/red/blue";
                    }
                    leaf b {
                      type string {
                        ciena-common-yang:stringptr "true";
                      }
                      ciena-common-yang:decrypt "b";
                      ciena-common-yang:decrypt-path "/ciena-common-test/encryption-test-container/X/Z/container-generate-at-relative-path/red/blue";
                    }
                    leaf c {
                      type string {
                        ciena-common-yang:stringptr "true";
                      }
                      ciena-common-yang:decrypt "c";
                      ciena-common-yang:decrypt-path "/ciena-common-test/encryption-test-container/X/Z/container-generate-at-relative-path/red/blue";
                    }
                    leaf d {
                      type string {
                        ciena-common-yang:stringptr "true";
                      }
                      ciena-common-yang:decrypt "d";
                      ciena-common-yang:decrypt-path "/ciena-common-test/encryption-test-container/X/Z/container-generate-at-relative-path/red/blue";
                    }
                  }
                }
                leaf a {
                  type string {
                    ciena-common-yang:stringptr "true";
                  }
                  ciena-common-yang:decrypt "a";
                  ciena-common-yang:decrypt-path "/ciena-common-test/encryption-test-container/X/Z/container-generate-at-relative-path";
                }
                container b {
                  ciena-common-yang:decrypt "b";
                  ciena-common-yang:decrypt-path "/ciena-common-test/encryption-test-container/X/Z/container-generate-at-relative-path";
                  container red {
                    ciena-common-yang:decrypt "red";
                    ciena-common-yang:decrypt-path "/ciena-common-test/encryption-test-container/X/Z/container-generate-at-relative-path/b";
                    container blue {
                      ciena-common-yang:decrypt "blue";
                      ciena-common-yang:decrypt-path "/ciena-common-test/encryption-test-container/X/Z/container-generate-at-relative-path/b/red";
                      leaf a {
                        type string {
                          ciena-common-yang:stringptr "true";
                        }
                        ciena-common-yang:decrypt "a";
                        ciena-common-yang:decrypt-path "/ciena-common-test/encryption-test-container/X/Z/container-generate-at-relative-path/b/red/blue";
                      }
                      leaf b {
                        type string {
                          ciena-common-yang:stringptr "true";
                        }
                        ciena-common-yang:decrypt "b";
                        ciena-common-yang:decrypt-path "/ciena-common-test/encryption-test-container/X/Z/container-generate-at-relative-path/b/red/blue";
                      }
                      leaf c {
                        type string {
                          ciena-common-yang:stringptr "true";
                        }
                        ciena-common-yang:decrypt "c";
                        ciena-common-yang:decrypt-path "/ciena-common-test/encryption-test-container/X/Z/container-generate-at-relative-path/b/red/blue";
                      }
                      leaf d {
                        type string {
                          ciena-common-yang:stringptr "true";
                        }
                        ciena-common-yang:decrypt "d";
                        ciena-common-yang:decrypt-path "/ciena-common-test/encryption-test-container/X/Z/container-generate-at-relative-path/b/red/blue";
                      }
                    }
                  }
                  leaf c {
                    type string {
                      ciena-common-yang:stringptr "true";
                    }
                    ciena-common-yang:decrypt "c";
                    ciena-common-yang:decrypt-path "/ciena-common-test/encryption-test-container/X/Z/container-generate-at-relative-path/b";
                  }
                }
                config false;
              }
              leaf l {
                type uint8;
              }
            }
            container container-generate-at-abs-path {
              ciena-common-yang:encrypt "container-generate-at-abs-path-enc";
              ciena-common-yang:encrypt-path "/ciena-common-test/encryption-test-container";
              description
                "test container encryption with absolute path encrypt-path information";
              leaf a {
                ciena-common-yang:encrypt "a";
                ciena-common-yang:encrypt-path "/ciena-common-test/encryption-test-container/container-generate-at-abs-path-enc";
                type uint8;
              }
              container b {
                ciena-common-yang:encrypt "b";
                ciena-common-yang:encrypt-path "/ciena-common-test/encryption-test-container/container-generate-at-abs-path-enc";
                leaf c {
                  ciena-common-yang:encrypt "c";
                  ciena-common-yang:encrypt-path "/ciena-common-test/encryption-test-container/container-generate-at-abs-path-enc/b";
                  type uint8;
                }
              }
              config false;
            }
            container encrypt-to-existing-container {
              ciena-common-yang:encrypt "encrypt-to-existing-container-encrypted";
              ciena-common-yang:encrypt-path "/ciena-common-test/encryption-test-container";
              description
                "test container encryption to existing container. no generation will happen.";
              leaf a {
                ciena-common-yang:encrypt "a";
                ciena-common-yang:encrypt-path "/ciena-common-test/encryption-test-container/encrypt-to-existing-container-encrypted";
                type uint8;
              }
            }
            container encrypt-to-existing-container-encrypted {
              ciena-common-yang:decrypt "encrypt-to-existing-container";
              ciena-common-yang:decrypt-path "/ciena-common-test/encryption-test-container";
              leaf a {
                ciena-common-yang:decrypt "a";
                ciena-common-yang:decrypt-path "/ciena-common-test/encryption-test-container/encrypt-to-existing-container";
                type string {
                  ciena-common-yang:stringptr "true";
                }
              }
            }
            container outter-container {
              ciena-common-yang:encrypt "outter-container-enc";
              ciena-common-yang:encrypt-path "/ciena-common-test/encryption-test-container";
              description
                "simple nested container test";
              leaf aaa {
                ciena-common-yang:encrypt "aaa";
                ciena-common-yang:encrypt-path "/ciena-common-test/encryption-test-container/outter-container-enc";
                type uint8;
              }
              container middle-container {
                ciena-common-yang:encrypt "middle-container";
                ciena-common-yang:encrypt-path "/ciena-common-test/encryption-test-container/outter-container-enc";
                leaf bbb {
                  ciena-common-yang:encrypt "bbb";
                  ciena-common-yang:encrypt-path "/ciena-common-test/encryption-test-container/outter-container-enc/middle-container";
                  type uint8;
                }
                container inner-container {
                  ciena-common-yang:encrypt "inner-container";
                  ciena-common-yang:encrypt-path "/ciena-common-test/encryption-test-container/outter-container-enc/middle-container";
                  leaf ccc {
                    ciena-common-yang:encrypt "ccc";
                    ciena-common-yang:encrypt-path "/ciena-common-test/encryption-test-container/outter-container-enc/middle-container/inner-container";
                    type uint8;
                  }
                }
              }
            }
            container outter-container-enc {
              ciena-common-yang:decrypt "outter-container";
              ciena-common-yang:decrypt-path "/ciena-common-test/encryption-test-container";
              leaf aaa {
                type string {
                  ciena-common-yang:stringptr "true";
                }
                ciena-common-yang:decrypt "aaa";
                ciena-common-yang:decrypt-path "/ciena-common-test/encryption-test-container/outter-container";
              }
              container middle-container {
                ciena-common-yang:decrypt "middle-container";
                ciena-common-yang:decrypt-path "/ciena-common-test/encryption-test-container/outter-container";
                leaf bbb {
                  type string {
                    ciena-common-yang:stringptr "true";
                  }
                  ciena-common-yang:decrypt "bbb";
                  ciena-common-yang:decrypt-path "/ciena-common-test/encryption-test-container/outter-container/middle-container";
                }
                container inner-container {
                  ciena-common-yang:decrypt "inner-container";
                  ciena-common-yang:decrypt-path "/ciena-common-test/encryption-test-container/outter-container/middle-container";
                  leaf ccc {
                    type string {
                      ciena-common-yang:stringptr "true";
                    }
                    ciena-common-yang:decrypt "ccc";
                    ciena-common-yang:decrypt-path "/ciena-common-test/encryption-test-container/outter-container/middle-container/inner-container";
                  }
                }
              }
            }
            container one-to-two-container {
              ciena-common-yang:encrypt "one-to-two-container-enc";
              ciena-common-yang:encrypt-path "/ciena-common-test/encryption-test-container";
              description
                "error scenario test: leaves under one container encrypted to two containers
                 is not fully supported, the leaves for one container will be missing";
              leaf aaa {
                ciena-common-yang:encrypt "aaa";
                ciena-common-yang:encrypt-path "/ciena-common-test/encryption-test-container/one-to-two-container-enc";
                type uint8;
              }
              leaf-list bbb {
                ciena-common-yang:encrypt "bbb";
                ciena-common-yang:encrypt-path "/ciena-common-test/encryption-test-container/one-to-two-container-other";
                type uint8;
              }
              container inner-container {
                ciena-common-yang:encrypt "inner-container";
                ciena-common-yang:encrypt-path "/ciena-common-test/encryption-test-container/one-to-two-container-enc";
                leaf-list ccc {
                  ciena-common-yang:encrypt "ccc";
                  ciena-common-yang:encrypt-path "/ciena-common-test/encryption-test-container/one-to-two-container-enc/inner-container";
                  type uint8;
                }
                leaf ddd {
                  ciena-common-yang:encrypt "ddd";
                  ciena-common-yang:encrypt-path "/ciena-common-test/encryption-test-container/one-to-two-container-other";
                  type uint8;
                }
              }
            }
            container one-to-two-container-enc {
              ciena-common-yang:decrypt "one-to-two-container";
              ciena-common-yang:decrypt-path "/ciena-common-test/encryption-test-container";
              leaf aaa {
                type string {
                  ciena-common-yang:stringptr "true";
                }
                ciena-common-yang:decrypt "aaa";
                ciena-common-yang:decrypt-path "/ciena-common-test/encryption-test-container/one-to-two-container";
              }
              container inner-container {
                ciena-common-yang:decrypt "inner-container";
                ciena-common-yang:decrypt-path "/ciena-common-test/encryption-test-container/one-to-two-container";
                leaf-list ccc {
                  type string {
                    ciena-common-yang:stringptr "true";
                  }
                  ciena-common-yang:decrypt "ccc";
                  ciena-common-yang:decrypt-path "/ciena-common-test/encryption-test-container/one-to-two-container/inner-container";
                }
              }
            }
            container one-to-two-container-other {
              leaf-list bbb {
                ciena-common-yang:decrypt "bbb";
                ciena-common-yang:decrypt-path "/ciena-common-test/encryption-test-container/one-to-two-container";
                type string {
                  ciena-common-yang:stringptr "true";
                }
              }
              leaf ddd {
                ciena-common-yang:decrypt "ddd";
                ciena-common-yang:decrypt-path "/ciena-common-test/encryption-test-container/one-to-two-container/inner-container";
                type string {
                  ciena-common-yang:stringptr "true";
                }
              }
              leaf fff {
                type uint8;
              }
            }
            list nested-list {
              ciena-common-yang:encrypt "nested-list-enc";
              ciena-common-yang:encrypt-path "/ciena-common-test/encryption-test-container";
              description
                "test nested list encryption";
              key "name";
              leaf name {
                ciena-common-yang:encrypt "name";
                ciena-common-yang:encrypt-path "/ciena-common-test/encryption-test-container/nested-list-enc";
                type stringptr;
              }
              leaf aaa {
                ciena-common-yang:encrypt "aaa";
                ciena-common-yang:encrypt-path "/ciena-common-test/encryption-test-container/nested-list-enc";
                type uint8;
              }
              list inner-list {
                ciena-common-yang:encrypt "inner-list";
                ciena-common-yang:encrypt-path "/ciena-common-test/encryption-test-container/nested-list-enc";
                key "index";
                leaf index {
                  ciena-common-yang:encrypt "index";
                  ciena-common-yang:encrypt-path "/ciena-common-test/encryption-test-container/nested-list-enc/inner-list";
                  type uint8;
                }
                leaf-list ccc {
                  ciena-common-yang:encrypt "ccc";
                  ciena-common-yang:encrypt-path "/ciena-common-test/encryption-test-container/nested-list-enc/inner-list";
                  type string;
                }
              }
            }
            list nested-list-enc {
              ciena-common-yang:decrypt "nested-list";
              ciena-common-yang:decrypt-path "/ciena-common-test/encryption-test-container";
              key "name";
              leaf name {
                type string {
                  ciena-common-yang:stringptr "true";
                }
                ciena-common-yang:decrypt "name";
                ciena-common-yang:decrypt-path "/ciena-common-test/encryption-test-container/nested-list";
              }
              leaf aaa {
                type string {
                  ciena-common-yang:stringptr "true";
                }
                ciena-common-yang:decrypt "aaa";
                ciena-common-yang:decrypt-path "/ciena-common-test/encryption-test-container/nested-list";
              }
              list inner-list {
                ciena-common-yang:decrypt "inner-list";
                ciena-common-yang:decrypt-path "/ciena-common-test/encryption-test-container/nested-list";
                key "index";
                leaf index {
                  type string {
                    ciena-common-yang:stringptr "true";
                  }
                  ciena-common-yang:decrypt "index";
                  ciena-common-yang:decrypt-path "/ciena-common-test/encryption-test-container/nested-list/inner-list";
                }
                leaf-list ccc {
                  type string {
                    ciena-common-yang:stringptr "true";
                  }
                  ciena-common-yang:decrypt "ccc";
                  ciena-common-yang:decrypt-path "/ciena-common-test/encryption-test-container/nested-list/inner-list";
                }
              }
            }
            container other {
              leaf ccc {
                type string;
              }
            }
            container user-defined-leaves {
              description
                "selected leaves encryption container";
              leaf a {
                ciena-common-yang:encrypt "x";
                ciena-common-yang:encrypt-path "/ciena-common-test/encryption-test-container/user-defined-leaves-encrypted";
                type string;
              }
              leaf b {
                type string;
              }
            }
            container user-defined-leaves-encrypted {
              leaf x {
                ciena-common-yang:decrypt "a";
                ciena-common-yang:decrypt-path "/ciena-common-test/encryption-test-container/user-defined-leaves";
                type string;
              }
            }
            list nested-list-leaf-encryption {
              key "name";
              leaf name {
                type string;
              }
              leaf x {
                ciena-common-yang:encrypt "x-enc";
                ciena-common-yang:encrypt-path "/ciena-common-test/encryption-test-container/nested-list-leaf-encryption";
                type string;
              }
              leaf x-enc {
                type string {
                  ciena-common-yang:stringptr "true";
                }
                ciena-common-yang:decrypt "x";
                ciena-common-yang:decrypt-path "/ciena-common-test/encryption-test-container/nested-list-leaf-encryption";
              }
              list inner {
                key "index";
                leaf index {
                  type uint8;
                }
                leaf u {
                  ciena-common-yang:encrypt "u-enc";
                  ciena-common-yang:encrypt-path "/ciena-common-test/encryption-test-container/nested-list-leaf-encryption/inner";
                  type string;
                }
                leaf u-enc {
                  type string {
                    ciena-common-yang:stringptr "true";
                  }
                  ciena-common-yang:decrypt "u";
                  ciena-common-yang:decrypt-path "/ciena-common-test/encryption-test-container/nested-list-leaf-encryption/inner";
                }
              }
            }
            list encryption-list-test {
              key "key1 key2";
              leaf key1 {
                type stringptr;
              }
              leaf key2 {
                type typetest;
              }
              container leaf-list-test {
                leaf-list binary-test {
                  ciena-common-yang:encrypt "binary-test-encrypted";
                  ciena-common-yang:encrypt-path "/ciena-common-test/encryption-test-container/encryption-list-test/leaf-list-test";
                  type binary;
                }
                leaf-list binary-test-encrypted {
                  type string {
                    ciena-common-yang:stringptr "true";
                  }
                  ciena-common-yang:decrypt "binary-test";
                  ciena-common-yang:decrypt-path "/ciena-common-test/encryption-test-container/encryption-list-test/leaf-list-test";
                }
                leaf-list bits-test {
                  ciena-common-yang:encrypt "bits-test-encrypted";
                  ciena-common-yang:encrypt-path "/ciena-common-test/encryption-test-container/encryption-list-test/leaf-list-test";
                  type bits {
                    bit disable-nagle {
                      position 0;
                    }
                    bit auto-sense-speed {
                      position 1;
                    }
                  }
                }
                leaf-list bits-test-encrypted {
                  type string {
                    ciena-common-yang:stringptr "true";
                  }
                  ciena-common-yang:decrypt "bits-test";
                  ciena-common-yang:decrypt-path "/ciena-common-test/encryption-test-container/encryption-list-test/leaf-list-test";
                }
                leaf-list boolean-test {
                  ciena-common-yang:encrypt "boolean-test-encrypted";
                  ciena-common-yang:encrypt-path "/ciena-common-test/encryption-test-container/encryption-list-test/leaf-list-test";
                  type boolean;
                }
                leaf-list boolean-test-encrypted {
                  type string {
                    ciena-common-yang:stringptr "true";
                  }
                  ciena-common-yang:decrypt "boolean-test";
                  ciena-common-yang:decrypt-path "/ciena-common-test/encryption-test-container/encryption-list-test/leaf-list-test";
                }
                leaf-list decimal64-test {
                  ciena-common-yang:encrypt "decimal64-test-encrypted";
                  ciena-common-yang:encrypt-path "/ciena-common-test/encryption-test-container/encryption-list-test/leaf-list-test";
                  type decimal64 {
                    fraction-digits 10;
                  }
                }
                leaf-list decimal64-test-encrypted {
                  type string {
                    ciena-common-yang:stringptr "true";
                  }
                  ciena-common-yang:decrypt "decimal64-test";
                  ciena-common-yang:decrypt-path "/ciena-common-test/encryption-test-container/encryption-list-test/leaf-list-test";
                }
                leaf-list empty-test {
                  ciena-common-yang:encrypt "empty-test-encrypted";
                  ciena-common-yang:encrypt-path "/ciena-common-test/encryption-test-container/encryption-list-test/leaf-list-test";
                  type empty;
                }
                leaf-list empty-test-encrypted {
                  type string {
                    ciena-common-yang:stringptr "true";
                  }
                  ciena-common-yang:decrypt "empty-test";
                  ciena-common-yang:decrypt-path "/ciena-common-test/encryption-test-container/encryption-list-test/leaf-list-test";
                }
                leaf-list enumeration-test {
                  ciena-common-yang:encrypt "enumeration-test-encrypted";
                  ciena-common-yang:encrypt-path "/ciena-common-test/encryption-test-container/encryption-list-test/leaf-list-test";
                  type enumeration {
                    enum test-a;
                    enum test-b;
                    enum test-c;
                    enum map;
                  }
                }
                leaf-list enumeration-test-encrypted {
                  type string {
                    ciena-common-yang:stringptr "true";
                  }
                  ciena-common-yang:decrypt "enumeration-test";
                  ciena-common-yang:decrypt-path "/ciena-common-test/encryption-test-container/encryption-list-test/leaf-list-test";
                }
                leaf-list identityref-test {
                  ciena-common-yang:encrypt "identityref-test-encrypted";
                  ciena-common-yang:encrypt-path "/ciena-common-test/encryption-test-container/encryption-list-test/leaf-list-test";
                  type identityref {
                    base test:crypto-alg;
                  }
                }
                leaf-list identityref-test-encrypted {
                  type string {
                    ciena-common-yang:stringptr "true";
                  }
                  ciena-common-yang:decrypt "identityref-test";
                  ciena-common-yang:decrypt-path "/ciena-common-test/encryption-test-container/encryption-list-test/leaf-list-test";
                }
                leaf-list instance-identifier-test {
                  ciena-common-yang:encrypt "instance-identifier-test-encrypted";
                  ciena-common-yang:encrypt-path "/ciena-common-test/encryption-test-container/encryption-list-test/leaf-list-test";
                  type instance-identifier;
                }
                leaf-list instance-identifier-test-encrypted {
                  type string {
                    ciena-common-yang:stringptr "true";
                  }
                  ciena-common-yang:decrypt "instance-identifier-test";
                  ciena-common-yang:decrypt-path "/ciena-common-test/encryption-test-container/encryption-list-test/leaf-list-test";
                }
                leaf-list leafref-test {
                  ciena-common-yang:encrypt "leafref-test-encrypted";
                  ciena-common-yang:encrypt-path "/ciena-common-test/encryption-test-container/encryption-list-test/leaf-list-test";
                  type leafref {
                    path "/test:red/test:blue/test:b";
                  }
                }
                leaf-list leafref-test-encrypted {
                  type string {
                    ciena-common-yang:stringptr "true";
                  }
                  ciena-common-yang:decrypt "leafref-test";
                  ciena-common-yang:decrypt-path "/ciena-common-test/encryption-test-container/encryption-list-test/leaf-list-test";
                }
                leaf-list stringptr-test {
                  ciena-common-yang:encrypt "stringptr-test-encrypted";
                  ciena-common-yang:encrypt-path "/ciena-common-test/encryption-test-container/encryption-list-test/leaf-list-test";
                  type stringptr;
                }
                leaf-list stringptr-test-encrypted {
                  type string {
                    ciena-common-yang:stringptr "true";
                  }
                  ciena-common-yang:decrypt "stringptr-test";
                  ciena-common-yang:decrypt-path "/ciena-common-test/encryption-test-container/encryption-list-test/leaf-list-test";
                }
                leaf-list string-test {
                  ciena-common-yang:encrypt "string-test-encrypted";
                  ciena-common-yang:encrypt-path "/ciena-common-test/encryption-test-container/encryption-list-test/leaf-list-test";
                  type string;
                }
                leaf-list string-test-encrypted {
                  type string {
                    ciena-common-yang:stringptr "true";
                  }
                  ciena-common-yang:decrypt "string-test";
                  ciena-common-yang:decrypt-path "/ciena-common-test/encryption-test-container/encryption-list-test/leaf-list-test";
                }
                leaf-list uint8-test {
                  ciena-common-yang:encrypt "uint8-test-encrypted";
                  ciena-common-yang:encrypt-path "/ciena-common-test/encryption-test-container/encryption-list-test/leaf-list-test";
                  type uint8;
                }
                leaf-list uint8-test-encrypted {
                  type string {
                    ciena-common-yang:stringptr "true";
                  }
                  ciena-common-yang:decrypt "uint8-test";
                  ciena-common-yang:decrypt-path "/ciena-common-test/encryption-test-container/encryption-list-test/leaf-list-test";
                }
                leaf-list union-test {
                  ciena-common-yang:encrypt "union-test-encrypted";
                  ciena-common-yang:encrypt-path "/ciena-common-test/encryption-test-container/encryption-list-test/leaf-list-test";
                  type union {
                    type int32;
                    type enumeration {
                      enum unbounded;
                    }
                  }
                }
                leaf-list union-test-encrypted {
                  type string {
                    ciena-common-yang:stringptr "true";
                  }
                  ciena-common-yang:decrypt "union-test";
                  ciena-common-yang:decrypt-path "/ciena-common-test/encryption-test-container/encryption-list-test/leaf-list-test";
                }
              }
              container leaf-test {
                leaf binary-test {
                  ciena-common-yang:encrypt "binary-test-encrypted";
                  ciena-common-yang:encrypt-path "/ciena-common-test/encryption-test-container/encryption-list-test/leaf-test";
                  type binary;
                  ciena-common-yang:sensitive "true";
                }
                leaf binary-test-encrypted {
                  type string {
                    ciena-common-yang:stringptr "true";
                  }
                  ciena-common-yang:decrypt "binary-test";
                  ciena-common-yang:decrypt-path "/ciena-common-test/encryption-test-container/encryption-list-test/leaf-test";
                  ciena-common-yang:sensitive "true";
                }
                leaf bits-test {
                  ciena-common-yang:encrypt "bits-test-encrypted";
                  ciena-common-yang:encrypt-path "/ciena-common-test/encryption-test-container/encryption-list-test/leaf-test";
                  ciena-common-yang:sensitive "true";
                  type bits {
                    bit apple {
                      position 0;
                    }
                    bit orange {
                      position 1;
                    }
                    bit banana {
                      position 2;
                    }
                  }
                }
                leaf bits-test-encrypted {
                  type string {
                    ciena-common-yang:stringptr "true";
                  }
                  ciena-common-yang:decrypt "bits-test";
                  ciena-common-yang:decrypt-path "/ciena-common-test/encryption-test-container/encryption-list-test/leaf-test";
                  ciena-common-yang:sensitive "true";
                }
                leaf offset-bits-test {
                  ciena-common-yang:encrypt "offset-bits-test-encrypted";
                  ciena-common-yang:encrypt-path "/ciena-common-test/encryption-test-container/encryption-list-test/leaf-test";
                  ciena-common-yang:sensitive "true";
                  type bits {
                    bit apple {
                      position 3;
                    }
                    bit orange {
                      position 5;
                    }
                    bit banana {
                      position 7;
                    }
                  }
                }
                leaf offset-bits-test-encrypted {
                  type string {
                    ciena-common-yang:stringptr "true";
                  }
                  ciena-common-yang:decrypt "offset-bits-test";
                  ciena-common-yang:decrypt-path "/ciena-common-test/encryption-test-container/encryption-list-test/leaf-test";
                  ciena-common-yang:sensitive "true";
                }
                leaf boolean-test {
                  ciena-common-yang:encrypt "boolean-test-encrypted";
                  ciena-common-yang:encrypt-path "/ciena-common-test/encryption-test-container/encryption-list-test/leaf-test";
                  ciena-common-yang:sensitive "true";
                  type boolean;
                }
                leaf boolean-test-encrypted {
                  type string {
                    ciena-common-yang:stringptr "true";
                  }
                  ciena-common-yang:decrypt "boolean-test";
                  ciena-common-yang:decrypt-path "/ciena-common-test/encryption-test-container/encryption-list-test/leaf-test";
                  ciena-common-yang:sensitive "true";
                }
                leaf decimal64-test {
                  ciena-common-yang:encrypt "decimal64-test-encrypted";
                  ciena-common-yang:encrypt-path "/ciena-common-test/encryption-test-container/encryption-list-test/leaf-test";
                  ciena-common-yang:sensitive "true";
                  type decimal64 {
                    fraction-digits 2;
                  }
                }
                leaf decimal64-test-encrypted {
                  type string {
                    ciena-common-yang:stringptr "true";
                  }
                  ciena-common-yang:decrypt "decimal64-test";
                  ciena-common-yang:decrypt-path "/ciena-common-test/encryption-test-container/encryption-list-test/leaf-test";
                  ciena-common-yang:sensitive "true";
                }
                leaf empty-test {
                  ciena-common-yang:encrypt "empty-test-encrypted";
                  ciena-common-yang:encrypt-path "/ciena-common-test/encryption-test-container/encryption-list-test/leaf-test";
                  ciena-common-yang:sensitive "true";
                  type empty;
                }
                leaf empty-test-encrypted {
                  type string {
                    ciena-common-yang:stringptr "true";
                  }
                  ciena-common-yang:decrypt "empty-test";
                  ciena-common-yang:decrypt-path "/ciena-common-test/encryption-test-container/encryption-list-test/leaf-test";
                  ciena-common-yang:sensitive "true";
                }
                leaf enumeration-test {
                  ciena-common-yang:encrypt "enumeration-test-encrypted";
                  ciena-common-yang:encrypt-path "/ciena-common-test/encryption-test-container/encryption-list-test/leaf-test";
                  ciena-common-yang:sensitive "true";
                  type enumeration {
                    enum test-1;
                    enum test-2;
                    enum test-3;
                  }
                }
                leaf enumeration-test-encrypted {
                  type string {
                    ciena-common-yang:stringptr "true";
                  }
                  ciena-common-yang:decrypt "enumeration-test";
                  ciena-common-yang:decrypt-path "/ciena-common-test/encryption-test-container/encryption-list-test/leaf-test";
                  ciena-common-yang:sensitive "true";
                }
                leaf enumeration-extended-test {
                  ciena-common-yang:encrypt "enumeration-extended-test-encrypted";
                  ciena-common-yang:encrypt-path "/ciena-common-test/encryption-test-container/encryption-list-test/leaf-test";
                  ciena-common-yang:sensitive "true";
                  type enumeration {
                    enum forty-one {
                      value 41;
                    }
                    enum ten {
                      value 10;
                    }
                    enum seven {
                      value 7;
                    }
                  }
                }
                leaf enumeration-extended-test-encrypted {
                  type string {
                    ciena-common-yang:stringptr "true";
                  }
                  ciena-common-yang:decrypt "enumeration-extended-test";
                  ciena-common-yang:decrypt-path "/ciena-common-test/encryption-test-container/encryption-list-test/leaf-test";
                  ciena-common-yang:sensitive "true";
                }
                leaf identityref-test {
                  ciena-common-yang:encrypt "identifyref-test-encrypted";
                  ciena-common-yang:encrypt-path "/ciena-common-test/encryption-test-container/encryption-list-test/leaf-test";
                  ciena-common-yang:sensitive "true";
                  type identityref {
                    base test:crypto-alg;
                  }
                }
                leaf identifyref-test-encrypted {
                  type string {
                    ciena-common-yang:stringptr "true";
                  }
                  ciena-common-yang:decrypt "identityref-test";
                  ciena-common-yang:decrypt-path "/ciena-common-test/encryption-test-container/encryption-list-test/leaf-test";
                  ciena-common-yang:sensitive "true";
                }
                leaf instance-identifier-test {
                  ciena-common-yang:encrypt "instance-identifier-test-encrypted";
                  ciena-common-yang:encrypt-path "/ciena-common-test/encryption-test-container/encryption-list-test/leaf-test";
                  ciena-common-yang:sensitive "true";
                  type instance-identifier;
                }
                leaf instance-identifier-test-encrypted {
                  type string {
                    ciena-common-yang:stringptr "true";
                  }
                  ciena-common-yang:decrypt "instance-identifier-test";
                  ciena-common-yang:decrypt-path "/ciena-common-test/encryption-test-container/encryption-list-test/leaf-test";
                  ciena-common-yang:sensitive "true";
                }
                leaf int64-test {
                  ciena-common-yang:encrypt "int64-test-encrypted";
                  ciena-common-yang:encrypt-path "/ciena-common-test/encryption-test-container/encryption-list-test/leaf-test";
                  ciena-common-yang:sensitive "true";
                  type int64;
                }
                leaf int64-test-encrypted {
                  type string {
                    ciena-common-yang:stringptr "true";
                  }
                  ciena-common-yang:decrypt "int64-test";
                  ciena-common-yang:decrypt-path "/ciena-common-test/encryption-test-container/encryption-list-test/leaf-test";
                  ciena-common-yang:sensitive "true";
                }
                leaf leafref-test {
                  ciena-common-yang:encrypt "leafref-test-encrypted";
                  ciena-common-yang:encrypt-path "/ciena-common-test/encryption-test-container/encryption-list-test/leaf-test";
                  ciena-common-yang:sensitive "true";
                  type leafref {
                    path "/test:red/test:blue/test:c";
                  }
                }
                leaf leafref-test-encrypted {
                  type string {
                    ciena-common-yang:stringptr "true";
                  }
                  ciena-common-yang:decrypt "leafref-test";
                  ciena-common-yang:decrypt-path "/ciena-common-test/encryption-test-container/encryption-list-test/leaf-test";
                  ciena-common-yang:sensitive "true";
                }
                leaf stringptr-test {
                  ciena-common-yang:encrypt "stringptr-test-encrypted";
                  ciena-common-yang:encrypt-path "/ciena-common-test/encryption-test-container/encryption-list-test/leaf-test";
                  ciena-common-yang:sensitive "true";
                  type string {
                    ciena-common-yang:stringptr "true";
                  }
                }
                leaf stringptr-test-encrypted {
                  type string {
                    ciena-common-yang:stringptr "true";
                  }
                  ciena-common-yang:decrypt "stringptr-test";
                  ciena-common-yang:decrypt-path "/ciena-common-test/encryption-test-container/encryption-list-test/leaf-test";
                  ciena-common-yang:sensitive "true";
                }
                leaf string-test {
                  ciena-common-yang:encrypt "string-test-encrypted";
                  ciena-common-yang:encrypt-path "/ciena-common-test/encryption-test-container/encryption-list-test/leaf-test";
                  ciena-common-yang:sensitive "true";
                  type string {
                    length "0..15";
                  }
                }
                leaf string-test-encrypted {
                  type string {
                    ciena-common-yang:stringptr "true";
                  }
                  ciena-common-yang:decrypt "string-test";
                  ciena-common-yang:decrypt-path "/ciena-common-test/encryption-test-container/encryption-list-test/leaf-test";
                  ciena-common-yang:sensitive "true";
                }
                leaf union-test {
                  ciena-common-yang:encrypt "union-test-encrypted";
                  ciena-common-yang:encrypt-path "/ciena-common-test/encryption-test-container/encryption-list-test/leaf-test";
                  type union {
                    type int32;
                    type enumeration {
                      enum unbounded;
                    }
                  }
                  ciena-common-yang:sensitive "true";
                }
                leaf union-test-encrypted {
                  type string {
                    ciena-common-yang:stringptr "true";
                  }
                  ciena-common-yang:decrypt "union-test";
                  ciena-common-yang:decrypt-path "/ciena-common-test/encryption-test-container/encryption-list-test/leaf-test";
                  ciena-common-yang:sensitive "true";
                }
              }
            }
          }
          action toggle-sleep {
            input {
              leaf sleep {
                type boolean;
              }
            }
          }
          uses grouping-test;
          action rpc-test-empty;
          action rpc-test-no-output {
            input {
              leaf input-test {
                type string;
              }
            }
          }
          action rpc-test-no-input {
            output {
              leaf input-test {
                type string;
              }
            }
          }
          action rpc-test {
            input {
              uses grouping-no-action-test;
            }
            output {
              uses grouping-no-action-test;
            }
          }
          action rpc-trigger-encryption-set {
            input {
              leaf path {
                type instance-identifier;
              }
            }
          }
          notification notification-test {
            uses red-blue-group;
          }
          notification encryption-notification-test {
            container X {
              leaf y {
                ciena-common-yang:encrypt "y-encrypted";
                ciena-common-yang:encrypt-path "/ciena-common-test/encryption-notification-test/X";
                type string;
              }
              leaf y-encrypted {
                type string {
                  ciena-common-yang:stringptr "true";
                }
                ciena-common-yang:decrypt "y";
                ciena-common-yang:decrypt-path "/ciena-common-test/encryption-notification-test/X";
              }
            }
          }
          action stack-push {
            description
              "Push into thread specific stack";
            input {
              leaf attr {
                type string;
                default "ddy_stack_test";
              }
              leaf recursive {
                type uint64;
                default "10";
              }
              leaf multistack {
                type uint64;
                default "0";
              }
            }
            output {
              leaf pass {
                type boolean;
              }
            }
          }
          action stack-pop {
            description
              "Pop from thread specific stack";
            input {
              leaf attr {
                type string;
                default "ddy_stack_test";
              }
              leaf recursive {
                type uint64;
                default "10";
              }
              leaf multistack {
                type uint64;
                default "0";
              }
            }
            output {
              leaf pass {
                type boolean;
              }
              leaf-list pop {
                type string;
              }
            }
          }
          action stack-get {
            description
              "Get pushed data for an attribute";
            input {
              leaf attr {
                type string;
                default "ddy_stack_test";
              }
              leaf recursive {
                type uint64;
                default "10";
              }
              leaf multistack {
                type uint64;
                default "0";
              }
            }
            output {
              leaf pass {
                type boolean;
              }
              leaf-list get {
                type string;
              }
            }
          }
          action stack-merge {
            description
              "Merge thread specific stacks";
            input {
              leaf attr {
                type string;
                default "ddy_stack_test";
              }
              leaf count {
                type uint64;
                default "0";
              }
              leaf all {
                type boolean;
              }
            }
            output {
              leaf pass {
                type boolean;
              }
            }
          }
          action return-code-set {
            description
              "Set the return code in the response";
            input {
              leaf return-code {
                type identityref {
                  base ciena-common-yang:error-code;
                }
              }
            }
            output {
              leaf pass {
                type boolean;
              }
            }
          }
          action validate-test {
            description
              "Set the return code in the response";
            input {
              uses abc_validate_group;
              container sub-group {
                uses abc_validate_group;
              }
            }
            output {
              uses ciena-common-yang:rpc-result-common;
            }
          }
          action test-deadline-timeout {
            description
              "Take input as timeout and handler will wait till this time
                based on test scenario type and return pass as true/false.";
            input {
              uses deadline-group;
            }
            output {
              leaf pass {
                type boolean;
              }
            }
          }
          container mount_test_a {
            list b {
              key "name";
              leaf name {
                type string;
              }
              anyxml c;
              container anyxml-mount {
                ciena-common-yang:mount-start "ciena-common-test";
                ciena-common-yang:mount-end "ciena-common-test";
              }
              anydata d;
              container anydata-mount {
                ciena-common-yang:mount-start "ciena-common-test";
                ciena-common-yang:mount-end "ciena-common-test";
              }
            }
          }
          container mount_test_b {
            list b {
              key "name";
              leaf name {
                type string;
              }
              anyxml c;
              container anyxml-mount {
                ciena-common-yang:mount-start "ciena-common-test-list";
                uses ciena-common-test-list:ciena-common-test-list-mount-data;
                uses ciena-common-test-list:ciena-common-test-list-mount-actions-notifs;
                ciena-common-yang:mount-end "ciena-common-test-list";
              }
            }
          }
          container i_love_big_data {
            list big_list {
              key "name";
              leaf name {
                type uint64;
              }
              leaf some_data {
                type decimal64 {
                  fraction-digits 10;
                }
              }
            }
          }
          container i_love_instance_id_for_keys {
            list some_list {
              key "instance_id_name";
              leaf instance_id_name {
                type instance-identifier;
              }
              leaf some_data {
                type decimal64 {
                  fraction-digits 10;
                }
              }
              container some_container {
                description
                  "Dummy container to have same context as parent";
                list sub_list {
                  description
                    "Another keyed list to have instance-id in parent context";
                  key "some_sub_key";
                  leaf some_sub_key {
                    type uint32;
                  }
                  leaf some_sub_leaf {
                    type uint32;
                  }
                }
              }
            }
          }
          container test-restconf-a {
            leaf b {
              type string;
            }
            leaf c {
              type uint8;
            }
            leaf awesome-wildcard-field {
              type string;
            }
            list d {
              key "name";
              leaf name {
                type string;
              }
              leaf test-state {
                type boolean;
              }
              container awesome-wildcard-field {
                leaf awesome-wildcard-field {
                  type boolean;
                }
                leaf awesome-wildcard-field-not {
                  type string;
                }
              }
              list e {
                key "index";
                leaf index {
                  type uint8;
                }
                leaf name {
                  type string;
                }
                list awesome-wildcard-field {
                  key "awesome-wildcard-field";
                  leaf awesome-wildcard-field {
                    type uint8;
                  }
                }
              }
            }
          }
          container test-colon-container {
            leaf enumeration-test {
              ciena-common-yang:sensitive "true";
              type enumeration {
                enum "1:n Mux type";
                enum "2:n Mux type";
                enum "3:n Mux type";
              }
            }
          }
          container multi-augment;
          container ddy-test-server-config {
            leaf handle-complete-transaction {
              type enumeration {
                enum none {
                  description
                    "complete-transaction not handled at all";
                }
                enum local {
                  description
                    "complete-transaction bound to local service";
                }
                enum service {
                  description
                    "complete-transaction bound to ddy-test-server";
                }
              }
              default "none";
            }
          }
          action client-activations {
            description
              "Sometimes you are testing something and you just need a simple way to execute a task.";
            input {
              leaf number {
                description
                  "This number can be used to call a specific function.";
                type uint64;
              }
            }
          }
          ciena-common-yang:mount-end "ciena-common-test";
        }
        anydata d;
        container anydata-mount {
          ciena-common-yang:mount-start "ciena-common-test";
          container string-based-return-code-list {
            config false;
            description
              "List of errors in case of command failure";
            list return-code-list {
              leaf instance {
                type string {
                  ciena-common-yang:stringptr "true";
                }
                description
                  "The instance to which the error code applies.";
              }
              leaf error {
                type string;
              }
            }
          }
          uses red-blue-group;
          uses blue-yellow-group;
          container white {
            uses abc_group;
            container cont1 {
              uses abc_group;
            }
            container cont2 {
              uses abc_group;
            }
            container cont3 {
              uses abc_group;
            }
            container cont4 {
              uses abc_group;
            }
            list list1 {
              key "k";
              leaf k {
                type uint8;
              }
              uses abc_group;
            }
          }
          container validation-test {
            uses abc_validate_group;
          }
          container to-pointer-test {
            container a {
              leaf string-test {
                type string;
              }
            }
          }
          list to-pointer-test2 {
            key "first-key";
            leaf first-key {
              type uint8;
            }
            list second-list {
              key "second-key";
              leaf second-key {
                type uint8;
              }
              leaf second-string {
                type string;
              }
              container second-container {
                leaf second-container-string {
                  type string;
                }
              }
            }
          }
          container nested-container {
            container cone {
              leaf a {
                type uint8;
                default "1";
              }
              leaf b {
                type uint8;
                default "2";
              }
              leaf c {
                type uint8;
                default "3";
              }
            }
            container ctwo {
              config false;
              leaf d {
                type uint8;
              }
              leaf e {
                type uint8;
              }
              leaf f {
                type uint8;
              }
            }
          }
          container read-only {
            config false;
            uses red-blue-group;
            container name {
              container collision {
                leaf test {
                  type uint8;
                }
                container child1 {
                  container child2 {
                    leaf test {
                      type uint8;
                    }
                  }
                }
              }
            }
            container name-collision {
              leaf test {
                type uint8;
              }
              container child1 {
                container child2 {
                  leaf test {
                    type uint8;
                  }
                }
              }
            }
          }
          container remove-via-deviation {
            uses red-blue-group;
          }
          uses ordered-lists-group;
          container simple-deadline-test {
            uses deadline-group;
          }
          container simple-test-container {
            ciena-common-yang:containerptr "true";
            list keys-only-list {
              key "name";
              leaf name {
                type string;
              }
            }
            leaf other-attribute {
              type string;
            }
            container leaf-test {
              leaf string-test {
                ciena-common-yang:encrypt "string-test-encrypted";
                ciena-common-yang:encrypt-path "/ciena-common-test/simple-test-container/leaf-test";
                type string;
              }
              leaf string-test-encrypted {
                type string {
                  ciena-common-yang:stringptr "true";
                }
                ciena-common-yang:decrypt "string-test";
                ciena-common-yang:decrypt-path "/ciena-common-test/simple-test-container/leaf-test";
              }
              leaf uint8-test {
                type uint8;
              }
            }
            container presence-test {
              presence "presense test container";
            }
            container presence-test-2 {
              choice start-time {
                mandatory true;
                container immediate {
                  presence "Start the measurement session immediately.";
                }
                leaf relative {
                  type string;
                }
                leaf absolute {
                  type string;
                }
              }
            }
            list outter {
              key "index";
              leaf index {
                type uint8;
              }
              min-elements 2;
              max-elements 3;
              list inner {
                key "name";
                leaf name {
                  type string;
                }
                max-elements 2;
                leaf value {
                  type uint16;
                }
              }
              leaf-list boolean-leaf-list {
                type boolean;
                max-elements 3;
                min-elements 2;
              }
              leaf mode {
                type uint8 {
                  range "0..10";
                }
              }
            }
            list first {
              key "key1 key2";
              leaf key1 {
                type uint8;
              }
              leaf key2 {
                type string;
              }
              list second {
                key "key1 key2";
                leaf key1 {
                  type uint8;
                }
                leaf key2 {
                  type string;
                }
                list third {
                  key "key1";
                  leaf key1 {
                    type uint8;
                  }
                  container red {
                    container blue {
                      leaf a {
                        type string;
                      }
                      leaf b {
                        type string;
                      }
                    }
                    leaf yellow-leaf {
                      type string;
                    }
                    anyxml config;
                  }
                }
              }
            }
          }
          container list-keys {
            list bits-key {
              key "bit";
              leaf bit {
                type bits {
                  bit x;
                  bit y;
                  bit z;
                }
              }
            }
          }
          container identity-test {
            leaf base-test {
              type identityref {
                base test:crypto-alg;
              }
            }
            leaf mid-level-test {
              type identityref {
                base test:des;
              }
            }
            leaf top-test {
              type identityref {
                base test:des3;
              }
            }
            leaf external-test {
              type identityref {
                base ciena-common-yang:error-does-not-exist;
              }
            }
          }
          container encryption-test-container {
            container container-generate-at-abs-path-enc {
              ciena-common-yang:decrypt "container-generate-at-abs-path";
              ciena-common-yang:decrypt-path "/ciena-common-test/encryption-test-container";
              leaf a {
                type string {
                  ciena-common-yang:stringptr "true";
                }
                ciena-common-yang:decrypt "a";
                ciena-common-yang:decrypt-path "/ciena-common-test/encryption-test-container/container-generate-at-abs-path";
              }
              container b {
                ciena-common-yang:decrypt "b";
                ciena-common-yang:decrypt-path "/ciena-common-test/encryption-test-container/container-generate-at-abs-path";
                leaf c {
                  type string {
                    ciena-common-yang:stringptr "true";
                  }
                  ciena-common-yang:decrypt "c";
                  ciena-common-yang:decrypt-path "/ciena-common-test/encryption-test-container/container-generate-at-abs-path/b";
                }
              }
              config false;
            }
            list encryption-mount-test {
              key "name";
              leaf name {
                type string;
              }
              container data {
                ciena-common-yang:mount-start "ciena-common-test";
                ciena-common-yang:mount-end "ciena-common-test";
              }
            }
            list instance {
              key "name";
              leaf name {
                type string;
              }
              container result {
                ciena-common-yang:encrypt "container-1";
                ciena-common-yang:encrypt-path "/ciena-common-test/encryption-test-container/instance";
                list amp {
                  ciena-common-yang:encrypt "amp";
                  ciena-common-yang:encrypt-path "/ciena-common-test/encryption-test-container/instance/container-1";
                  key "amp_name";
                  leaf amp_name {
                    ciena-common-yang:encrypt "amp_name";
                    ciena-common-yang:encrypt-path "/ciena-common-test/encryption-test-container/instance/container-1/amp";
                    type string;
                  }
                  list measurement-no-power {
                    ciena-common-yang:encrypt "measurement-no-power";
                    ciena-common-yang:encrypt-path "/ciena-common-test/encryption-test-container/instance/container-1/amp";
                    description
                      "Power measurements of span measured with all channels blocked.";
                    key "index";
                    leaf index {
                      ciena-common-yang:encrypt "index";
                      ciena-common-yang:encrypt-path "/ciena-common-test/encryption-test-container/instance/container-1/amp/measurement-no-power";
                      type uint8;
                    }
                    leaf in-current-power {
                      ciena-common-yang:encrypt "in-current-power";
                      ciena-common-yang:encrypt-path "/ciena-common-test/encryption-test-container/instance/container-1/amp/measurement-no-power";
                      type decimal64 {
                        fraction-digits 1;
                      }
                    }
                    leaf in-min-power {
                      ciena-common-yang:encrypt "in-min-power";
                      ciena-common-yang:encrypt-path "/ciena-common-test/encryption-test-container/instance/container-1/amp/measurement-no-power";
                      type decimal64 {
                        fraction-digits 1;
                      }
                    }
                    config false;
                  }
                }
              }
              container container-1 {
                ciena-common-yang:decrypt "result";
                ciena-common-yang:decrypt-path "/ciena-common-test/encryption-test-container/instance";
                list amp {
                  ciena-common-yang:decrypt "amp";
                  ciena-common-yang:decrypt-path "/ciena-common-test/encryption-test-container/instance/result";
                  key "amp_name";
                  leaf amp_name {
                    type string {
                      ciena-common-yang:stringptr "true";
                    }
                    ciena-common-yang:decrypt "amp_name";
                    ciena-common-yang:decrypt-path "/ciena-common-test/encryption-test-container/instance/result/amp";
                  }
                  list measurement-no-power {
                    ciena-common-yang:decrypt "measurement-no-power";
                    ciena-common-yang:decrypt-path "/ciena-common-test/encryption-test-container/instance/result/amp";
                    key "index";
                    leaf index {
                      type string {
                        ciena-common-yang:stringptr "true";
                      }
                      ciena-common-yang:decrypt "index";
                      ciena-common-yang:decrypt-path "/ciena-common-test/encryption-test-container/instance/result/amp/measurement-no-power";
                    }
                    leaf in-current-power {
                      type string {
                        ciena-common-yang:stringptr "true";
                      }
                      ciena-common-yang:decrypt "in-current-power";
                      ciena-common-yang:decrypt-path "/ciena-common-test/encryption-test-container/instance/result/amp/measurement-no-power";
                    }
                    leaf in-min-power {
                      type string {
                        ciena-common-yang:stringptr "true";
                      }
                      ciena-common-yang:decrypt "in-min-power";
                      ciena-common-yang:decrypt-path "/ciena-common-test/encryption-test-container/instance/result/amp/measurement-no-power";
                    }
                    config false;
                  }
                }
              }
              list some-other-list {
                key "name";
                leaf name {
                  type string;
                }
                leaf measurement {
                  type uint8;
                }
              }
            }
            list key-in-grouping {
              ciena-common-yang:encrypt "key-in-grouping-encrypted";
              ciena-common-yang:encrypt-path "/ciena-common-test/encryption-test-container";
              description
                "test list key leaf definition can be provided by grouping";
              key "name";
              leaf name {
                ciena-common-yang:encrypt "name";
                ciena-common-yang:encrypt-path "/ciena-common-test/encryption-test-container/key-in-grouping-encrypted";
                type string;
              }
              leaf stats {
                ciena-common-yang:encrypt "stats";
                ciena-common-yang:encrypt-path "/ciena-common-test/encryption-test-container/key-in-grouping-encrypted";
                type uint32;
              }
            }
            list key-in-grouping-encrypted {
              ciena-common-yang:decrypt "key-in-grouping";
              ciena-common-yang:decrypt-path "/ciena-common-test/encryption-test-container";
              key "name";
              leaf name {
                type string {
                  ciena-common-yang:stringptr "true";
                }
                ciena-common-yang:decrypt "name";
                ciena-common-yang:decrypt-path "/ciena-common-test/encryption-test-container/key-in-grouping";
              }
              leaf stats {
                type string {
                  ciena-common-yang:stringptr "true";
                }
                ciena-common-yang:decrypt "stats";
                ciena-common-yang:decrypt-path "/ciena-common-test/encryption-test-container/key-in-grouping";
              }
            }
            list list-enc-generate-with-renamed-leaves {
              ciena-common-yang:encrypt "list-enc-generate-with-renamed-leaves-enc";
              ciena-common-yang:encrypt-path "/ciena-common-test/encryption-test-container";
              description
                "test list encryption with nested containers and leaves renamed";
              key "name";
              leaf name {
                ciena-common-yang:encrypt "name";
                ciena-common-yang:encrypt-path "/ciena-common-test/encryption-test-container/list-enc-generate-with-renamed-leaves-enc";
                type string;
              }
              leaf aaa {
                ciena-common-yang:encrypt "aaa-enc";
                ciena-common-yang:encrypt-path "/ciena-common-test/encryption-test-container/list-enc-generate-with-renamed-leaves-enc";
                type uint8;
                ciena-common-yang:sensitive "true";
              }
              container ddd {
                ciena-common-yang:encrypt "ddd-enc";
                ciena-common-yang:encrypt-path "/ciena-common-test/encryption-test-container/list-enc-generate-with-renamed-leaves-enc";
                leaf eee {
                  ciena-common-yang:encrypt "eee-enc";
                  ciena-common-yang:encrypt-path "/ciena-common-test/encryption-test-container/list-enc-generate-with-renamed-leaves-enc/ddd-enc";
                  type uint8;
                }
                leaf fff {
                  ciena-common-yang:encrypt "fff";
                  ciena-common-yang:encrypt-path "/ciena-common-test/encryption-test-container/list-enc-generate-with-renamed-leaves-enc/ddd-enc";
                  type uint8;
                }
                config false;
              }
            }
            list list-enc-generate-with-renamed-leaves-enc {
              ciena-common-yang:decrypt "list-enc-generate-with-renamed-leaves";
              ciena-common-yang:decrypt-path "/ciena-common-test/encryption-test-container";
              key "name";
              leaf name {
                type string {
                  ciena-common-yang:stringptr "true";
                }
                ciena-common-yang:decrypt "name";
                ciena-common-yang:decrypt-path "/ciena-common-test/encryption-test-container/list-enc-generate-with-renamed-leaves";
              }
              leaf aaa-enc {
                type string {
                  ciena-common-yang:stringptr "true";
                }
                ciena-common-yang:decrypt "aaa";
                ciena-common-yang:decrypt-path "/ciena-common-test/encryption-test-container/list-enc-generate-with-renamed-leaves";
                ciena-common-yang:sensitive "true";
              }
              container ddd-enc {
                ciena-common-yang:decrypt "ddd";
                ciena-common-yang:decrypt-path "/ciena-common-test/encryption-test-container/list-enc-generate-with-renamed-leaves";
                leaf eee-enc {
                  type string {
                    ciena-common-yang:stringptr "true";
                  }
                  ciena-common-yang:decrypt "eee";
                  ciena-common-yang:decrypt-path "/ciena-common-test/encryption-test-container/list-enc-generate-with-renamed-leaves/ddd";
                }
                leaf fff {
                  type string {
                    ciena-common-yang:stringptr "true";
                  }
                  ciena-common-yang:decrypt "fff";
                  ciena-common-yang:decrypt-path "/ciena-common-test/encryption-test-container/list-enc-generate-with-renamed-leaves/ddd";
                }
                config false;
              }
            }
            list list-generate-with-enc-path-for-leaves {
              ciena-common-yang:encrypt "list-generate-with-enc-path-for-leaves-enc";
              ciena-common-yang:encrypt-path "/ciena-common-test/encryption-test-container";
              description
                "test list encryption with some leaves having encryption-path and encryption-relative-path information";
              key "index";
              leaf index {
                ciena-common-yang:encrypt "index-enc";
                ciena-common-yang:encrypt-path "/ciena-common-test/encryption-test-container/list-generate-with-enc-path-for-leaves-enc";
                type uint8;
              }
              leaf ggg {
                ciena-common-yang:encrypt "ggg";
                ciena-common-yang:encrypt-path "/ciena-common-test/encryption-test-container/list-generate-with-enc-path-for-leaves-enc";
                type uint8;
              }
              container hhh {
                ciena-common-yang:encrypt "hhh";
                ciena-common-yang:encrypt-path "/ciena-common-test/encryption-test-container/list-generate-with-enc-path-for-leaves-enc";
                leaf iii {
                  ciena-common-yang:encrypt "iii-enc";
                  ciena-common-yang:encrypt-path "/ciena-common-test/encryption-test-container/list-generate-with-enc-path-for-leaves-enc/hhh";
                  type uint8;
                }
                leaf jjj {
                  ciena-common-yang:encrypt "none-existing-leaf";
                  ciena-common-yang:encrypt-path "/ciena-common-test/encryption-test-container/A/B";
                  type uint8;
                  ciena-common-yang:sensitive "true";
                }
                leaf kkk {
                  ciena-common-yang:encrypt "none-existing-leaf-2";
                  ciena-common-yang:encrypt-path "/ciena-common-test/encryption-test-container/A/B";
                  type uint8;
                  config false;
                  ciena-common-yang:sensitive "true";
                }
              }
            }
            list list-generate-with-enc-path-for-leaves-enc {
              ciena-common-yang:decrypt "list-generate-with-enc-path-for-leaves";
              ciena-common-yang:decrypt-path "/ciena-common-test/encryption-test-container";
              key "index-enc";
              leaf index-enc {
                type string {
                  ciena-common-yang:stringptr "true";
                }
                ciena-common-yang:decrypt "index";
                ciena-common-yang:decrypt-path "/ciena-common-test/encryption-test-container/list-generate-with-enc-path-for-leaves";
              }
              leaf ggg {
                type string {
                  ciena-common-yang:stringptr "true";
                }
                ciena-common-yang:decrypt "ggg";
                ciena-common-yang:decrypt-path "/ciena-common-test/encryption-test-container/list-generate-with-enc-path-for-leaves";
              }
              container hhh {
                ciena-common-yang:decrypt "hhh";
                ciena-common-yang:decrypt-path "/ciena-common-test/encryption-test-container/list-generate-with-enc-path-for-leaves";
                leaf iii-enc {
                  type string {
                    ciena-common-yang:stringptr "true";
                  }
                  ciena-common-yang:decrypt "iii";
                  ciena-common-yang:decrypt-path "/ciena-common-test/encryption-test-container/list-generate-with-enc-path-for-leaves/hhh";
                }
              }
            }
            container A {
              container B {
                leaf none-existing-leaf {
                  ciena-common-yang:decrypt "jjj";
                  ciena-common-yang:decrypt-path "/ciena-common-test/encryption-test-container/list-generate-with-enc-path-for-leaves/hhh";
                  type string {
                    ciena-common-yang:stringptr "true";
                  }
                  ciena-common-yang:sensitive "true";
                }
                leaf none-existing-leaf-2 {
                  ciena-common-yang:decrypt "kkk";
                  ciena-common-yang:decrypt-path "/ciena-common-test/encryption-test-container/list-generate-with-enc-path-for-leaves/hhh";
                  type string {
                    ciena-common-yang:stringptr "true";
                  }
                  ciena-common-yang:sensitive "true";
                  config false;
                }
                leaf y {
                  type string {
                    ciena-common-yang:stringptr "true";
                  }
                }
                leaf z {
                  type uint8;
                }
              }
            }
            container container-generate-as-sibling {
              ciena-common-yang:encrypt "container-generate-as-sibling-enc";
              ciena-common-yang:encrypt-path "/ciena-common-test/encryption-test-container";
              description
                "test simple container encryption default generating as siblings";
              leaf a {
                ciena-common-yang:encrypt "a";
                ciena-common-yang:encrypt-path "/ciena-common-test/encryption-test-container/container-generate-as-sibling-enc";
                type uint8;
              }
              container b {
                ciena-common-yang:encrypt "b";
                ciena-common-yang:encrypt-path "/ciena-common-test/encryption-test-container/container-generate-as-sibling-enc";
                leaf c {
                  ciena-common-yang:encrypt "c";
                  ciena-common-yang:encrypt-path "/ciena-common-test/encryption-test-container/container-generate-as-sibling-enc/b";
                  type uint8;
                }
              }
            }
            container container-generate-as-sibling-enc {
              ciena-common-yang:decrypt "container-generate-as-sibling";
              ciena-common-yang:decrypt-path "/ciena-common-test/encryption-test-container";
              leaf a {
                type string {
                  ciena-common-yang:stringptr "true";
                }
                ciena-common-yang:decrypt "a";
                ciena-common-yang:decrypt-path "/ciena-common-test/encryption-test-container/container-generate-as-sibling";
              }
              container b {
                ciena-common-yang:decrypt "b";
                ciena-common-yang:decrypt-path "/ciena-common-test/encryption-test-container/container-generate-as-sibling";
                leaf c {
                  type string {
                    ciena-common-yang:stringptr "true";
                  }
                  ciena-common-yang:decrypt "c";
                  ciena-common-yang:decrypt-path "/ciena-common-test/encryption-test-container/container-generate-as-sibling/b";
                }
              }
            }
            container X {
              container Z {
                container container-generate-at-relative-path {
                  ciena-common-yang:encrypt "container-generate-at-relative-path-enc";
                  ciena-common-yang:encrypt-path "/ciena-common-test/encryption-test-container/K";
                  description
                    "test container encryption with encrypt-relative-path information";
                  container red {
                    ciena-common-yang:encrypt "red";
                    ciena-common-yang:encrypt-path "/ciena-common-test/encryption-test-container/K/container-generate-at-relative-path-enc";
                    container blue {
                      ciena-common-yang:encrypt "blue";
                      ciena-common-yang:encrypt-path "/ciena-common-test/encryption-test-container/K/container-generate-at-relative-path-enc/red";
                      leaf a {
                        ciena-common-yang:encrypt "a";
                        ciena-common-yang:encrypt-path "/ciena-common-test/encryption-test-container/K/container-generate-at-relative-path-enc/red/blue";
                        type uint8;
                      }
                      leaf b {
                        ciena-common-yang:encrypt "b";
                        ciena-common-yang:encrypt-path "/ciena-common-test/encryption-test-container/K/container-generate-at-relative-path-enc/red/blue";
                        type uint8;
                        default "22";
                      }
                      leaf c {
                        ciena-common-yang:encrypt "c";
                        ciena-common-yang:encrypt-path "/ciena-common-test/encryption-test-container/K/container-generate-at-relative-path-enc/red/blue";
                        type uint8;
                        default "44";
                      }
                      leaf d {
                        ciena-common-yang:encrypt "d";
                        ciena-common-yang:encrypt-path "/ciena-common-test/encryption-test-container/K/container-generate-at-relative-path-enc/red/blue";
                        type uint8;
                        default "88";
                      }
                    }
                  }
                  leaf a {
                    ciena-common-yang:encrypt "a";
                    ciena-common-yang:encrypt-path "/ciena-common-test/encryption-test-container/K/container-generate-at-relative-path-enc";
                    type uint8;
                  }
                  container b {
                    ciena-common-yang:encrypt "b";
                    ciena-common-yang:encrypt-path "/ciena-common-test/encryption-test-container/K/container-generate-at-relative-path-enc";
                    container red {
                      ciena-common-yang:encrypt "red";
                      ciena-common-yang:encrypt-path "/ciena-common-test/encryption-test-container/K/container-generate-at-relative-path-enc/b";
                      container blue {
                        ciena-common-yang:encrypt "blue";
                        ciena-common-yang:encrypt-path "/ciena-common-test/encryption-test-container/K/container-generate-at-relative-path-enc/b/red";
                        leaf a {
                          ciena-common-yang:encrypt "a";
                          ciena-common-yang:encrypt-path "/ciena-common-test/encryption-test-container/K/container-generate-at-relative-path-enc/b/red/blue";
                          type uint8;
                        }
                        leaf b {
                          ciena-common-yang:encrypt "b";
                          ciena-common-yang:encrypt-path "/ciena-common-test/encryption-test-container/K/container-generate-at-relative-path-enc/b/red/blue";
                          type uint8;
                          default "22";
                        }
                        leaf c {
                          ciena-common-yang:encrypt "c";
                          ciena-common-yang:encrypt-path "/ciena-common-test/encryption-test-container/K/container-generate-at-relative-path-enc/b/red/blue";
                          type uint8;
                          default "44";
                        }
                        leaf d {
                          ciena-common-yang:encrypt "d";
                          ciena-common-yang:encrypt-path "/ciena-common-test/encryption-test-container/K/container-generate-at-relative-path-enc/b/red/blue";
                          type uint8;
                          default "88";
                        }
                      }
                    }
                    leaf c {
                      ciena-common-yang:encrypt "c";
                      ciena-common-yang:encrypt-path "/ciena-common-test/encryption-test-container/K/container-generate-at-relative-path-enc/b";
                      type uint8;
                    }
                  }
                  config false;
                }
              }
            }
            container K {
              container container-generate-at-relative-path-enc {
                ciena-common-yang:decrypt "container-generate-at-relative-path";
                ciena-common-yang:decrypt-path "/ciena-common-test/encryption-test-container/X/Z";
                container red {
                  ciena-common-yang:decrypt "red";
                  ciena-common-yang:decrypt-path "/ciena-common-test/encryption-test-container/X/Z/container-generate-at-relative-path";
                  container blue {
                    ciena-common-yang:decrypt "blue";
                    ciena-common-yang:decrypt-path "/ciena-common-test/encryption-test-container/X/Z/container-generate-at-relative-path/red";
                    leaf a {
                      type string {
                        ciena-common-yang:stringptr "true";
                      }
                      ciena-common-yang:decrypt "a";
                      ciena-common-yang:decrypt-path "/ciena-common-test/encryption-test-container/X/Z/container-generate-at-relative-path/red/blue";
                    }
                    leaf b {
                      type string {
                        ciena-common-yang:stringptr "true";
                      }
                      ciena-common-yang:decrypt "b";
                      ciena-common-yang:decrypt-path "/ciena-common-test/encryption-test-container/X/Z/container-generate-at-relative-path/red/blue";
                    }
                    leaf c {
                      type string {
                        ciena-common-yang:stringptr "true";
                      }
                      ciena-common-yang:decrypt "c";
                      ciena-common-yang:decrypt-path "/ciena-common-test/encryption-test-container/X/Z/container-generate-at-relative-path/red/blue";
                    }
                    leaf d {
                      type string {
                        ciena-common-yang:stringptr "true";
                      }
                      ciena-common-yang:decrypt "d";
                      ciena-common-yang:decrypt-path "/ciena-common-test/encryption-test-container/X/Z/container-generate-at-relative-path/red/blue";
                    }
                  }
                }
                leaf a {
                  type string {
                    ciena-common-yang:stringptr "true";
                  }
                  ciena-common-yang:decrypt "a";
                  ciena-common-yang:decrypt-path "/ciena-common-test/encryption-test-container/X/Z/container-generate-at-relative-path";
                }
                container b {
                  ciena-common-yang:decrypt "b";
                  ciena-common-yang:decrypt-path "/ciena-common-test/encryption-test-container/X/Z/container-generate-at-relative-path";
                  container red {
                    ciena-common-yang:decrypt "red";
                    ciena-common-yang:decrypt-path "/ciena-common-test/encryption-test-container/X/Z/container-generate-at-relative-path/b";
                    container blue {
                      ciena-common-yang:decrypt "blue";
                      ciena-common-yang:decrypt-path "/ciena-common-test/encryption-test-container/X/Z/container-generate-at-relative-path/b/red";
                      leaf a {
                        type string {
                          ciena-common-yang:stringptr "true";
                        }
                        ciena-common-yang:decrypt "a";
                        ciena-common-yang:decrypt-path "/ciena-common-test/encryption-test-container/X/Z/container-generate-at-relative-path/b/red/blue";
                      }
                      leaf b {
                        type string {
                          ciena-common-yang:stringptr "true";
                        }
                        ciena-common-yang:decrypt "b";
                        ciena-common-yang:decrypt-path "/ciena-common-test/encryption-test-container/X/Z/container-generate-at-relative-path/b/red/blue";
                      }
                      leaf c {
                        type string {
                          ciena-common-yang:stringptr "true";
                        }
                        ciena-common-yang:decrypt "c";
                        ciena-common-yang:decrypt-path "/ciena-common-test/encryption-test-container/X/Z/container-generate-at-relative-path/b/red/blue";
                      }
                      leaf d {
                        type string {
                          ciena-common-yang:stringptr "true";
                        }
                        ciena-common-yang:decrypt "d";
                        ciena-common-yang:decrypt-path "/ciena-common-test/encryption-test-container/X/Z/container-generate-at-relative-path/b/red/blue";
                      }
                    }
                  }
                  leaf c {
                    type string {
                      ciena-common-yang:stringptr "true";
                    }
                    ciena-common-yang:decrypt "c";
                    ciena-common-yang:decrypt-path "/ciena-common-test/encryption-test-container/X/Z/container-generate-at-relative-path/b";
                  }
                }
                config false;
              }
              leaf l {
                type uint8;
              }
            }
            container container-generate-at-abs-path {
              ciena-common-yang:encrypt "container-generate-at-abs-path-enc";
              ciena-common-yang:encrypt-path "/ciena-common-test/encryption-test-container";
              description
                "test container encryption with absolute path encrypt-path information";
              leaf a {
                ciena-common-yang:encrypt "a";
                ciena-common-yang:encrypt-path "/ciena-common-test/encryption-test-container/container-generate-at-abs-path-enc";
                type uint8;
              }
              container b {
                ciena-common-yang:encrypt "b";
                ciena-common-yang:encrypt-path "/ciena-common-test/encryption-test-container/container-generate-at-abs-path-enc";
                leaf c {
                  ciena-common-yang:encrypt "c";
                  ciena-common-yang:encrypt-path "/ciena-common-test/encryption-test-container/container-generate-at-abs-path-enc/b";
                  type uint8;
                }
              }
              config false;
            }
            container encrypt-to-existing-container {
              ciena-common-yang:encrypt "encrypt-to-existing-container-encrypted";
              ciena-common-yang:encrypt-path "/ciena-common-test/encryption-test-container";
              description
                "test container encryption to existing container. no generation will happen.";
              leaf a {
                ciena-common-yang:encrypt "a";
                ciena-common-yang:encrypt-path "/ciena-common-test/encryption-test-container/encrypt-to-existing-container-encrypted";
                type uint8;
              }
            }
            container encrypt-to-existing-container-encrypted {
              ciena-common-yang:decrypt "encrypt-to-existing-container";
              ciena-common-yang:decrypt-path "/ciena-common-test/encryption-test-container";
              leaf a {
                ciena-common-yang:decrypt "a";
                ciena-common-yang:decrypt-path "/ciena-common-test/encryption-test-container/encrypt-to-existing-container";
                type string {
                  ciena-common-yang:stringptr "true";
                }
              }
            }
            container outter-container {
              ciena-common-yang:encrypt "outter-container-enc";
              ciena-common-yang:encrypt-path "/ciena-common-test/encryption-test-container";
              description
                "simple nested container test";
              leaf aaa {
                ciena-common-yang:encrypt "aaa";
                ciena-common-yang:encrypt-path "/ciena-common-test/encryption-test-container/outter-container-enc";
                type uint8;
              }
              container middle-container {
                ciena-common-yang:encrypt "middle-container";
                ciena-common-yang:encrypt-path "/ciena-common-test/encryption-test-container/outter-container-enc";
                leaf bbb {
                  ciena-common-yang:encrypt "bbb";
                  ciena-common-yang:encrypt-path "/ciena-common-test/encryption-test-container/outter-container-enc/middle-container";
                  type uint8;
                }
                container inner-container {
                  ciena-common-yang:encrypt "inner-container";
                  ciena-common-yang:encrypt-path "/ciena-common-test/encryption-test-container/outter-container-enc/middle-container";
                  leaf ccc {
                    ciena-common-yang:encrypt "ccc";
                    ciena-common-yang:encrypt-path "/ciena-common-test/encryption-test-container/outter-container-enc/middle-container/inner-container";
                    type uint8;
                  }
                }
              }
            }
            container outter-container-enc {
              ciena-common-yang:decrypt "outter-container";
              ciena-common-yang:decrypt-path "/ciena-common-test/encryption-test-container";
              leaf aaa {
                type string {
                  ciena-common-yang:stringptr "true";
                }
                ciena-common-yang:decrypt "aaa";
                ciena-common-yang:decrypt-path "/ciena-common-test/encryption-test-container/outter-container";
              }
              container middle-container {
                ciena-common-yang:decrypt "middle-container";
                ciena-common-yang:decrypt-path "/ciena-common-test/encryption-test-container/outter-container";
                leaf bbb {
                  type string {
                    ciena-common-yang:stringptr "true";
                  }
                  ciena-common-yang:decrypt "bbb";
                  ciena-common-yang:decrypt-path "/ciena-common-test/encryption-test-container/outter-container/middle-container";
                }
                container inner-container {
                  ciena-common-yang:decrypt "inner-container";
                  ciena-common-yang:decrypt-path "/ciena-common-test/encryption-test-container/outter-container/middle-container";
                  leaf ccc {
                    type string {
                      ciena-common-yang:stringptr "true";
                    }
                    ciena-common-yang:decrypt "ccc";
                    ciena-common-yang:decrypt-path "/ciena-common-test/encryption-test-container/outter-container/middle-container/inner-container";
                  }
                }
              }
            }
            container one-to-two-container {
              ciena-common-yang:encrypt "one-to-two-container-enc";
              ciena-common-yang:encrypt-path "/ciena-common-test/encryption-test-container";
              description
                "error scenario test: leaves under one container encrypted to two containers
                 is not fully supported, the leaves for one container will be missing";
              leaf aaa {
                ciena-common-yang:encrypt "aaa";
                ciena-common-yang:encrypt-path "/ciena-common-test/encryption-test-container/one-to-two-container-enc";
                type uint8;
              }
              leaf-list bbb {
                ciena-common-yang:encrypt "bbb";
                ciena-common-yang:encrypt-path "/ciena-common-test/encryption-test-container/one-to-two-container-other";
                type uint8;
              }
              container inner-container {
                ciena-common-yang:encrypt "inner-container";
                ciena-common-yang:encrypt-path "/ciena-common-test/encryption-test-container/one-to-two-container-enc";
                leaf-list ccc {
                  ciena-common-yang:encrypt "ccc";
                  ciena-common-yang:encrypt-path "/ciena-common-test/encryption-test-container/one-to-two-container-enc/inner-container";
                  type uint8;
                }
                leaf ddd {
                  ciena-common-yang:encrypt "ddd";
                  ciena-common-yang:encrypt-path "/ciena-common-test/encryption-test-container/one-to-two-container-other";
                  type uint8;
                }
              }
            }
            container one-to-two-container-enc {
              ciena-common-yang:decrypt "one-to-two-container";
              ciena-common-yang:decrypt-path "/ciena-common-test/encryption-test-container";
              leaf aaa {
                type string {
                  ciena-common-yang:stringptr "true";
                }
                ciena-common-yang:decrypt "aaa";
                ciena-common-yang:decrypt-path "/ciena-common-test/encryption-test-container/one-to-two-container";
              }
              container inner-container {
                ciena-common-yang:decrypt "inner-container";
                ciena-common-yang:decrypt-path "/ciena-common-test/encryption-test-container/one-to-two-container";
                leaf-list ccc {
                  type string {
                    ciena-common-yang:stringptr "true";
                  }
                  ciena-common-yang:decrypt "ccc";
                  ciena-common-yang:decrypt-path "/ciena-common-test/encryption-test-container/one-to-two-container/inner-container";
                }
              }
            }
            container one-to-two-container-other {
              leaf-list bbb {
                ciena-common-yang:decrypt "bbb";
                ciena-common-yang:decrypt-path "/ciena-common-test/encryption-test-container/one-to-two-container";
                type string {
                  ciena-common-yang:stringptr "true";
                }
              }
              leaf ddd {
                ciena-common-yang:decrypt "ddd";
                ciena-common-yang:decrypt-path "/ciena-common-test/encryption-test-container/one-to-two-container/inner-container";
                type string {
                  ciena-common-yang:stringptr "true";
                }
              }
              leaf fff {
                type uint8;
              }
            }
            list nested-list {
              ciena-common-yang:encrypt "nested-list-enc";
              ciena-common-yang:encrypt-path "/ciena-common-test/encryption-test-container";
              description
                "test nested list encryption";
              key "name";
              leaf name {
                ciena-common-yang:encrypt "name";
                ciena-common-yang:encrypt-path "/ciena-common-test/encryption-test-container/nested-list-enc";
                type stringptr;
              }
              leaf aaa {
                ciena-common-yang:encrypt "aaa";
                ciena-common-yang:encrypt-path "/ciena-common-test/encryption-test-container/nested-list-enc";
                type uint8;
              }
              list inner-list {
                ciena-common-yang:encrypt "inner-list";
                ciena-common-yang:encrypt-path "/ciena-common-test/encryption-test-container/nested-list-enc";
                key "index";
                leaf index {
                  ciena-common-yang:encrypt "index";
                  ciena-common-yang:encrypt-path "/ciena-common-test/encryption-test-container/nested-list-enc/inner-list";
                  type uint8;
                }
                leaf-list ccc {
                  ciena-common-yang:encrypt "ccc";
                  ciena-common-yang:encrypt-path "/ciena-common-test/encryption-test-container/nested-list-enc/inner-list";
                  type string;
                }
              }
            }
            list nested-list-enc {
              ciena-common-yang:decrypt "nested-list";
              ciena-common-yang:decrypt-path "/ciena-common-test/encryption-test-container";
              key "name";
              leaf name {
                type string {
                  ciena-common-yang:stringptr "true";
                }
                ciena-common-yang:decrypt "name";
                ciena-common-yang:decrypt-path "/ciena-common-test/encryption-test-container/nested-list";
              }
              leaf aaa {
                type string {
                  ciena-common-yang:stringptr "true";
                }
                ciena-common-yang:decrypt "aaa";
                ciena-common-yang:decrypt-path "/ciena-common-test/encryption-test-container/nested-list";
              }
              list inner-list {
                ciena-common-yang:decrypt "inner-list";
                ciena-common-yang:decrypt-path "/ciena-common-test/encryption-test-container/nested-list";
                key "index";
                leaf index {
                  type string {
                    ciena-common-yang:stringptr "true";
                  }
                  ciena-common-yang:decrypt "index";
                  ciena-common-yang:decrypt-path "/ciena-common-test/encryption-test-container/nested-list/inner-list";
                }
                leaf-list ccc {
                  type string {
                    ciena-common-yang:stringptr "true";
                  }
                  ciena-common-yang:decrypt "ccc";
                  ciena-common-yang:decrypt-path "/ciena-common-test/encryption-test-container/nested-list/inner-list";
                }
              }
            }
            container other {
              leaf ccc {
                type string;
              }
            }
            container user-defined-leaves {
              description
                "selected leaves encryption container";
              leaf a {
                ciena-common-yang:encrypt "x";
                ciena-common-yang:encrypt-path "/ciena-common-test/encryption-test-container/user-defined-leaves-encrypted";
                type string;
              }
              leaf b {
                type string;
              }
            }
            container user-defined-leaves-encrypted {
              leaf x {
                ciena-common-yang:decrypt "a";
                ciena-common-yang:decrypt-path "/ciena-common-test/encryption-test-container/user-defined-leaves";
                type string;
              }
            }
            list nested-list-leaf-encryption {
              key "name";
              leaf name {
                type string;
              }
              leaf x {
                ciena-common-yang:encrypt "x-enc";
                ciena-common-yang:encrypt-path "/ciena-common-test/encryption-test-container/nested-list-leaf-encryption";
                type string;
              }
              leaf x-enc {
                type string {
                  ciena-common-yang:stringptr "true";
                }
                ciena-common-yang:decrypt "x";
                ciena-common-yang:decrypt-path "/ciena-common-test/encryption-test-container/nested-list-leaf-encryption";
              }
              list inner {
                key "index";
                leaf index {
                  type uint8;
                }
                leaf u {
                  ciena-common-yang:encrypt "u-enc";
                  ciena-common-yang:encrypt-path "/ciena-common-test/encryption-test-container/nested-list-leaf-encryption/inner";
                  type string;
                }
                leaf u-enc {
                  type string {
                    ciena-common-yang:stringptr "true";
                  }
                  ciena-common-yang:decrypt "u";
                  ciena-common-yang:decrypt-path "/ciena-common-test/encryption-test-container/nested-list-leaf-encryption/inner";
                }
              }
            }
            list encryption-list-test {
              key "key1 key2";
              leaf key1 {
                type stringptr;
              }
              leaf key2 {
                type typetest;
              }
              container leaf-list-test {
                leaf-list binary-test {
                  ciena-common-yang:encrypt "binary-test-encrypted";
                  ciena-common-yang:encrypt-path "/ciena-common-test/encryption-test-container/encryption-list-test/leaf-list-test";
                  type binary;
                }
                leaf-list binary-test-encrypted {
                  type string {
                    ciena-common-yang:stringptr "true";
                  }
                  ciena-common-yang:decrypt "binary-test";
                  ciena-common-yang:decrypt-path "/ciena-common-test/encryption-test-container/encryption-list-test/leaf-list-test";
                }
                leaf-list bits-test {
                  ciena-common-yang:encrypt "bits-test-encrypted";
                  ciena-common-yang:encrypt-path "/ciena-common-test/encryption-test-container/encryption-list-test/leaf-list-test";
                  type bits {
                    bit disable-nagle {
                      position 0;
                    }
                    bit auto-sense-speed {
                      position 1;
                    }
                  }
                }
                leaf-list bits-test-encrypted {
                  type string {
                    ciena-common-yang:stringptr "true";
                  }
                  ciena-common-yang:decrypt "bits-test";
                  ciena-common-yang:decrypt-path "/ciena-common-test/encryption-test-container/encryption-list-test/leaf-list-test";
                }
                leaf-list boolean-test {
                  ciena-common-yang:encrypt "boolean-test-encrypted";
                  ciena-common-yang:encrypt-path "/ciena-common-test/encryption-test-container/encryption-list-test/leaf-list-test";
                  type boolean;
                }
                leaf-list boolean-test-encrypted {
                  type string {
                    ciena-common-yang:stringptr "true";
                  }
                  ciena-common-yang:decrypt "boolean-test";
                  ciena-common-yang:decrypt-path "/ciena-common-test/encryption-test-container/encryption-list-test/leaf-list-test";
                }
                leaf-list decimal64-test {
                  ciena-common-yang:encrypt "decimal64-test-encrypted";
                  ciena-common-yang:encrypt-path "/ciena-common-test/encryption-test-container/encryption-list-test/leaf-list-test";
                  type decimal64 {
                    fraction-digits 10;
                  }
                }
                leaf-list decimal64-test-encrypted {
                  type string {
                    ciena-common-yang:stringptr "true";
                  }
                  ciena-common-yang:decrypt "decimal64-test";
                  ciena-common-yang:decrypt-path "/ciena-common-test/encryption-test-container/encryption-list-test/leaf-list-test";
                }
                leaf-list empty-test {
                  ciena-common-yang:encrypt "empty-test-encrypted";
                  ciena-common-yang:encrypt-path "/ciena-common-test/encryption-test-container/encryption-list-test/leaf-list-test";
                  type empty;
                }
                leaf-list empty-test-encrypted {
                  type string {
                    ciena-common-yang:stringptr "true";
                  }
                  ciena-common-yang:decrypt "empty-test";
                  ciena-common-yang:decrypt-path "/ciena-common-test/encryption-test-container/encryption-list-test/leaf-list-test";
                }
                leaf-list enumeration-test {
                  ciena-common-yang:encrypt "enumeration-test-encrypted";
                  ciena-common-yang:encrypt-path "/ciena-common-test/encryption-test-container/encryption-list-test/leaf-list-test";
                  type enumeration {
                    enum test-a;
                    enum test-b;
                    enum test-c;
                    enum map;
                  }
                }
                leaf-list enumeration-test-encrypted {
                  type string {
                    ciena-common-yang:stringptr "true";
                  }
                  ciena-common-yang:decrypt "enumeration-test";
                  ciena-common-yang:decrypt-path "/ciena-common-test/encryption-test-container/encryption-list-test/leaf-list-test";
                }
                leaf-list identityref-test {
                  ciena-common-yang:encrypt "identityref-test-encrypted";
                  ciena-common-yang:encrypt-path "/ciena-common-test/encryption-test-container/encryption-list-test/leaf-list-test";
                  type identityref {
                    base test:crypto-alg;
                  }
                }
                leaf-list identityref-test-encrypted {
                  type string {
                    ciena-common-yang:stringptr "true";
                  }
                  ciena-common-yang:decrypt "identityref-test";
                  ciena-common-yang:decrypt-path "/ciena-common-test/encryption-test-container/encryption-list-test/leaf-list-test";
                }
                leaf-list instance-identifier-test {
                  ciena-common-yang:encrypt "instance-identifier-test-encrypted";
                  ciena-common-yang:encrypt-path "/ciena-common-test/encryption-test-container/encryption-list-test/leaf-list-test";
                  type instance-identifier;
                }
                leaf-list instance-identifier-test-encrypted {
                  type string {
                    ciena-common-yang:stringptr "true";
                  }
                  ciena-common-yang:decrypt "instance-identifier-test";
                  ciena-common-yang:decrypt-path "/ciena-common-test/encryption-test-container/encryption-list-test/leaf-list-test";
                }
                leaf-list leafref-test {
                  ciena-common-yang:encrypt "leafref-test-encrypted";
                  ciena-common-yang:encrypt-path "/ciena-common-test/encryption-test-container/encryption-list-test/leaf-list-test";
                  type leafref {
                    path "/test:red/test:blue/test:b";
                  }
                }
                leaf-list leafref-test-encrypted {
                  type string {
                    ciena-common-yang:stringptr "true";
                  }
                  ciena-common-yang:decrypt "leafref-test";
                  ciena-common-yang:decrypt-path "/ciena-common-test/encryption-test-container/encryption-list-test/leaf-list-test";
                }
                leaf-list stringptr-test {
                  ciena-common-yang:encrypt "stringptr-test-encrypted";
                  ciena-common-yang:encrypt-path "/ciena-common-test/encryption-test-container/encryption-list-test/leaf-list-test";
                  type stringptr;
                }
                leaf-list stringptr-test-encrypted {
                  type string {
                    ciena-common-yang:stringptr "true";
                  }
                  ciena-common-yang:decrypt "stringptr-test";
                  ciena-common-yang:decrypt-path "/ciena-common-test/encryption-test-container/encryption-list-test/leaf-list-test";
                }
                leaf-list string-test {
                  ciena-common-yang:encrypt "string-test-encrypted";
                  ciena-common-yang:encrypt-path "/ciena-common-test/encryption-test-container/encryption-list-test/leaf-list-test";
                  type string;
                }
                leaf-list string-test-encrypted {
                  type string {
                    ciena-common-yang:stringptr "true";
                  }
                  ciena-common-yang:decrypt "string-test";
                  ciena-common-yang:decrypt-path "/ciena-common-test/encryption-test-container/encryption-list-test/leaf-list-test";
                }
                leaf-list uint8-test {
                  ciena-common-yang:encrypt "uint8-test-encrypted";
                  ciena-common-yang:encrypt-path "/ciena-common-test/encryption-test-container/encryption-list-test/leaf-list-test";
                  type uint8;
                }
                leaf-list uint8-test-encrypted {
                  type string {
                    ciena-common-yang:stringptr "true";
                  }
                  ciena-common-yang:decrypt "uint8-test";
                  ciena-common-yang:decrypt-path "/ciena-common-test/encryption-test-container/encryption-list-test/leaf-list-test";
                }
                leaf-list union-test {
                  ciena-common-yang:encrypt "union-test-encrypted";
                  ciena-common-yang:encrypt-path "/ciena-common-test/encryption-test-container/encryption-list-test/leaf-list-test";
                  type union {
                    type int32;
                    type enumeration {
                      enum unbounded;
                    }
                  }
                }
                leaf-list union-test-encrypted {
                  type string {
                    ciena-common-yang:stringptr "true";
                  }
                  ciena-common-yang:decrypt "union-test";
                  ciena-common-yang:decrypt-path "/ciena-common-test/encryption-test-container/encryption-list-test/leaf-list-test";
                }
              }
              container leaf-test {
                leaf binary-test {
                  ciena-common-yang:encrypt "binary-test-encrypted";
                  ciena-common-yang:encrypt-path "/ciena-common-test/encryption-test-container/encryption-list-test/leaf-test";
                  type binary;
                  ciena-common-yang:sensitive "true";
                }
                leaf binary-test-encrypted {
                  type string {
                    ciena-common-yang:stringptr "true";
                  }
                  ciena-common-yang:decrypt "binary-test";
                  ciena-common-yang:decrypt-path "/ciena-common-test/encryption-test-container/encryption-list-test/leaf-test";
                  ciena-common-yang:sensitive "true";
                }
                leaf bits-test {
                  ciena-common-yang:encrypt "bits-test-encrypted";
                  ciena-common-yang:encrypt-path "/ciena-common-test/encryption-test-container/encryption-list-test/leaf-test";
                  ciena-common-yang:sensitive "true";
                  type bits {
                    bit apple {
                      position 0;
                    }
                    bit orange {
                      position 1;
                    }
                    bit banana {
                      position 2;
                    }
                  }
                }
                leaf bits-test-encrypted {
                  type string {
                    ciena-common-yang:stringptr "true";
                  }
                  ciena-common-yang:decrypt "bits-test";
                  ciena-common-yang:decrypt-path "/ciena-common-test/encryption-test-container/encryption-list-test/leaf-test";
                  ciena-common-yang:sensitive "true";
                }
                leaf offset-bits-test {
                  ciena-common-yang:encrypt "offset-bits-test-encrypted";
                  ciena-common-yang:encrypt-path "/ciena-common-test/encryption-test-container/encryption-list-test/leaf-test";
                  ciena-common-yang:sensitive "true";
                  type bits {
                    bit apple {
                      position 3;
                    }
                    bit orange {
                      position 5;
                    }
                    bit banana {
                      position 7;
                    }
                  }
                }
                leaf offset-bits-test-encrypted {
                  type string {
                    ciena-common-yang:stringptr "true";
                  }
                  ciena-common-yang:decrypt "offset-bits-test";
                  ciena-common-yang:decrypt-path "/ciena-common-test/encryption-test-container/encryption-list-test/leaf-test";
                  ciena-common-yang:sensitive "true";
                }
                leaf boolean-test {
                  ciena-common-yang:encrypt "boolean-test-encrypted";
                  ciena-common-yang:encrypt-path "/ciena-common-test/encryption-test-container/encryption-list-test/leaf-test";
                  ciena-common-yang:sensitive "true";
                  type boolean;
                }
                leaf boolean-test-encrypted {
                  type string {
                    ciena-common-yang:stringptr "true";
                  }
                  ciena-common-yang:decrypt "boolean-test";
                  ciena-common-yang:decrypt-path "/ciena-common-test/encryption-test-container/encryption-list-test/leaf-test";
                  ciena-common-yang:sensitive "true";
                }
                leaf decimal64-test {
                  ciena-common-yang:encrypt "decimal64-test-encrypted";
                  ciena-common-yang:encrypt-path "/ciena-common-test/encryption-test-container/encryption-list-test/leaf-test";
                  ciena-common-yang:sensitive "true";
                  type decimal64 {
                    fraction-digits 2;
                  }
                }
                leaf decimal64-test-encrypted {
                  type string {
                    ciena-common-yang:stringptr "true";
                  }
                  ciena-common-yang:decrypt "decimal64-test";
                  ciena-common-yang:decrypt-path "/ciena-common-test/encryption-test-container/encryption-list-test/leaf-test";
                  ciena-common-yang:sensitive "true";
                }
                leaf empty-test {
                  ciena-common-yang:encrypt "empty-test-encrypted";
                  ciena-common-yang:encrypt-path "/ciena-common-test/encryption-test-container/encryption-list-test/leaf-test";
                  ciena-common-yang:sensitive "true";
                  type empty;
                }
                leaf empty-test-encrypted {
                  type string {
                    ciena-common-yang:stringptr "true";
                  }
                  ciena-common-yang:decrypt "empty-test";
                  ciena-common-yang:decrypt-path "/ciena-common-test/encryption-test-container/encryption-list-test/leaf-test";
                  ciena-common-yang:sensitive "true";
                }
                leaf enumeration-test {
                  ciena-common-yang:encrypt "enumeration-test-encrypted";
                  ciena-common-yang:encrypt-path "/ciena-common-test/encryption-test-container/encryption-list-test/leaf-test";
                  ciena-common-yang:sensitive "true";
                  type enumeration {
                    enum test-1;
                    enum test-2;
                    enum test-3;
                  }
                }
                leaf enumeration-test-encrypted {
                  type string {
                    ciena-common-yang:stringptr "true";
                  }
                  ciena-common-yang:decrypt "enumeration-test";
                  ciena-common-yang:decrypt-path "/ciena-common-test/encryption-test-container/encryption-list-test/leaf-test";
                  ciena-common-yang:sensitive "true";
                }
                leaf enumeration-extended-test {
                  ciena-common-yang:encrypt "enumeration-extended-test-encrypted";
                  ciena-common-yang:encrypt-path "/ciena-common-test/encryption-test-container/encryption-list-test/leaf-test";
                  ciena-common-yang:sensitive "true";
                  type enumeration {
                    enum forty-one {
                      value 41;
                    }
                    enum ten {
                      value 10;
                    }
                    enum seven {
                      value 7;
                    }
                  }
                }
                leaf enumeration-extended-test-encrypted {
                  type string {
                    ciena-common-yang:stringptr "true";
                  }
                  ciena-common-yang:decrypt "enumeration-extended-test";
                  ciena-common-yang:decrypt-path "/ciena-common-test/encryption-test-container/encryption-list-test/leaf-test";
                  ciena-common-yang:sensitive "true";
                }
                leaf identityref-test {
                  ciena-common-yang:encrypt "identifyref-test-encrypted";
                  ciena-common-yang:encrypt-path "/ciena-common-test/encryption-test-container/encryption-list-test/leaf-test";
                  ciena-common-yang:sensitive "true";
                  type identityref {
                    base test:crypto-alg;
                  }
                }
                leaf identifyref-test-encrypted {
                  type string {
                    ciena-common-yang:stringptr "true";
                  }
                  ciena-common-yang:decrypt "identityref-test";
                  ciena-common-yang:decrypt-path "/ciena-common-test/encryption-test-container/encryption-list-test/leaf-test";
                  ciena-common-yang:sensitive "true";
                }
                leaf instance-identifier-test {
                  ciena-common-yang:encrypt "instance-identifier-test-encrypted";
                  ciena-common-yang:encrypt-path "/ciena-common-test/encryption-test-container/encryption-list-test/leaf-test";
                  ciena-common-yang:sensitive "true";
                  type instance-identifier;
                }
                leaf instance-identifier-test-encrypted {
                  type string {
                    ciena-common-yang:stringptr "true";
                  }
                  ciena-common-yang:decrypt "instance-identifier-test";
                  ciena-common-yang:decrypt-path "/ciena-common-test/encryption-test-container/encryption-list-test/leaf-test";
                  ciena-common-yang:sensitive "true";
                }
                leaf int64-test {
                  ciena-common-yang:encrypt "int64-test-encrypted";
                  ciena-common-yang:encrypt-path "/ciena-common-test/encryption-test-container/encryption-list-test/leaf-test";
                  ciena-common-yang:sensitive "true";
                  type int64;
                }
                leaf int64-test-encrypted {
                  type string {
                    ciena-common-yang:stringptr "true";
                  }
                  ciena-common-yang:decrypt "int64-test";
                  ciena-common-yang:decrypt-path "/ciena-common-test/encryption-test-container/encryption-list-test/leaf-test";
                  ciena-common-yang:sensitive "true";
                }
                leaf leafref-test {
                  ciena-common-yang:encrypt "leafref-test-encrypted";
                  ciena-common-yang:encrypt-path "/ciena-common-test/encryption-test-container/encryption-list-test/leaf-test";
                  ciena-common-yang:sensitive "true";
                  type leafref {
                    path "/test:red/test:blue/test:c";
                  }
                }
                leaf leafref-test-encrypted {
                  type string {
                    ciena-common-yang:stringptr "true";
                  }
                  ciena-common-yang:decrypt "leafref-test";
                  ciena-common-yang:decrypt-path "/ciena-common-test/encryption-test-container/encryption-list-test/leaf-test";
                  ciena-common-yang:sensitive "true";
                }
                leaf stringptr-test {
                  ciena-common-yang:encrypt "stringptr-test-encrypted";
                  ciena-common-yang:encrypt-path "/ciena-common-test/encryption-test-container/encryption-list-test/leaf-test";
                  ciena-common-yang:sensitive "true";
                  type string {
                    ciena-common-yang:stringptr "true";
                  }
                }
                leaf stringptr-test-encrypted {
                  type string {
                    ciena-common-yang:stringptr "true";
                  }
                  ciena-common-yang:decrypt "stringptr-test";
                  ciena-common-yang:decrypt-path "/ciena-common-test/encryption-test-container/encryption-list-test/leaf-test";
                  ciena-common-yang:sensitive "true";
                }
                leaf string-test {
                  ciena-common-yang:encrypt "string-test-encrypted";
                  ciena-common-yang:encrypt-path "/ciena-common-test/encryption-test-container/encryption-list-test/leaf-test";
                  ciena-common-yang:sensitive "true";
                  type string {
                    length "0..15";
                  }
                }
                leaf string-test-encrypted {
                  type string {
                    ciena-common-yang:stringptr "true";
                  }
                  ciena-common-yang:decrypt "string-test";
                  ciena-common-yang:decrypt-path "/ciena-common-test/encryption-test-container/encryption-list-test/leaf-test";
                  ciena-common-yang:sensitive "true";
                }
                leaf union-test {
                  ciena-common-yang:encrypt "union-test-encrypted";
                  ciena-common-yang:encrypt-path "/ciena-common-test/encryption-test-container/encryption-list-test/leaf-test";
                  type union {
                    type int32;
                    type enumeration {
                      enum unbounded;
                    }
                  }
                  ciena-common-yang:sensitive "true";
                }
                leaf union-test-encrypted {
                  type string {
                    ciena-common-yang:stringptr "true";
                  }
                  ciena-common-yang:decrypt "union-test";
                  ciena-common-yang:decrypt-path "/ciena-common-test/encryption-test-container/encryption-list-test/leaf-test";
                  ciena-common-yang:sensitive "true";
                }
              }
            }
          }
          action toggle-sleep {
            input {
              leaf sleep {
                type boolean;
              }
            }
          }
          uses grouping-test;
          action rpc-test-empty;
          action rpc-test-no-output {
            input {
              leaf input-test {
                type string;
              }
            }
          }
          action rpc-test-no-input {
            output {
              leaf input-test {
                type string;
              }
            }
          }
          action rpc-test {
            input {
              uses grouping-no-action-test;
            }
            output {
              uses grouping-no-action-test;
            }
          }
          action rpc-trigger-encryption-set {
            input {
              leaf path {
                type instance-identifier;
              }
            }
          }
          notification notification-test {
            uses red-blue-group;
          }
          notification encryption-notification-test {
            container X {
              leaf y {
                ciena-common-yang:encrypt "y-encrypted";
                ciena-common-yang:encrypt-path "/ciena-common-test/encryption-notification-test/X";
                type string;
              }
              leaf y-encrypted {
                type string {
                  ciena-common-yang:stringptr "true";
                }
                ciena-common-yang:decrypt "y";
                ciena-common-yang:decrypt-path "/ciena-common-test/encryption-notification-test/X";
              }
            }
          }
          action stack-push {
            description
              "Push into thread specific stack";
            input {
              leaf attr {
                type string;
                default "ddy_stack_test";
              }
              leaf recursive {
                type uint64;
                default "10";
              }
              leaf multistack {
                type uint64;
                default "0";
              }
            }
            output {
              leaf pass {
                type boolean;
              }
            }
          }
          action stack-pop {
            description
              "Pop from thread specific stack";
            input {
              leaf attr {
                type string;
                default "ddy_stack_test";
              }
              leaf recursive {
                type uint64;
                default "10";
              }
              leaf multistack {
                type uint64;
                default "0";
              }
            }
            output {
              leaf pass {
                type boolean;
              }
              leaf-list pop {
                type string;
              }
            }
          }
          action stack-get {
            description
              "Get pushed data for an attribute";
            input {
              leaf attr {
                type string;
                default "ddy_stack_test";
              }
              leaf recursive {
                type uint64;
                default "10";
              }
              leaf multistack {
                type uint64;
                default "0";
              }
            }
            output {
              leaf pass {
                type boolean;
              }
              leaf-list get {
                type string;
              }
            }
          }
          action stack-merge {
            description
              "Merge thread specific stacks";
            input {
              leaf attr {
                type string;
                default "ddy_stack_test";
              }
              leaf count {
                type uint64;
                default "0";
              }
              leaf all {
                type boolean;
              }
            }
            output {
              leaf pass {
                type boolean;
              }
            }
          }
          action return-code-set {
            description
              "Set the return code in the response";
            input {
              leaf return-code {
                type identityref {
                  base ciena-common-yang:error-code;
                }
              }
            }
            output {
              leaf pass {
                type boolean;
              }
            }
          }
          action validate-test {
            description
              "Set the return code in the response";
            input {
              uses abc_validate_group;
              container sub-group {
                uses abc_validate_group;
              }
            }
            output {
              uses ciena-common-yang:rpc-result-common;
            }
          }
          action test-deadline-timeout {
            description
              "Take input as timeout and handler will wait till this time
                based on test scenario type and return pass as true/false.";
            input {
              uses deadline-group;
            }
            output {
              leaf pass {
                type boolean;
              }
            }
          }
          container mount_test_a {
            list b {
              key "name";
              leaf name {
                type string;
              }
              anyxml c;
              container anyxml-mount {
                ciena-common-yang:mount-start "ciena-common-test";
                ciena-common-yang:mount-end "ciena-common-test";
              }
              anydata d;
              container anydata-mount {
                ciena-common-yang:mount-start "ciena-common-test";
                ciena-common-yang:mount-end "ciena-common-test";
              }
            }
          }
          container mount_test_b {
            list b {
              key "name";
              leaf name {
                type string;
              }
              anyxml c;
              container anyxml-mount {
                ciena-common-yang:mount-start "ciena-common-test-list";
                uses ciena-common-test-list:ciena-common-test-list-mount-data;
                uses ciena-common-test-list:ciena-common-test-list-mount-actions-notifs;
                ciena-common-yang:mount-end "ciena-common-test-list";
              }
            }
          }
          container i_love_big_data {
            list big_list {
              key "name";
              leaf name {
                type uint64;
              }
              leaf some_data {
                type decimal64 {
                  fraction-digits 10;
                }
              }
            }
          }
          container i_love_instance_id_for_keys {
            list some_list {
              key "instance_id_name";
              leaf instance_id_name {
                type instance-identifier;
              }
              leaf some_data {
                type decimal64 {
                  fraction-digits 10;
                }
              }
              container some_container {
                description
                  "Dummy container to have same context as parent";
                list sub_list {
                  description
                    "Another keyed list to have instance-id in parent context";
                  key "some_sub_key";
                  leaf some_sub_key {
                    type uint32;
                  }
                  leaf some_sub_leaf {
                    type uint32;
                  }
                }
              }
            }
          }
          container test-restconf-a {
            leaf b {
              type string;
            }
            leaf c {
              type uint8;
            }
            leaf awesome-wildcard-field {
              type string;
            }
            list d {
              key "name";
              leaf name {
                type string;
              }
              leaf test-state {
                type boolean;
              }
              container awesome-wildcard-field {
                leaf awesome-wildcard-field {
                  type boolean;
                }
                leaf awesome-wildcard-field-not {
                  type string;
                }
              }
              list e {
                key "index";
                leaf index {
                  type uint8;
                }
                leaf name {
                  type string;
                }
                list awesome-wildcard-field {
                  key "awesome-wildcard-field";
                  leaf awesome-wildcard-field {
                    type uint8;
                  }
                }
              }
            }
          }
          container test-colon-container {
            leaf enumeration-test {
              ciena-common-yang:sensitive "true";
              type enumeration {
                enum "1:n Mux type";
                enum "2:n Mux type";
                enum "3:n Mux type";
              }
            }
          }
          container multi-augment;
          container ddy-test-server-config {
            leaf handle-complete-transaction {
              type enumeration {
                enum none {
                  description
                    "complete-transaction not handled at all";
                }
                enum local {
                  description
                    "complete-transaction bound to local service";
                }
                enum service {
                  description
                    "complete-transaction bound to ddy-test-server";
                }
              }
              default "none";
            }
          }
          action client-activations {
            description
              "Sometimes you are testing something and you just need a simple way to execute a task.";
            input {
              leaf number {
                description
                  "This number can be used to call a specific function.";
                type uint64;
              }
            }
          }
          ciena-common-yang:mount-end "ciena-common-test";
        }
      }
    }
    container mount_test_b {
      list b {
        key "name";
        leaf name {
          type string;
        }
        anyxml c;
        container anyxml-mount {
          ciena-common-yang:mount-start "ciena-common-test-list";
          uses ciena-common-test-list:ciena-common-test-list-mount-data;
          uses ciena-common-test-list:ciena-common-test-list-mount-actions-notifs;
          ciena-common-yang:mount-end "ciena-common-test-list";
        }
      }
    }
    container i_love_big_data {
      list big_list {
        key "name";
        leaf name {
          type uint64;
        }
        leaf some_data {
          type decimal64 {
            fraction-digits 10;
          }
        }
      }
    }
    container i_love_instance_id_for_keys {
      list some_list {
        key "instance_id_name";
        leaf instance_id_name {
          type instance-identifier;
        }
        leaf some_data {
          type decimal64 {
            fraction-digits 10;
          }
        }
        container some_container {
          description
            "Dummy container to have same context as parent";
          list sub_list {
            description
              "Another keyed list to have instance-id in parent context";
            key "some_sub_key";
            leaf some_sub_key {
              type uint32;
            }
            leaf some_sub_leaf {
              type uint32;
            }
          }
        }
      }
    }
    container test-restconf-a {
      leaf b {
        type string;
      }
      leaf c {
        type uint8;
      }
      leaf awesome-wildcard-field {
        type string;
      }
      list d {
        key "name";
        leaf name {
          type string;
        }
        leaf test-state {
          type boolean;
        }
        container awesome-wildcard-field {
          leaf awesome-wildcard-field {
            type boolean;
          }
          leaf awesome-wildcard-field-not {
            type string;
          }
        }
        list e {
          key "index";
          leaf index {
            type uint8;
          }
          leaf name {
            type string;
          }
          list awesome-wildcard-field {
            key "awesome-wildcard-field";
            leaf awesome-wildcard-field {
              type uint8;
            }
          }
        }
      }
    }
    container test-colon-container {
      leaf enumeration-test {
        ciena-common-yang:sensitive "true";
        type enumeration {
          enum "1:n Mux type";
          enum "2:n Mux type";
          enum "3:n Mux type";
        }
      }
    }
    container multi-augment;
    container ddy-test-server-config {
      leaf handle-complete-transaction {
        type enumeration {
          enum none {
            description
              "complete-transaction not handled at all";
          }
          enum local {
            description
              "complete-transaction bound to local service";
          }
          enum service {
            description
              "complete-transaction bound to ddy-test-server";
          }
        }
        default "none";
      }
    }
  }

  grouping ciena-common-test-mount-actions-notifs {
    action toggle-sleep {
      input {
        leaf sleep {
          type boolean;
        }
      }
    }
    action rpc-test-empty;
    action rpc-test-no-output {
      input {
        leaf input-test {
          type string;
        }
      }
    }
    action rpc-test-no-input {
      output {
        leaf input-test {
          type string;
        }
      }
    }
    action rpc-test {
      input {
        uses grouping-no-action-test;
      }
      output {
        uses grouping-no-action-test;
      }
    }
    action rpc-trigger-encryption-set {
      input {
        leaf path {
          type instance-identifier;
        }
      }
    }
    notification notification-test {
      uses red-blue-group;
    }
    notification encryption-notification-test {
      container X {
        leaf y {
          ciena-common-yang:encrypt "y-encrypted";
          ciena-common-yang:encrypt-path "/ciena-common-test/encryption-notification-test/X";
          type string;
        }
        leaf y-encrypted {
          type string {
            ciena-common-yang:stringptr "true";
          }
          ciena-common-yang:decrypt "y";
          ciena-common-yang:decrypt-path "/ciena-common-test/encryption-notification-test/X";
        }
      }
    }
    action stack-push {
      description
        "Push into thread specific stack";
      input {
        leaf attr {
          type string;
          default "ddy_stack_test";
        }
        leaf recursive {
          type uint64;
          default "10";
        }
        leaf multistack {
          type uint64;
          default "0";
        }
      }
      output {
        leaf pass {
          type boolean;
        }
      }
    }
    action stack-pop {
      description
        "Pop from thread specific stack";
      input {
        leaf attr {
          type string;
          default "ddy_stack_test";
        }
        leaf recursive {
          type uint64;
          default "10";
        }
        leaf multistack {
          type uint64;
          default "0";
        }
      }
      output {
        leaf pass {
          type boolean;
        }
        leaf-list pop {
          type string;
        }
      }
    }
    action stack-get {
      description
        "Get pushed data for an attribute";
      input {
        leaf attr {
          type string;
          default "ddy_stack_test";
        }
        leaf recursive {
          type uint64;
          default "10";
        }
        leaf multistack {
          type uint64;
          default "0";
        }
      }
      output {
        leaf pass {
          type boolean;
        }
        leaf-list get {
          type string;
        }
      }
    }
    action stack-merge {
      description
        "Merge thread specific stacks";
      input {
        leaf attr {
          type string;
          default "ddy_stack_test";
        }
        leaf count {
          type uint64;
          default "0";
        }
        leaf all {
          type boolean;
        }
      }
      output {
        leaf pass {
          type boolean;
        }
      }
    }
    action return-code-set {
      description
        "Set the return code in the response";
      input {
        leaf return-code {
          type identityref {
            base ciena-common-yang:error-code;
          }
        }
      }
      output {
        leaf pass {
          type boolean;
        }
      }
    }
    action validate-test {
      description
        "Set the return code in the response";
      input {
        uses abc_validate_group;
        container sub-group {
          uses abc_validate_group;
        }
      }
      output {
        uses ciena-common-yang:rpc-result-common;
      }
    }
    action test-deadline-timeout {
      description
        "Take input as timeout and handler will wait till this time
          based on test scenario type and return pass as true/false.";
      input {
        uses deadline-group;
      }
      output {
        leaf pass {
          type boolean;
        }
      }
    }
    action client-activations {
      description
        "Sometimes you are testing something and you just need a simple way to execute a task.";
      input {
        leaf number {
          description
            "This number can be used to call a specific function.";
          type uint64;
        }
      }
    }
  }

  grouping ciena-common-test-mount-actions-notifs-as-cont {
    container toggle-sleep {
      container input {
        ciena-common-yang:containerptr "true";
      }
    }
    container rpc-test-empty;
    container rpc-test-no-output {
      container input {
        ciena-common-yang:containerptr "true";
      }
    }
    container rpc-test-no-input {
      container output {
        ciena-common-yang:containerptr "true";
      }
    }
    container rpc-test {
      container input {
        ciena-common-yang:containerptr "true";
      }
      container output {
        ciena-common-yang:containerptr "true";
      }
    }
    container rpc-trigger-encryption-set {
      container input {
        ciena-common-yang:containerptr "true";
      }
    }
    container notification-test {
      ciena-common-yang:containerptr "true";
      uses red-blue-group;
    }
    container encryption-notification-test {
      ciena-common-yang:containerptr "true";
      container X {
        leaf y {
          ciena-common-yang:encrypt "y-encrypted";
          ciena-common-yang:encrypt-path "/ciena-common-test/encryption-notification-test/X";
          type string;
        }
        leaf y-encrypted {
          type string {
            ciena-common-yang:stringptr "true";
          }
          ciena-common-yang:decrypt "y";
          ciena-common-yang:decrypt-path "/ciena-common-test/encryption-notification-test/X";
        }
      }
    }
    container stack-push {
      description
        "Push into thread specific stack";
      container input {
        ciena-common-yang:containerptr "true";
      }
      container output {
        ciena-common-yang:containerptr "true";
      }
    }
    container stack-pop {
      description
        "Pop from thread specific stack";
      container input {
        ciena-common-yang:containerptr "true";
      }
      container output {
        ciena-common-yang:containerptr "true";
      }
    }
    container stack-get {
      description
        "Get pushed data for an attribute";
      container input {
        ciena-common-yang:containerptr "true";
      }
      container output {
        ciena-common-yang:containerptr "true";
      }
    }
    container stack-merge {
      description
        "Merge thread specific stacks";
      container input {
        ciena-common-yang:containerptr "true";
      }
      container output {
        ciena-common-yang:containerptr "true";
      }
    }
    container return-code-set {
      description
        "Set the return code in the response";
      container input {
        ciena-common-yang:containerptr "true";
      }
      container output {
        ciena-common-yang:containerptr "true";
      }
    }
    container validate-test {
      description
        "Set the return code in the response";
      container input {
        ciena-common-yang:containerptr "true";
      }
      container output {
        ciena-common-yang:containerptr "true";
      }
    }
    container test-deadline-timeout {
      description
        "Take input as timeout and handler will wait till this time
          based on test scenario type and return pass as true/false.";
      container input {
        ciena-common-yang:containerptr "true";
      }
      container output {
        ciena-common-yang:containerptr "true";
      }
    }
    container client-activations {
      description
        "Sometimes you are testing something and you just need a simple way to execute a task.";
      container input {
        ciena-common-yang:containerptr "true";
      }
    }
  }

  grouping ciena-common-test-mount-data-actions-notifs-as-cont {
    container string-based-return-code-list {
      config false;
      description
        "List of errors in case of command failure";
      list return-code-list {
        leaf instance {
          type string {
            ciena-common-yang:stringptr "true";
          }
          description
            "The instance to which the error code applies.";
        }
        leaf error {
          type string;
        }
      }
    }
    uses red-blue-group;
    uses blue-yellow-group;
    container white {
      uses abc_group;
      container cont1 {
        uses abc_group;
      }
      container cont2 {
        uses abc_group;
      }
      container cont3 {
        uses abc_group;
      }
      container cont4 {
        uses abc_group;
      }
      list list1 {
        key "k";
        leaf k {
          type uint8;
        }
        uses abc_group;
      }
    }
    container validation-test {
      uses abc_validate_group;
    }
    container to-pointer-test {
      container a {
        leaf string-test {
          type string;
        }
      }
    }
    list to-pointer-test2 {
      key "first-key";
      leaf first-key {
        type uint8;
      }
      list second-list {
        key "second-key";
        leaf second-key {
          type uint8;
        }
        leaf second-string {
          type string;
        }
        container second-container {
          leaf second-container-string {
            type string;
          }
        }
      }
    }
    container nested-container {
      container cone {
        leaf a {
          type uint8;
          default "1";
        }
        leaf b {
          type uint8;
          default "2";
        }
        leaf c {
          type uint8;
          default "3";
        }
      }
      container ctwo {
        config false;
        leaf d {
          type uint8;
        }
        leaf e {
          type uint8;
        }
        leaf f {
          type uint8;
        }
      }
    }
    container read-only {
      config false;
      uses red-blue-group;
      container name {
        container collision {
          leaf test {
            type uint8;
          }
          container child1 {
            container child2 {
              leaf test {
                type uint8;
              }
            }
          }
        }
      }
      container name-collision {
        leaf test {
          type uint8;
        }
        container child1 {
          container child2 {
            leaf test {
              type uint8;
            }
          }
        }
      }
    }
    container remove-via-deviation {
      uses red-blue-group;
    }
    uses ordered-lists-group;
    container simple-deadline-test {
      uses deadline-group;
    }
    container simple-test-container {
      ciena-common-yang:containerptr "true";
      list keys-only-list {
        key "name";
        leaf name {
          type string;
        }
      }
      leaf other-attribute {
        type string;
      }
      container leaf-test {
        leaf string-test {
          ciena-common-yang:encrypt "string-test-encrypted";
          ciena-common-yang:encrypt-path "/ciena-common-test/simple-test-container/leaf-test";
          type string;
        }
        leaf string-test-encrypted {
          type string {
            ciena-common-yang:stringptr "true";
          }
          ciena-common-yang:decrypt "string-test";
          ciena-common-yang:decrypt-path "/ciena-common-test/simple-test-container/leaf-test";
        }
        leaf uint8-test {
          type uint8;
        }
      }
      container presence-test {
        presence "presense test container";
      }
      container presence-test-2 {
        choice start-time {
          mandatory true;
          container immediate {
            presence "Start the measurement session immediately.";
          }
          leaf relative {
            type string;
          }
          leaf absolute {
            type string;
          }
        }
      }
      list outter {
        key "index";
        leaf index {
          type uint8;
        }
        min-elements 2;
        max-elements 3;
        list inner {
          key "name";
          leaf name {
            type string;
          }
          max-elements 2;
          leaf value {
            type uint16;
          }
        }
        leaf-list boolean-leaf-list {
          type boolean;
          max-elements 3;
          min-elements 2;
        }
        leaf mode {
          type uint8 {
            range "0..10";
          }
        }
      }
      list first {
        key "key1 key2";
        leaf key1 {
          type uint8;
        }
        leaf key2 {
          type string;
        }
        list second {
          key "key1 key2";
          leaf key1 {
            type uint8;
          }
          leaf key2 {
            type string;
          }
          list third {
            key "key1";
            leaf key1 {
              type uint8;
            }
            container red {
              container blue {
                leaf a {
                  type string;
                }
                leaf b {
                  type string;
                }
              }
              leaf yellow-leaf {
                type string;
              }
              anyxml config;
            }
          }
        }
      }
    }
    container list-keys {
      list bits-key {
        key "bit";
        leaf bit {
          type bits {
            bit x;
            bit y;
            bit z;
          }
        }
      }
    }
    container identity-test {
      leaf base-test {
        type identityref {
          base test:crypto-alg;
        }
      }
      leaf mid-level-test {
        type identityref {
          base test:des;
        }
      }
      leaf top-test {
        type identityref {
          base test:des3;
        }
      }
      leaf external-test {
        type identityref {
          base ciena-common-yang:error-does-not-exist;
        }
      }
    }
    container encryption-test-container {
      container container-generate-at-abs-path-enc {
        ciena-common-yang:decrypt "container-generate-at-abs-path";
        ciena-common-yang:decrypt-path "/ciena-common-test/encryption-test-container";
        leaf a {
          type string {
            ciena-common-yang:stringptr "true";
          }
          ciena-common-yang:decrypt "a";
          ciena-common-yang:decrypt-path "/ciena-common-test/encryption-test-container/container-generate-at-abs-path";
        }
        container b {
          ciena-common-yang:decrypt "b";
          ciena-common-yang:decrypt-path "/ciena-common-test/encryption-test-container/container-generate-at-abs-path";
          leaf c {
            type string {
              ciena-common-yang:stringptr "true";
            }
            ciena-common-yang:decrypt "c";
            ciena-common-yang:decrypt-path "/ciena-common-test/encryption-test-container/container-generate-at-abs-path/b";
          }
        }
        config false;
      }
      list encryption-mount-test {
        key "name";
        leaf name {
          type string;
        }
        container data {
          ciena-common-yang:mount-start "ciena-common-test";
          container string-based-return-code-list {
            config false;
            description
              "List of errors in case of command failure";
            list return-code-list {
              leaf instance {
                type string {
                  ciena-common-yang:stringptr "true";
                }
                description
                  "The instance to which the error code applies.";
              }
              leaf error {
                type string;
              }
            }
          }
          uses red-blue-group;
          uses blue-yellow-group;
          container white {
            uses abc_group;
            container cont1 {
              uses abc_group;
            }
            container cont2 {
              uses abc_group;
            }
            container cont3 {
              uses abc_group;
            }
            container cont4 {
              uses abc_group;
            }
            list list1 {
              key "k";
              leaf k {
                type uint8;
              }
              uses abc_group;
            }
          }
          container validation-test {
            uses abc_validate_group;
          }
          container to-pointer-test {
            container a {
              leaf string-test {
                type string;
              }
            }
          }
          list to-pointer-test2 {
            key "first-key";
            leaf first-key {
              type uint8;
            }
            list second-list {
              key "second-key";
              leaf second-key {
                type uint8;
              }
              leaf second-string {
                type string;
              }
              container second-container {
                leaf second-container-string {
                  type string;
                }
              }
            }
          }
          container nested-container {
            container cone {
              leaf a {
                type uint8;
                default "1";
              }
              leaf b {
                type uint8;
                default "2";
              }
              leaf c {
                type uint8;
                default "3";
              }
            }
            container ctwo {
              config false;
              leaf d {
                type uint8;
              }
              leaf e {
                type uint8;
              }
              leaf f {
                type uint8;
              }
            }
          }
          container read-only {
            config false;
            uses red-blue-group;
            container name {
              container collision {
                leaf test {
                  type uint8;
                }
                container child1 {
                  container child2 {
                    leaf test {
                      type uint8;
                    }
                  }
                }
              }
            }
            container name-collision {
              leaf test {
                type uint8;
              }
              container child1 {
                container child2 {
                  leaf test {
                    type uint8;
                  }
                }
              }
            }
          }
          container remove-via-deviation {
            uses red-blue-group;
          }
          uses ordered-lists-group;
          container simple-deadline-test {
            uses deadline-group;
          }
          container simple-test-container {
            ciena-common-yang:containerptr "true";
            list keys-only-list {
              key "name";
              leaf name {
                type string;
              }
            }
            leaf other-attribute {
              type string;
            }
            container leaf-test {
              leaf string-test {
                ciena-common-yang:encrypt "string-test-encrypted";
                ciena-common-yang:encrypt-path "/ciena-common-test/simple-test-container/leaf-test";
                type string;
              }
              leaf string-test-encrypted {
                type string {
                  ciena-common-yang:stringptr "true";
                }
                ciena-common-yang:decrypt "string-test";
                ciena-common-yang:decrypt-path "/ciena-common-test/simple-test-container/leaf-test";
              }
              leaf uint8-test {
                type uint8;
              }
            }
            container presence-test {
              presence "presense test container";
            }
            container presence-test-2 {
              choice start-time {
                mandatory true;
                container immediate {
                  presence "Start the measurement session immediately.";
                }
                leaf relative {
                  type string;
                }
                leaf absolute {
                  type string;
                }
              }
            }
            list outter {
              key "index";
              leaf index {
                type uint8;
              }
              min-elements 2;
              max-elements 3;
              list inner {
                key "name";
                leaf name {
                  type string;
                }
                max-elements 2;
                leaf value {
                  type uint16;
                }
              }
              leaf-list boolean-leaf-list {
                type boolean;
                max-elements 3;
                min-elements 2;
              }
              leaf mode {
                type uint8 {
                  range "0..10";
                }
              }
            }
            list first {
              key "key1 key2";
              leaf key1 {
                type uint8;
              }
              leaf key2 {
                type string;
              }
              list second {
                key "key1 key2";
                leaf key1 {
                  type uint8;
                }
                leaf key2 {
                  type string;
                }
                list third {
                  key "key1";
                  leaf key1 {
                    type uint8;
                  }
                  container red {
                    container blue {
                      leaf a {
                        type string;
                      }
                      leaf b {
                        type string;
                      }
                    }
                    leaf yellow-leaf {
                      type string;
                    }
                    anyxml config;
                  }
                }
              }
            }
          }
          container list-keys {
            list bits-key {
              key "bit";
              leaf bit {
                type bits {
                  bit x;
                  bit y;
                  bit z;
                }
              }
            }
          }
          container identity-test {
            leaf base-test {
              type identityref {
                base test:crypto-alg;
              }
            }
            leaf mid-level-test {
              type identityref {
                base test:des;
              }
            }
            leaf top-test {
              type identityref {
                base test:des3;
              }
            }
            leaf external-test {
              type identityref {
                base ciena-common-yang:error-does-not-exist;
              }
            }
          }
          container encryption-test-container {
            container container-generate-at-abs-path-enc {
              ciena-common-yang:decrypt "container-generate-at-abs-path";
              ciena-common-yang:decrypt-path "/ciena-common-test/encryption-test-container";
              leaf a {
                type string {
                  ciena-common-yang:stringptr "true";
                }
                ciena-common-yang:decrypt "a";
                ciena-common-yang:decrypt-path "/ciena-common-test/encryption-test-container/container-generate-at-abs-path";
              }
              container b {
                ciena-common-yang:decrypt "b";
                ciena-common-yang:decrypt-path "/ciena-common-test/encryption-test-container/container-generate-at-abs-path";
                leaf c {
                  type string {
                    ciena-common-yang:stringptr "true";
                  }
                  ciena-common-yang:decrypt "c";
                  ciena-common-yang:decrypt-path "/ciena-common-test/encryption-test-container/container-generate-at-abs-path/b";
                }
              }
              config false;
            }
            list encryption-mount-test {
              key "name";
              leaf name {
                type string;
              }
              container data {
                ciena-common-yang:mount-start "ciena-common-test";
                ciena-common-yang:mount-end "ciena-common-test";
              }
            }
            list instance {
              key "name";
              leaf name {
                type string;
              }
              container result {
                ciena-common-yang:encrypt "container-1";
                ciena-common-yang:encrypt-path "/ciena-common-test/encryption-test-container/instance";
                list amp {
                  ciena-common-yang:encrypt "amp";
                  ciena-common-yang:encrypt-path "/ciena-common-test/encryption-test-container/instance/container-1";
                  key "amp_name";
                  leaf amp_name {
                    ciena-common-yang:encrypt "amp_name";
                    ciena-common-yang:encrypt-path "/ciena-common-test/encryption-test-container/instance/container-1/amp";
                    type string;
                  }
                  list measurement-no-power {
                    ciena-common-yang:encrypt "measurement-no-power";
                    ciena-common-yang:encrypt-path "/ciena-common-test/encryption-test-container/instance/container-1/amp";
                    description
                      "Power measurements of span measured with all channels blocked.";
                    key "index";
                    leaf index {
                      ciena-common-yang:encrypt "index";
                      ciena-common-yang:encrypt-path "/ciena-common-test/encryption-test-container/instance/container-1/amp/measurement-no-power";
                      type uint8;
                    }
                    leaf in-current-power {
                      ciena-common-yang:encrypt "in-current-power";
                      ciena-common-yang:encrypt-path "/ciena-common-test/encryption-test-container/instance/container-1/amp/measurement-no-power";
                      type decimal64 {
                        fraction-digits 1;
                      }
                    }
                    leaf in-min-power {
                      ciena-common-yang:encrypt "in-min-power";
                      ciena-common-yang:encrypt-path "/ciena-common-test/encryption-test-container/instance/container-1/amp/measurement-no-power";
                      type decimal64 {
                        fraction-digits 1;
                      }
                    }
                    config false;
                  }
                }
              }
              container container-1 {
                ciena-common-yang:decrypt "result";
                ciena-common-yang:decrypt-path "/ciena-common-test/encryption-test-container/instance";
                list amp {
                  ciena-common-yang:decrypt "amp";
                  ciena-common-yang:decrypt-path "/ciena-common-test/encryption-test-container/instance/result";
                  key "amp_name";
                  leaf amp_name {
                    type string {
                      ciena-common-yang:stringptr "true";
                    }
                    ciena-common-yang:decrypt "amp_name";
                    ciena-common-yang:decrypt-path "/ciena-common-test/encryption-test-container/instance/result/amp";
                  }
                  list measurement-no-power {
                    ciena-common-yang:decrypt "measurement-no-power";
                    ciena-common-yang:decrypt-path "/ciena-common-test/encryption-test-container/instance/result/amp";
                    key "index";
                    leaf index {
                      type string {
                        ciena-common-yang:stringptr "true";
                      }
                      ciena-common-yang:decrypt "index";
                      ciena-common-yang:decrypt-path "/ciena-common-test/encryption-test-container/instance/result/amp/measurement-no-power";
                    }
                    leaf in-current-power {
                      type string {
                        ciena-common-yang:stringptr "true";
                      }
                      ciena-common-yang:decrypt "in-current-power";
                      ciena-common-yang:decrypt-path "/ciena-common-test/encryption-test-container/instance/result/amp/measurement-no-power";
                    }
                    leaf in-min-power {
                      type string {
                        ciena-common-yang:stringptr "true";
                      }
                      ciena-common-yang:decrypt "in-min-power";
                      ciena-common-yang:decrypt-path "/ciena-common-test/encryption-test-container/instance/result/amp/measurement-no-power";
                    }
                    config false;
                  }
                }
              }
              list some-other-list {
                key "name";
                leaf name {
                  type string;
                }
                leaf measurement {
                  type uint8;
                }
              }
            }
            list key-in-grouping {
              ciena-common-yang:encrypt "key-in-grouping-encrypted";
              ciena-common-yang:encrypt-path "/ciena-common-test/encryption-test-container";
              description
                "test list key leaf definition can be provided by grouping";
              key "name";
              leaf name {
                ciena-common-yang:encrypt "name";
                ciena-common-yang:encrypt-path "/ciena-common-test/encryption-test-container/key-in-grouping-encrypted";
                type string;
              }
              leaf stats {
                ciena-common-yang:encrypt "stats";
                ciena-common-yang:encrypt-path "/ciena-common-test/encryption-test-container/key-in-grouping-encrypted";
                type uint32;
              }
            }
            list key-in-grouping-encrypted {
              ciena-common-yang:decrypt "key-in-grouping";
              ciena-common-yang:decrypt-path "/ciena-common-test/encryption-test-container";
              key "name";
              leaf name {
                type string {
                  ciena-common-yang:stringptr "true";
                }
                ciena-common-yang:decrypt "name";
                ciena-common-yang:decrypt-path "/ciena-common-test/encryption-test-container/key-in-grouping";
              }
              leaf stats {
                type string {
                  ciena-common-yang:stringptr "true";
                }
                ciena-common-yang:decrypt "stats";
                ciena-common-yang:decrypt-path "/ciena-common-test/encryption-test-container/key-in-grouping";
              }
            }
            list list-enc-generate-with-renamed-leaves {
              ciena-common-yang:encrypt "list-enc-generate-with-renamed-leaves-enc";
              ciena-common-yang:encrypt-path "/ciena-common-test/encryption-test-container";
              description
                "test list encryption with nested containers and leaves renamed";
              key "name";
              leaf name {
                ciena-common-yang:encrypt "name";
                ciena-common-yang:encrypt-path "/ciena-common-test/encryption-test-container/list-enc-generate-with-renamed-leaves-enc";
                type string;
              }
              leaf aaa {
                ciena-common-yang:encrypt "aaa-enc";
                ciena-common-yang:encrypt-path "/ciena-common-test/encryption-test-container/list-enc-generate-with-renamed-leaves-enc";
                type uint8;
                ciena-common-yang:sensitive "true";
              }
              container ddd {
                ciena-common-yang:encrypt "ddd-enc";
                ciena-common-yang:encrypt-path "/ciena-common-test/encryption-test-container/list-enc-generate-with-renamed-leaves-enc";
                leaf eee {
                  ciena-common-yang:encrypt "eee-enc";
                  ciena-common-yang:encrypt-path "/ciena-common-test/encryption-test-container/list-enc-generate-with-renamed-leaves-enc/ddd-enc";
                  type uint8;
                }
                leaf fff {
                  ciena-common-yang:encrypt "fff";
                  ciena-common-yang:encrypt-path "/ciena-common-test/encryption-test-container/list-enc-generate-with-renamed-leaves-enc/ddd-enc";
                  type uint8;
                }
                config false;
              }
            }
            list list-enc-generate-with-renamed-leaves-enc {
              ciena-common-yang:decrypt "list-enc-generate-with-renamed-leaves";
              ciena-common-yang:decrypt-path "/ciena-common-test/encryption-test-container";
              key "name";
              leaf name {
                type string {
                  ciena-common-yang:stringptr "true";
                }
                ciena-common-yang:decrypt "name";
                ciena-common-yang:decrypt-path "/ciena-common-test/encryption-test-container/list-enc-generate-with-renamed-leaves";
              }
              leaf aaa-enc {
                type string {
                  ciena-common-yang:stringptr "true";
                }
                ciena-common-yang:decrypt "aaa";
                ciena-common-yang:decrypt-path "/ciena-common-test/encryption-test-container/list-enc-generate-with-renamed-leaves";
                ciena-common-yang:sensitive "true";
              }
              container ddd-enc {
                ciena-common-yang:decrypt "ddd";
                ciena-common-yang:decrypt-path "/ciena-common-test/encryption-test-container/list-enc-generate-with-renamed-leaves";
                leaf eee-enc {
                  type string {
                    ciena-common-yang:stringptr "true";
                  }
                  ciena-common-yang:decrypt "eee";
                  ciena-common-yang:decrypt-path "/ciena-common-test/encryption-test-container/list-enc-generate-with-renamed-leaves/ddd";
                }
                leaf fff {
                  type string {
                    ciena-common-yang:stringptr "true";
                  }
                  ciena-common-yang:decrypt "fff";
                  ciena-common-yang:decrypt-path "/ciena-common-test/encryption-test-container/list-enc-generate-with-renamed-leaves/ddd";
                }
                config false;
              }
            }
            list list-generate-with-enc-path-for-leaves {
              ciena-common-yang:encrypt "list-generate-with-enc-path-for-leaves-enc";
              ciena-common-yang:encrypt-path "/ciena-common-test/encryption-test-container";
              description
                "test list encryption with some leaves having encryption-path and encryption-relative-path information";
              key "index";
              leaf index {
                ciena-common-yang:encrypt "index-enc";
                ciena-common-yang:encrypt-path "/ciena-common-test/encryption-test-container/list-generate-with-enc-path-for-leaves-enc";
                type uint8;
              }
              leaf ggg {
                ciena-common-yang:encrypt "ggg";
                ciena-common-yang:encrypt-path "/ciena-common-test/encryption-test-container/list-generate-with-enc-path-for-leaves-enc";
                type uint8;
              }
              container hhh {
                ciena-common-yang:encrypt "hhh";
                ciena-common-yang:encrypt-path "/ciena-common-test/encryption-test-container/list-generate-with-enc-path-for-leaves-enc";
                leaf iii {
                  ciena-common-yang:encrypt "iii-enc";
                  ciena-common-yang:encrypt-path "/ciena-common-test/encryption-test-container/list-generate-with-enc-path-for-leaves-enc/hhh";
                  type uint8;
                }
                leaf jjj {
                  ciena-common-yang:encrypt "none-existing-leaf";
                  ciena-common-yang:encrypt-path "/ciena-common-test/encryption-test-container/A/B";
                  type uint8;
                  ciena-common-yang:sensitive "true";
                }
                leaf kkk {
                  ciena-common-yang:encrypt "none-existing-leaf-2";
                  ciena-common-yang:encrypt-path "/ciena-common-test/encryption-test-container/A/B";
                  type uint8;
                  config false;
                  ciena-common-yang:sensitive "true";
                }
              }
            }
            list list-generate-with-enc-path-for-leaves-enc {
              ciena-common-yang:decrypt "list-generate-with-enc-path-for-leaves";
              ciena-common-yang:decrypt-path "/ciena-common-test/encryption-test-container";
              key "index-enc";
              leaf index-enc {
                type string {
                  ciena-common-yang:stringptr "true";
                }
                ciena-common-yang:decrypt "index";
                ciena-common-yang:decrypt-path "/ciena-common-test/encryption-test-container/list-generate-with-enc-path-for-leaves";
              }
              leaf ggg {
                type string {
                  ciena-common-yang:stringptr "true";
                }
                ciena-common-yang:decrypt "ggg";
                ciena-common-yang:decrypt-path "/ciena-common-test/encryption-test-container/list-generate-with-enc-path-for-leaves";
              }
              container hhh {
                ciena-common-yang:decrypt "hhh";
                ciena-common-yang:decrypt-path "/ciena-common-test/encryption-test-container/list-generate-with-enc-path-for-leaves";
                leaf iii-enc {
                  type string {
                    ciena-common-yang:stringptr "true";
                  }
                  ciena-common-yang:decrypt "iii";
                  ciena-common-yang:decrypt-path "/ciena-common-test/encryption-test-container/list-generate-with-enc-path-for-leaves/hhh";
                }
              }
            }
            container A {
              container B {
                leaf none-existing-leaf {
                  ciena-common-yang:decrypt "jjj";
                  ciena-common-yang:decrypt-path "/ciena-common-test/encryption-test-container/list-generate-with-enc-path-for-leaves/hhh";
                  type string {
                    ciena-common-yang:stringptr "true";
                  }
                  ciena-common-yang:sensitive "true";
                }
                leaf none-existing-leaf-2 {
                  ciena-common-yang:decrypt "kkk";
                  ciena-common-yang:decrypt-path "/ciena-common-test/encryption-test-container/list-generate-with-enc-path-for-leaves/hhh";
                  type string {
                    ciena-common-yang:stringptr "true";
                  }
                  ciena-common-yang:sensitive "true";
                  config false;
                }
                leaf y {
                  type string {
                    ciena-common-yang:stringptr "true";
                  }
                }
                leaf z {
                  type uint8;
                }
              }
            }
            container container-generate-as-sibling {
              ciena-common-yang:encrypt "container-generate-as-sibling-enc";
              ciena-common-yang:encrypt-path "/ciena-common-test/encryption-test-container";
              description
                "test simple container encryption default generating as siblings";
              leaf a {
                ciena-common-yang:encrypt "a";
                ciena-common-yang:encrypt-path "/ciena-common-test/encryption-test-container/container-generate-as-sibling-enc";
                type uint8;
              }
              container b {
                ciena-common-yang:encrypt "b";
                ciena-common-yang:encrypt-path "/ciena-common-test/encryption-test-container/container-generate-as-sibling-enc";
                leaf c {
                  ciena-common-yang:encrypt "c";
                  ciena-common-yang:encrypt-path "/ciena-common-test/encryption-test-container/container-generate-as-sibling-enc/b";
                  type uint8;
                }
              }
            }
            container container-generate-as-sibling-enc {
              ciena-common-yang:decrypt "container-generate-as-sibling";
              ciena-common-yang:decrypt-path "/ciena-common-test/encryption-test-container";
              leaf a {
                type string {
                  ciena-common-yang:stringptr "true";
                }
                ciena-common-yang:decrypt "a";
                ciena-common-yang:decrypt-path "/ciena-common-test/encryption-test-container/container-generate-as-sibling";
              }
              container b {
                ciena-common-yang:decrypt "b";
                ciena-common-yang:decrypt-path "/ciena-common-test/encryption-test-container/container-generate-as-sibling";
                leaf c {
                  type string {
                    ciena-common-yang:stringptr "true";
                  }
                  ciena-common-yang:decrypt "c";
                  ciena-common-yang:decrypt-path "/ciena-common-test/encryption-test-container/container-generate-as-sibling/b";
                }
              }
            }
            container X {
              container Z {
                container container-generate-at-relative-path {
                  ciena-common-yang:encrypt "container-generate-at-relative-path-enc";
                  ciena-common-yang:encrypt-path "/ciena-common-test/encryption-test-container/K";
                  description
                    "test container encryption with encrypt-relative-path information";
                  container red {
                    ciena-common-yang:encrypt "red";
                    ciena-common-yang:encrypt-path "/ciena-common-test/encryption-test-container/K/container-generate-at-relative-path-enc";
                    container blue {
                      ciena-common-yang:encrypt "blue";
                      ciena-common-yang:encrypt-path "/ciena-common-test/encryption-test-container/K/container-generate-at-relative-path-enc/red";
                      leaf a {
                        ciena-common-yang:encrypt "a";
                        ciena-common-yang:encrypt-path "/ciena-common-test/encryption-test-container/K/container-generate-at-relative-path-enc/red/blue";
                        type uint8;
                      }
                      leaf b {
                        ciena-common-yang:encrypt "b";
                        ciena-common-yang:encrypt-path "/ciena-common-test/encryption-test-container/K/container-generate-at-relative-path-enc/red/blue";
                        type uint8;
                        default "22";
                      }
                      leaf c {
                        ciena-common-yang:encrypt "c";
                        ciena-common-yang:encrypt-path "/ciena-common-test/encryption-test-container/K/container-generate-at-relative-path-enc/red/blue";
                        type uint8;
                        default "44";
                      }
                      leaf d {
                        ciena-common-yang:encrypt "d";
                        ciena-common-yang:encrypt-path "/ciena-common-test/encryption-test-container/K/container-generate-at-relative-path-enc/red/blue";
                        type uint8;
                        default "88";
                      }
                    }
                  }
                  leaf a {
                    ciena-common-yang:encrypt "a";
                    ciena-common-yang:encrypt-path "/ciena-common-test/encryption-test-container/K/container-generate-at-relative-path-enc";
                    type uint8;
                  }
                  container b {
                    ciena-common-yang:encrypt "b";
                    ciena-common-yang:encrypt-path "/ciena-common-test/encryption-test-container/K/container-generate-at-relative-path-enc";
                    container red {
                      ciena-common-yang:encrypt "red";
                      ciena-common-yang:encrypt-path "/ciena-common-test/encryption-test-container/K/container-generate-at-relative-path-enc/b";
                      container blue {
                        ciena-common-yang:encrypt "blue";
                        ciena-common-yang:encrypt-path "/ciena-common-test/encryption-test-container/K/container-generate-at-relative-path-enc/b/red";
                        leaf a {
                          ciena-common-yang:encrypt "a";
                          ciena-common-yang:encrypt-path "/ciena-common-test/encryption-test-container/K/container-generate-at-relative-path-enc/b/red/blue";
                          type uint8;
                        }
                        leaf b {
                          ciena-common-yang:encrypt "b";
                          ciena-common-yang:encrypt-path "/ciena-common-test/encryption-test-container/K/container-generate-at-relative-path-enc/b/red/blue";
                          type uint8;
                          default "22";
                        }
                        leaf c {
                          ciena-common-yang:encrypt "c";
                          ciena-common-yang:encrypt-path "/ciena-common-test/encryption-test-container/K/container-generate-at-relative-path-enc/b/red/blue";
                          type uint8;
                          default "44";
                        }
                        leaf d {
                          ciena-common-yang:encrypt "d";
                          ciena-common-yang:encrypt-path "/ciena-common-test/encryption-test-container/K/container-generate-at-relative-path-enc/b/red/blue";
                          type uint8;
                          default "88";
                        }
                      }
                    }
                    leaf c {
                      ciena-common-yang:encrypt "c";
                      ciena-common-yang:encrypt-path "/ciena-common-test/encryption-test-container/K/container-generate-at-relative-path-enc/b";
                      type uint8;
                    }
                  }
                  config false;
                }
              }
            }
            container K {
              container container-generate-at-relative-path-enc {
                ciena-common-yang:decrypt "container-generate-at-relative-path";
                ciena-common-yang:decrypt-path "/ciena-common-test/encryption-test-container/X/Z";
                container red {
                  ciena-common-yang:decrypt "red";
                  ciena-common-yang:decrypt-path "/ciena-common-test/encryption-test-container/X/Z/container-generate-at-relative-path";
                  container blue {
                    ciena-common-yang:decrypt "blue";
                    ciena-common-yang:decrypt-path "/ciena-common-test/encryption-test-container/X/Z/container-generate-at-relative-path/red";
                    leaf a {
                      type string {
                        ciena-common-yang:stringptr "true";
                      }
                      ciena-common-yang:decrypt "a";
                      ciena-common-yang:decrypt-path "/ciena-common-test/encryption-test-container/X/Z/container-generate-at-relative-path/red/blue";
                    }
                    leaf b {
                      type string {
                        ciena-common-yang:stringptr "true";
                      }
                      ciena-common-yang:decrypt "b";
                      ciena-common-yang:decrypt-path "/ciena-common-test/encryption-test-container/X/Z/container-generate-at-relative-path/red/blue";
                    }
                    leaf c {
                      type string {
                        ciena-common-yang:stringptr "true";
                      }
                      ciena-common-yang:decrypt "c";
                      ciena-common-yang:decrypt-path "/ciena-common-test/encryption-test-container/X/Z/container-generate-at-relative-path/red/blue";
                    }
                    leaf d {
                      type string {
                        ciena-common-yang:stringptr "true";
                      }
                      ciena-common-yang:decrypt "d";
                      ciena-common-yang:decrypt-path "/ciena-common-test/encryption-test-container/X/Z/container-generate-at-relative-path/red/blue";
                    }
                  }
                }
                leaf a {
                  type string {
                    ciena-common-yang:stringptr "true";
                  }
                  ciena-common-yang:decrypt "a";
                  ciena-common-yang:decrypt-path "/ciena-common-test/encryption-test-container/X/Z/container-generate-at-relative-path";
                }
                container b {
                  ciena-common-yang:decrypt "b";
                  ciena-common-yang:decrypt-path "/ciena-common-test/encryption-test-container/X/Z/container-generate-at-relative-path";
                  container red {
                    ciena-common-yang:decrypt "red";
                    ciena-common-yang:decrypt-path "/ciena-common-test/encryption-test-container/X/Z/container-generate-at-relative-path/b";
                    container blue {
                      ciena-common-yang:decrypt "blue";
                      ciena-common-yang:decrypt-path "/ciena-common-test/encryption-test-container/X/Z/container-generate-at-relative-path/b/red";
                      leaf a {
                        type string {
                          ciena-common-yang:stringptr "true";
                        }
                        ciena-common-yang:decrypt "a";
                        ciena-common-yang:decrypt-path "/ciena-common-test/encryption-test-container/X/Z/container-generate-at-relative-path/b/red/blue";
                      }
                      leaf b {
                        type string {
                          ciena-common-yang:stringptr "true";
                        }
                        ciena-common-yang:decrypt "b";
                        ciena-common-yang:decrypt-path "/ciena-common-test/encryption-test-container/X/Z/container-generate-at-relative-path/b/red/blue";
                      }
                      leaf c {
                        type string {
                          ciena-common-yang:stringptr "true";
                        }
                        ciena-common-yang:decrypt "c";
                        ciena-common-yang:decrypt-path "/ciena-common-test/encryption-test-container/X/Z/container-generate-at-relative-path/b/red/blue";
                      }
                      leaf d {
                        type string {
                          ciena-common-yang:stringptr "true";
                        }
                        ciena-common-yang:decrypt "d";
                        ciena-common-yang:decrypt-path "/ciena-common-test/encryption-test-container/X/Z/container-generate-at-relative-path/b/red/blue";
                      }
                    }
                  }
                  leaf c {
                    type string {
                      ciena-common-yang:stringptr "true";
                    }
                    ciena-common-yang:decrypt "c";
                    ciena-common-yang:decrypt-path "/ciena-common-test/encryption-test-container/X/Z/container-generate-at-relative-path/b";
                  }
                }
                config false;
              }
              leaf l {
                type uint8;
              }
            }
            container container-generate-at-abs-path {
              ciena-common-yang:encrypt "container-generate-at-abs-path-enc";
              ciena-common-yang:encrypt-path "/ciena-common-test/encryption-test-container";
              description
                "test container encryption with absolute path encrypt-path information";
              leaf a {
                ciena-common-yang:encrypt "a";
                ciena-common-yang:encrypt-path "/ciena-common-test/encryption-test-container/container-generate-at-abs-path-enc";
                type uint8;
              }
              container b {
                ciena-common-yang:encrypt "b";
                ciena-common-yang:encrypt-path "/ciena-common-test/encryption-test-container/container-generate-at-abs-path-enc";
                leaf c {
                  ciena-common-yang:encrypt "c";
                  ciena-common-yang:encrypt-path "/ciena-common-test/encryption-test-container/container-generate-at-abs-path-enc/b";
                  type uint8;
                }
              }
              config false;
            }
            container encrypt-to-existing-container {
              ciena-common-yang:encrypt "encrypt-to-existing-container-encrypted";
              ciena-common-yang:encrypt-path "/ciena-common-test/encryption-test-container";
              description
                "test container encryption to existing container. no generation will happen.";
              leaf a {
                ciena-common-yang:encrypt "a";
                ciena-common-yang:encrypt-path "/ciena-common-test/encryption-test-container/encrypt-to-existing-container-encrypted";
                type uint8;
              }
            }
            container encrypt-to-existing-container-encrypted {
              ciena-common-yang:decrypt "encrypt-to-existing-container";
              ciena-common-yang:decrypt-path "/ciena-common-test/encryption-test-container";
              leaf a {
                ciena-common-yang:decrypt "a";
                ciena-common-yang:decrypt-path "/ciena-common-test/encryption-test-container/encrypt-to-existing-container";
                type string {
                  ciena-common-yang:stringptr "true";
                }
              }
            }
            container outter-container {
              ciena-common-yang:encrypt "outter-container-enc";
              ciena-common-yang:encrypt-path "/ciena-common-test/encryption-test-container";
              description
                "simple nested container test";
              leaf aaa {
                ciena-common-yang:encrypt "aaa";
                ciena-common-yang:encrypt-path "/ciena-common-test/encryption-test-container/outter-container-enc";
                type uint8;
              }
              container middle-container {
                ciena-common-yang:encrypt "middle-container";
                ciena-common-yang:encrypt-path "/ciena-common-test/encryption-test-container/outter-container-enc";
                leaf bbb {
                  ciena-common-yang:encrypt "bbb";
                  ciena-common-yang:encrypt-path "/ciena-common-test/encryption-test-container/outter-container-enc/middle-container";
                  type uint8;
                }
                container inner-container {
                  ciena-common-yang:encrypt "inner-container";
                  ciena-common-yang:encrypt-path "/ciena-common-test/encryption-test-container/outter-container-enc/middle-container";
                  leaf ccc {
                    ciena-common-yang:encrypt "ccc";
                    ciena-common-yang:encrypt-path "/ciena-common-test/encryption-test-container/outter-container-enc/middle-container/inner-container";
                    type uint8;
                  }
                }
              }
            }
            container outter-container-enc {
              ciena-common-yang:decrypt "outter-container";
              ciena-common-yang:decrypt-path "/ciena-common-test/encryption-test-container";
              leaf aaa {
                type string {
                  ciena-common-yang:stringptr "true";
                }
                ciena-common-yang:decrypt "aaa";
                ciena-common-yang:decrypt-path "/ciena-common-test/encryption-test-container/outter-container";
              }
              container middle-container {
                ciena-common-yang:decrypt "middle-container";
                ciena-common-yang:decrypt-path "/ciena-common-test/encryption-test-container/outter-container";
                leaf bbb {
                  type string {
                    ciena-common-yang:stringptr "true";
                  }
                  ciena-common-yang:decrypt "bbb";
                  ciena-common-yang:decrypt-path "/ciena-common-test/encryption-test-container/outter-container/middle-container";
                }
                container inner-container {
                  ciena-common-yang:decrypt "inner-container";
                  ciena-common-yang:decrypt-path "/ciena-common-test/encryption-test-container/outter-container/middle-container";
                  leaf ccc {
                    type string {
                      ciena-common-yang:stringptr "true";
                    }
                    ciena-common-yang:decrypt "ccc";
                    ciena-common-yang:decrypt-path "/ciena-common-test/encryption-test-container/outter-container/middle-container/inner-container";
                  }
                }
              }
            }
            container one-to-two-container {
              ciena-common-yang:encrypt "one-to-two-container-enc";
              ciena-common-yang:encrypt-path "/ciena-common-test/encryption-test-container";
              description
                "error scenario test: leaves under one container encrypted to two containers
                 is not fully supported, the leaves for one container will be missing";
              leaf aaa {
                ciena-common-yang:encrypt "aaa";
                ciena-common-yang:encrypt-path "/ciena-common-test/encryption-test-container/one-to-two-container-enc";
                type uint8;
              }
              leaf-list bbb {
                ciena-common-yang:encrypt "bbb";
                ciena-common-yang:encrypt-path "/ciena-common-test/encryption-test-container/one-to-two-container-other";
                type uint8;
              }
              container inner-container {
                ciena-common-yang:encrypt "inner-container";
                ciena-common-yang:encrypt-path "/ciena-common-test/encryption-test-container/one-to-two-container-enc";
                leaf-list ccc {
                  ciena-common-yang:encrypt "ccc";
                  ciena-common-yang:encrypt-path "/ciena-common-test/encryption-test-container/one-to-two-container-enc/inner-container";
                  type uint8;
                }
                leaf ddd {
                  ciena-common-yang:encrypt "ddd";
                  ciena-common-yang:encrypt-path "/ciena-common-test/encryption-test-container/one-to-two-container-other";
                  type uint8;
                }
              }
            }
            container one-to-two-container-enc {
              ciena-common-yang:decrypt "one-to-two-container";
              ciena-common-yang:decrypt-path "/ciena-common-test/encryption-test-container";
              leaf aaa {
                type string {
                  ciena-common-yang:stringptr "true";
                }
                ciena-common-yang:decrypt "aaa";
                ciena-common-yang:decrypt-path "/ciena-common-test/encryption-test-container/one-to-two-container";
              }
              container inner-container {
                ciena-common-yang:decrypt "inner-container";
                ciena-common-yang:decrypt-path "/ciena-common-test/encryption-test-container/one-to-two-container";
                leaf-list ccc {
                  type string {
                    ciena-common-yang:stringptr "true";
                  }
                  ciena-common-yang:decrypt "ccc";
                  ciena-common-yang:decrypt-path "/ciena-common-test/encryption-test-container/one-to-two-container/inner-container";
                }
              }
            }
            container one-to-two-container-other {
              leaf-list bbb {
                ciena-common-yang:decrypt "bbb";
                ciena-common-yang:decrypt-path "/ciena-common-test/encryption-test-container/one-to-two-container";
                type string {
                  ciena-common-yang:stringptr "true";
                }
              }
              leaf ddd {
                ciena-common-yang:decrypt "ddd";
                ciena-common-yang:decrypt-path "/ciena-common-test/encryption-test-container/one-to-two-container/inner-container";
                type string {
                  ciena-common-yang:stringptr "true";
                }
              }
              leaf fff {
                type uint8;
              }
            }
            list nested-list {
              ciena-common-yang:encrypt "nested-list-enc";
              ciena-common-yang:encrypt-path "/ciena-common-test/encryption-test-container";
              description
                "test nested list encryption";
              key "name";
              leaf name {
                ciena-common-yang:encrypt "name";
                ciena-common-yang:encrypt-path "/ciena-common-test/encryption-test-container/nested-list-enc";
                type stringptr;
              }
              leaf aaa {
                ciena-common-yang:encrypt "aaa";
                ciena-common-yang:encrypt-path "/ciena-common-test/encryption-test-container/nested-list-enc";
                type uint8;
              }
              list inner-list {
                ciena-common-yang:encrypt "inner-list";
                ciena-common-yang:encrypt-path "/ciena-common-test/encryption-test-container/nested-list-enc";
                key "index";
                leaf index {
                  ciena-common-yang:encrypt "index";
                  ciena-common-yang:encrypt-path "/ciena-common-test/encryption-test-container/nested-list-enc/inner-list";
                  type uint8;
                }
                leaf-list ccc {
                  ciena-common-yang:encrypt "ccc";
                  ciena-common-yang:encrypt-path "/ciena-common-test/encryption-test-container/nested-list-enc/inner-list";
                  type string;
                }
              }
            }
            list nested-list-enc {
              ciena-common-yang:decrypt "nested-list";
              ciena-common-yang:decrypt-path "/ciena-common-test/encryption-test-container";
              key "name";
              leaf name {
                type string {
                  ciena-common-yang:stringptr "true";
                }
                ciena-common-yang:decrypt "name";
                ciena-common-yang:decrypt-path "/ciena-common-test/encryption-test-container/nested-list";
              }
              leaf aaa {
                type string {
                  ciena-common-yang:stringptr "true";
                }
                ciena-common-yang:decrypt "aaa";
                ciena-common-yang:decrypt-path "/ciena-common-test/encryption-test-container/nested-list";
              }
              list inner-list {
                ciena-common-yang:decrypt "inner-list";
                ciena-common-yang:decrypt-path "/ciena-common-test/encryption-test-container/nested-list";
                key "index";
                leaf index {
                  type string {
                    ciena-common-yang:stringptr "true";
                  }
                  ciena-common-yang:decrypt "index";
                  ciena-common-yang:decrypt-path "/ciena-common-test/encryption-test-container/nested-list/inner-list";
                }
                leaf-list ccc {
                  type string {
                    ciena-common-yang:stringptr "true";
                  }
                  ciena-common-yang:decrypt "ccc";
                  ciena-common-yang:decrypt-path "/ciena-common-test/encryption-test-container/nested-list/inner-list";
                }
              }
            }
            container other {
              leaf ccc {
                type string;
              }
            }
            container user-defined-leaves {
              description
                "selected leaves encryption container";
              leaf a {
                ciena-common-yang:encrypt "x";
                ciena-common-yang:encrypt-path "/ciena-common-test/encryption-test-container/user-defined-leaves-encrypted";
                type string;
              }
              leaf b {
                type string;
              }
            }
            container user-defined-leaves-encrypted {
              leaf x {
                ciena-common-yang:decrypt "a";
                ciena-common-yang:decrypt-path "/ciena-common-test/encryption-test-container/user-defined-leaves";
                type string;
              }
            }
            list nested-list-leaf-encryption {
              key "name";
              leaf name {
                type string;
              }
              leaf x {
                ciena-common-yang:encrypt "x-enc";
                ciena-common-yang:encrypt-path "/ciena-common-test/encryption-test-container/nested-list-leaf-encryption";
                type string;
              }
              leaf x-enc {
                type string {
                  ciena-common-yang:stringptr "true";
                }
                ciena-common-yang:decrypt "x";
                ciena-common-yang:decrypt-path "/ciena-common-test/encryption-test-container/nested-list-leaf-encryption";
              }
              list inner {
                key "index";
                leaf index {
                  type uint8;
                }
                leaf u {
                  ciena-common-yang:encrypt "u-enc";
                  ciena-common-yang:encrypt-path "/ciena-common-test/encryption-test-container/nested-list-leaf-encryption/inner";
                  type string;
                }
                leaf u-enc {
                  type string {
                    ciena-common-yang:stringptr "true";
                  }
                  ciena-common-yang:decrypt "u";
                  ciena-common-yang:decrypt-path "/ciena-common-test/encryption-test-container/nested-list-leaf-encryption/inner";
                }
              }
            }
            list encryption-list-test {
              key "key1 key2";
              leaf key1 {
                type stringptr;
              }
              leaf key2 {
                type typetest;
              }
              container leaf-list-test {
                leaf-list binary-test {
                  ciena-common-yang:encrypt "binary-test-encrypted";
                  ciena-common-yang:encrypt-path "/ciena-common-test/encryption-test-container/encryption-list-test/leaf-list-test";
                  type binary;
                }
                leaf-list binary-test-encrypted {
                  type string {
                    ciena-common-yang:stringptr "true";
                  }
                  ciena-common-yang:decrypt "binary-test";
                  ciena-common-yang:decrypt-path "/ciena-common-test/encryption-test-container/encryption-list-test/leaf-list-test";
                }
                leaf-list bits-test {
                  ciena-common-yang:encrypt "bits-test-encrypted";
                  ciena-common-yang:encrypt-path "/ciena-common-test/encryption-test-container/encryption-list-test/leaf-list-test";
                  type bits {
                    bit disable-nagle {
                      position 0;
                    }
                    bit auto-sense-speed {
                      position 1;
                    }
                  }
                }
                leaf-list bits-test-encrypted {
                  type string {
                    ciena-common-yang:stringptr "true";
                  }
                  ciena-common-yang:decrypt "bits-test";
                  ciena-common-yang:decrypt-path "/ciena-common-test/encryption-test-container/encryption-list-test/leaf-list-test";
                }
                leaf-list boolean-test {
                  ciena-common-yang:encrypt "boolean-test-encrypted";
                  ciena-common-yang:encrypt-path "/ciena-common-test/encryption-test-container/encryption-list-test/leaf-list-test";
                  type boolean;
                }
                leaf-list boolean-test-encrypted {
                  type string {
                    ciena-common-yang:stringptr "true";
                  }
                  ciena-common-yang:decrypt "boolean-test";
                  ciena-common-yang:decrypt-path "/ciena-common-test/encryption-test-container/encryption-list-test/leaf-list-test";
                }
                leaf-list decimal64-test {
                  ciena-common-yang:encrypt "decimal64-test-encrypted";
                  ciena-common-yang:encrypt-path "/ciena-common-test/encryption-test-container/encryption-list-test/leaf-list-test";
                  type decimal64 {
                    fraction-digits 10;
                  }
                }
                leaf-list decimal64-test-encrypted {
                  type string {
                    ciena-common-yang:stringptr "true";
                  }
                  ciena-common-yang:decrypt "decimal64-test";
                  ciena-common-yang:decrypt-path "/ciena-common-test/encryption-test-container/encryption-list-test/leaf-list-test";
                }
                leaf-list empty-test {
                  ciena-common-yang:encrypt "empty-test-encrypted";
                  ciena-common-yang:encrypt-path "/ciena-common-test/encryption-test-container/encryption-list-test/leaf-list-test";
                  type empty;
                }
                leaf-list empty-test-encrypted {
                  type string {
                    ciena-common-yang:stringptr "true";
                  }
                  ciena-common-yang:decrypt "empty-test";
                  ciena-common-yang:decrypt-path "/ciena-common-test/encryption-test-container/encryption-list-test/leaf-list-test";
                }
                leaf-list enumeration-test {
                  ciena-common-yang:encrypt "enumeration-test-encrypted";
                  ciena-common-yang:encrypt-path "/ciena-common-test/encryption-test-container/encryption-list-test/leaf-list-test";
                  type enumeration {
                    enum test-a;
                    enum test-b;
                    enum test-c;
                    enum map;
                  }
                }
                leaf-list enumeration-test-encrypted {
                  type string {
                    ciena-common-yang:stringptr "true";
                  }
                  ciena-common-yang:decrypt "enumeration-test";
                  ciena-common-yang:decrypt-path "/ciena-common-test/encryption-test-container/encryption-list-test/leaf-list-test";
                }
                leaf-list identityref-test {
                  ciena-common-yang:encrypt "identityref-test-encrypted";
                  ciena-common-yang:encrypt-path "/ciena-common-test/encryption-test-container/encryption-list-test/leaf-list-test";
                  type identityref {
                    base test:crypto-alg;
                  }
                }
                leaf-list identityref-test-encrypted {
                  type string {
                    ciena-common-yang:stringptr "true";
                  }
                  ciena-common-yang:decrypt "identityref-test";
                  ciena-common-yang:decrypt-path "/ciena-common-test/encryption-test-container/encryption-list-test/leaf-list-test";
                }
                leaf-list instance-identifier-test {
                  ciena-common-yang:encrypt "instance-identifier-test-encrypted";
                  ciena-common-yang:encrypt-path "/ciena-common-test/encryption-test-container/encryption-list-test/leaf-list-test";
                  type instance-identifier;
                }
                leaf-list instance-identifier-test-encrypted {
                  type string {
                    ciena-common-yang:stringptr "true";
                  }
                  ciena-common-yang:decrypt "instance-identifier-test";
                  ciena-common-yang:decrypt-path "/ciena-common-test/encryption-test-container/encryption-list-test/leaf-list-test";
                }
                leaf-list leafref-test {
                  ciena-common-yang:encrypt "leafref-test-encrypted";
                  ciena-common-yang:encrypt-path "/ciena-common-test/encryption-test-container/encryption-list-test/leaf-list-test";
                  type leafref {
                    path "/test:red/test:blue/test:b";
                  }
                }
                leaf-list leafref-test-encrypted {
                  type string {
                    ciena-common-yang:stringptr "true";
                  }
                  ciena-common-yang:decrypt "leafref-test";
                  ciena-common-yang:decrypt-path "/ciena-common-test/encryption-test-container/encryption-list-test/leaf-list-test";
                }
                leaf-list stringptr-test {
                  ciena-common-yang:encrypt "stringptr-test-encrypted";
                  ciena-common-yang:encrypt-path "/ciena-common-test/encryption-test-container/encryption-list-test/leaf-list-test";
                  type stringptr;
                }
                leaf-list stringptr-test-encrypted {
                  type string {
                    ciena-common-yang:stringptr "true";
                  }
                  ciena-common-yang:decrypt "stringptr-test";
                  ciena-common-yang:decrypt-path "/ciena-common-test/encryption-test-container/encryption-list-test/leaf-list-test";
                }
                leaf-list string-test {
                  ciena-common-yang:encrypt "string-test-encrypted";
                  ciena-common-yang:encrypt-path "/ciena-common-test/encryption-test-container/encryption-list-test/leaf-list-test";
                  type string;
                }
                leaf-list string-test-encrypted {
                  type string {
                    ciena-common-yang:stringptr "true";
                  }
                  ciena-common-yang:decrypt "string-test";
                  ciena-common-yang:decrypt-path "/ciena-common-test/encryption-test-container/encryption-list-test/leaf-list-test";
                }
                leaf-list uint8-test {
                  ciena-common-yang:encrypt "uint8-test-encrypted";
                  ciena-common-yang:encrypt-path "/ciena-common-test/encryption-test-container/encryption-list-test/leaf-list-test";
                  type uint8;
                }
                leaf-list uint8-test-encrypted {
                  type string {
                    ciena-common-yang:stringptr "true";
                  }
                  ciena-common-yang:decrypt "uint8-test";
                  ciena-common-yang:decrypt-path "/ciena-common-test/encryption-test-container/encryption-list-test/leaf-list-test";
                }
                leaf-list union-test {
                  ciena-common-yang:encrypt "union-test-encrypted";
                  ciena-common-yang:encrypt-path "/ciena-common-test/encryption-test-container/encryption-list-test/leaf-list-test";
                  type union {
                    type int32;
                    type enumeration {
                      enum unbounded;
                    }
                  }
                }
                leaf-list union-test-encrypted {
                  type string {
                    ciena-common-yang:stringptr "true";
                  }
                  ciena-common-yang:decrypt "union-test";
                  ciena-common-yang:decrypt-path "/ciena-common-test/encryption-test-container/encryption-list-test/leaf-list-test";
                }
              }
              container leaf-test {
                leaf binary-test {
                  ciena-common-yang:encrypt "binary-test-encrypted";
                  ciena-common-yang:encrypt-path "/ciena-common-test/encryption-test-container/encryption-list-test/leaf-test";
                  type binary;
                  ciena-common-yang:sensitive "true";
                }
                leaf binary-test-encrypted {
                  type string {
                    ciena-common-yang:stringptr "true";
                  }
                  ciena-common-yang:decrypt "binary-test";
                  ciena-common-yang:decrypt-path "/ciena-common-test/encryption-test-container/encryption-list-test/leaf-test";
                  ciena-common-yang:sensitive "true";
                }
                leaf bits-test {
                  ciena-common-yang:encrypt "bits-test-encrypted";
                  ciena-common-yang:encrypt-path "/ciena-common-test/encryption-test-container/encryption-list-test/leaf-test";
                  ciena-common-yang:sensitive "true";
                  type bits {
                    bit apple {
                      position 0;
                    }
                    bit orange {
                      position 1;
                    }
                    bit banana {
                      position 2;
                    }
                  }
                }
                leaf bits-test-encrypted {
                  type string {
                    ciena-common-yang:stringptr "true";
                  }
                  ciena-common-yang:decrypt "bits-test";
                  ciena-common-yang:decrypt-path "/ciena-common-test/encryption-test-container/encryption-list-test/leaf-test";
                  ciena-common-yang:sensitive "true";
                }
                leaf offset-bits-test {
                  ciena-common-yang:encrypt "offset-bits-test-encrypted";
                  ciena-common-yang:encrypt-path "/ciena-common-test/encryption-test-container/encryption-list-test/leaf-test";
                  ciena-common-yang:sensitive "true";
                  type bits {
                    bit apple {
                      position 3;
                    }
                    bit orange {
                      position 5;
                    }
                    bit banana {
                      position 7;
                    }
                  }
                }
                leaf offset-bits-test-encrypted {
                  type string {
                    ciena-common-yang:stringptr "true";
                  }
                  ciena-common-yang:decrypt "offset-bits-test";
                  ciena-common-yang:decrypt-path "/ciena-common-test/encryption-test-container/encryption-list-test/leaf-test";
                  ciena-common-yang:sensitive "true";
                }
                leaf boolean-test {
                  ciena-common-yang:encrypt "boolean-test-encrypted";
                  ciena-common-yang:encrypt-path "/ciena-common-test/encryption-test-container/encryption-list-test/leaf-test";
                  ciena-common-yang:sensitive "true";
                  type boolean;
                }
                leaf boolean-test-encrypted {
                  type string {
                    ciena-common-yang:stringptr "true";
                  }
                  ciena-common-yang:decrypt "boolean-test";
                  ciena-common-yang:decrypt-path "/ciena-common-test/encryption-test-container/encryption-list-test/leaf-test";
                  ciena-common-yang:sensitive "true";
                }
                leaf decimal64-test {
                  ciena-common-yang:encrypt "decimal64-test-encrypted";
                  ciena-common-yang:encrypt-path "/ciena-common-test/encryption-test-container/encryption-list-test/leaf-test";
                  ciena-common-yang:sensitive "true";
                  type decimal64 {
                    fraction-digits 2;
                  }
                }
                leaf decimal64-test-encrypted {
                  type string {
                    ciena-common-yang:stringptr "true";
                  }
                  ciena-common-yang:decrypt "decimal64-test";
                  ciena-common-yang:decrypt-path "/ciena-common-test/encryption-test-container/encryption-list-test/leaf-test";
                  ciena-common-yang:sensitive "true";
                }
                leaf empty-test {
                  ciena-common-yang:encrypt "empty-test-encrypted";
                  ciena-common-yang:encrypt-path "/ciena-common-test/encryption-test-container/encryption-list-test/leaf-test";
                  ciena-common-yang:sensitive "true";
                  type empty;
                }
                leaf empty-test-encrypted {
                  type string {
                    ciena-common-yang:stringptr "true";
                  }
                  ciena-common-yang:decrypt "empty-test";
                  ciena-common-yang:decrypt-path "/ciena-common-test/encryption-test-container/encryption-list-test/leaf-test";
                  ciena-common-yang:sensitive "true";
                }
                leaf enumeration-test {
                  ciena-common-yang:encrypt "enumeration-test-encrypted";
                  ciena-common-yang:encrypt-path "/ciena-common-test/encryption-test-container/encryption-list-test/leaf-test";
                  ciena-common-yang:sensitive "true";
                  type enumeration {
                    enum test-1;
                    enum test-2;
                    enum test-3;
                  }
                }
                leaf enumeration-test-encrypted {
                  type string {
                    ciena-common-yang:stringptr "true";
                  }
                  ciena-common-yang:decrypt "enumeration-test";
                  ciena-common-yang:decrypt-path "/ciena-common-test/encryption-test-container/encryption-list-test/leaf-test";
                  ciena-common-yang:sensitive "true";
                }
                leaf enumeration-extended-test {
                  ciena-common-yang:encrypt "enumeration-extended-test-encrypted";
                  ciena-common-yang:encrypt-path "/ciena-common-test/encryption-test-container/encryption-list-test/leaf-test";
                  ciena-common-yang:sensitive "true";
                  type enumeration {
                    enum forty-one {
                      value 41;
                    }
                    enum ten {
                      value 10;
                    }
                    enum seven {
                      value 7;
                    }
                  }
                }
                leaf enumeration-extended-test-encrypted {
                  type string {
                    ciena-common-yang:stringptr "true";
                  }
                  ciena-common-yang:decrypt "enumeration-extended-test";
                  ciena-common-yang:decrypt-path "/ciena-common-test/encryption-test-container/encryption-list-test/leaf-test";
                  ciena-common-yang:sensitive "true";
                }
                leaf identityref-test {
                  ciena-common-yang:encrypt "identifyref-test-encrypted";
                  ciena-common-yang:encrypt-path "/ciena-common-test/encryption-test-container/encryption-list-test/leaf-test";
                  ciena-common-yang:sensitive "true";
                  type identityref {
                    base test:crypto-alg;
                  }
                }
                leaf identifyref-test-encrypted {
                  type string {
                    ciena-common-yang:stringptr "true";
                  }
                  ciena-common-yang:decrypt "identityref-test";
                  ciena-common-yang:decrypt-path "/ciena-common-test/encryption-test-container/encryption-list-test/leaf-test";
                  ciena-common-yang:sensitive "true";
                }
                leaf instance-identifier-test {
                  ciena-common-yang:encrypt "instance-identifier-test-encrypted";
                  ciena-common-yang:encrypt-path "/ciena-common-test/encryption-test-container/encryption-list-test/leaf-test";
                  ciena-common-yang:sensitive "true";
                  type instance-identifier;
                }
                leaf instance-identifier-test-encrypted {
                  type string {
                    ciena-common-yang:stringptr "true";
                  }
                  ciena-common-yang:decrypt "instance-identifier-test";
                  ciena-common-yang:decrypt-path "/ciena-common-test/encryption-test-container/encryption-list-test/leaf-test";
                  ciena-common-yang:sensitive "true";
                }
                leaf int64-test {
                  ciena-common-yang:encrypt "int64-test-encrypted";
                  ciena-common-yang:encrypt-path "/ciena-common-test/encryption-test-container/encryption-list-test/leaf-test";
                  ciena-common-yang:sensitive "true";
                  type int64;
                }
                leaf int64-test-encrypted {
                  type string {
                    ciena-common-yang:stringptr "true";
                  }
                  ciena-common-yang:decrypt "int64-test";
                  ciena-common-yang:decrypt-path "/ciena-common-test/encryption-test-container/encryption-list-test/leaf-test";
                  ciena-common-yang:sensitive "true";
                }
                leaf leafref-test {
                  ciena-common-yang:encrypt "leafref-test-encrypted";
                  ciena-common-yang:encrypt-path "/ciena-common-test/encryption-test-container/encryption-list-test/leaf-test";
                  ciena-common-yang:sensitive "true";
                  type leafref {
                    path "/test:red/test:blue/test:c";
                  }
                }
                leaf leafref-test-encrypted {
                  type string {
                    ciena-common-yang:stringptr "true";
                  }
                  ciena-common-yang:decrypt "leafref-test";
                  ciena-common-yang:decrypt-path "/ciena-common-test/encryption-test-container/encryption-list-test/leaf-test";
                  ciena-common-yang:sensitive "true";
                }
                leaf stringptr-test {
                  ciena-common-yang:encrypt "stringptr-test-encrypted";
                  ciena-common-yang:encrypt-path "/ciena-common-test/encryption-test-container/encryption-list-test/leaf-test";
                  ciena-common-yang:sensitive "true";
                  type string {
                    ciena-common-yang:stringptr "true";
                  }
                }
                leaf stringptr-test-encrypted {
                  type string {
                    ciena-common-yang:stringptr "true";
                  }
                  ciena-common-yang:decrypt "stringptr-test";
                  ciena-common-yang:decrypt-path "/ciena-common-test/encryption-test-container/encryption-list-test/leaf-test";
                  ciena-common-yang:sensitive "true";
                }
                leaf string-test {
                  ciena-common-yang:encrypt "string-test-encrypted";
                  ciena-common-yang:encrypt-path "/ciena-common-test/encryption-test-container/encryption-list-test/leaf-test";
                  ciena-common-yang:sensitive "true";
                  type string {
                    length "0..15";
                  }
                }
                leaf string-test-encrypted {
                  type string {
                    ciena-common-yang:stringptr "true";
                  }
                  ciena-common-yang:decrypt "string-test";
                  ciena-common-yang:decrypt-path "/ciena-common-test/encryption-test-container/encryption-list-test/leaf-test";
                  ciena-common-yang:sensitive "true";
                }
                leaf union-test {
                  ciena-common-yang:encrypt "union-test-encrypted";
                  ciena-common-yang:encrypt-path "/ciena-common-test/encryption-test-container/encryption-list-test/leaf-test";
                  type union {
                    type int32;
                    type enumeration {
                      enum unbounded;
                    }
                  }
                  ciena-common-yang:sensitive "true";
                }
                leaf union-test-encrypted {
                  type string {
                    ciena-common-yang:stringptr "true";
                  }
                  ciena-common-yang:decrypt "union-test";
                  ciena-common-yang:decrypt-path "/ciena-common-test/encryption-test-container/encryption-list-test/leaf-test";
                  ciena-common-yang:sensitive "true";
                }
              }
            }
          }
          container toggle-sleep {
            container input {
              ciena-common-yang:containerptr "true";
            }
          }
          uses grouping-test;
          container rpc-test-empty;
          container rpc-test-no-output {
            container input {
              ciena-common-yang:containerptr "true";
            }
          }
          container rpc-test-no-input {
            container output {
              ciena-common-yang:containerptr "true";
            }
          }
          container rpc-test {
            container input {
              ciena-common-yang:containerptr "true";
            }
            container output {
              ciena-common-yang:containerptr "true";
            }
          }
          container rpc-trigger-encryption-set {
            container input {
              ciena-common-yang:containerptr "true";
            }
          }
          container notification-test {
            ciena-common-yang:containerptr "true";
            uses red-blue-group;
          }
          container encryption-notification-test {
            ciena-common-yang:containerptr "true";
            container X {
              leaf y {
                ciena-common-yang:encrypt "y-encrypted";
                ciena-common-yang:encrypt-path "/ciena-common-test/encryption-notification-test/X";
                type string;
              }
              leaf y-encrypted {
                type string {
                  ciena-common-yang:stringptr "true";
                }
                ciena-common-yang:decrypt "y";
                ciena-common-yang:decrypt-path "/ciena-common-test/encryption-notification-test/X";
              }
            }
          }
          container stack-push {
            description
              "Push into thread specific stack";
            container input {
              ciena-common-yang:containerptr "true";
            }
            container output {
              ciena-common-yang:containerptr "true";
            }
          }
          container stack-pop {
            description
              "Pop from thread specific stack";
            container input {
              ciena-common-yang:containerptr "true";
            }
            container output {
              ciena-common-yang:containerptr "true";
            }
          }
          container stack-get {
            description
              "Get pushed data for an attribute";
            container input {
              ciena-common-yang:containerptr "true";
            }
            container output {
              ciena-common-yang:containerptr "true";
            }
          }
          container stack-merge {
            description
              "Merge thread specific stacks";
            container input {
              ciena-common-yang:containerptr "true";
            }
            container output {
              ciena-common-yang:containerptr "true";
            }
          }
          container return-code-set {
            description
              "Set the return code in the response";
            container input {
              ciena-common-yang:containerptr "true";
            }
            container output {
              ciena-common-yang:containerptr "true";
            }
          }
          container validate-test {
            description
              "Set the return code in the response";
            container input {
              ciena-common-yang:containerptr "true";
            }
            container output {
              ciena-common-yang:containerptr "true";
            }
          }
          container test-deadline-timeout {
            description
              "Take input as timeout and handler will wait till this time
                based on test scenario type and return pass as true/false.";
            container input {
              ciena-common-yang:containerptr "true";
            }
            container output {
              ciena-common-yang:containerptr "true";
            }
          }
          container mount_test_a {
            list b {
              key "name";
              leaf name {
                type string;
              }
              anyxml c;
              container anyxml-mount {
                ciena-common-yang:mount-start "ciena-common-test";
                ciena-common-yang:mount-end "ciena-common-test";
              }
              anydata d;
              container anydata-mount {
                ciena-common-yang:mount-start "ciena-common-test";
                ciena-common-yang:mount-end "ciena-common-test";
              }
            }
          }
          container mount_test_b {
            list b {
              key "name";
              leaf name {
                type string;
              }
              anyxml c;
              container anyxml-mount {
                ciena-common-yang:mount-start "ciena-common-test-list";
                uses ciena-common-test-list:ciena-common-test-list-mount-data-actions-notifs-as-cont;
                ciena-common-yang:mount-end "ciena-common-test-list";
              }
            }
          }
          container i_love_big_data {
            list big_list {
              key "name";
              leaf name {
                type uint64;
              }
              leaf some_data {
                type decimal64 {
                  fraction-digits 10;
                }
              }
            }
          }
          container i_love_instance_id_for_keys {
            list some_list {
              key "instance_id_name";
              leaf instance_id_name {
                type instance-identifier;
              }
              leaf some_data {
                type decimal64 {
                  fraction-digits 10;
                }
              }
              container some_container {
                description
                  "Dummy container to have same context as parent";
                list sub_list {
                  description
                    "Another keyed list to have instance-id in parent context";
                  key "some_sub_key";
                  leaf some_sub_key {
                    type uint32;
                  }
                  leaf some_sub_leaf {
                    type uint32;
                  }
                }
              }
            }
          }
          container test-restconf-a {
            leaf b {
              type string;
            }
            leaf c {
              type uint8;
            }
            leaf awesome-wildcard-field {
              type string;
            }
            list d {
              key "name";
              leaf name {
                type string;
              }
              leaf test-state {
                type boolean;
              }
              container awesome-wildcard-field {
                leaf awesome-wildcard-field {
                  type boolean;
                }
                leaf awesome-wildcard-field-not {
                  type string;
                }
              }
              list e {
                key "index";
                leaf index {
                  type uint8;
                }
                leaf name {
                  type string;
                }
                list awesome-wildcard-field {
                  key "awesome-wildcard-field";
                  leaf awesome-wildcard-field {
                    type uint8;
                  }
                }
              }
            }
          }
          container test-colon-container {
            leaf enumeration-test {
              ciena-common-yang:sensitive "true";
              type enumeration {
                enum "1:n Mux type";
                enum "2:n Mux type";
                enum "3:n Mux type";
              }
            }
          }
          container multi-augment;
          container ddy-test-server-config {
            leaf handle-complete-transaction {
              type enumeration {
                enum none {
                  description
                    "complete-transaction not handled at all";
                }
                enum local {
                  description
                    "complete-transaction bound to local service";
                }
                enum service {
                  description
                    "complete-transaction bound to ddy-test-server";
                }
              }
              default "none";
            }
          }
          container client-activations {
            description
              "Sometimes you are testing something and you just need a simple way to execute a task.";
            container input {
              ciena-common-yang:containerptr "true";
            }
          }
          ciena-common-yang:mount-end "ciena-common-test";
        }
      }
      list instance {
        key "name";
        leaf name {
          type string;
        }
        container result {
          ciena-common-yang:encrypt "container-1";
          ciena-common-yang:encrypt-path "/ciena-common-test/encryption-test-container/instance";
          list amp {
            ciena-common-yang:encrypt "amp";
            ciena-common-yang:encrypt-path "/ciena-common-test/encryption-test-container/instance/container-1";
            key "amp_name";
            leaf amp_name {
              ciena-common-yang:encrypt "amp_name";
              ciena-common-yang:encrypt-path "/ciena-common-test/encryption-test-container/instance/container-1/amp";
              type string;
            }
            list measurement-no-power {
              ciena-common-yang:encrypt "measurement-no-power";
              ciena-common-yang:encrypt-path "/ciena-common-test/encryption-test-container/instance/container-1/amp";
              description
                "Power measurements of span measured with all channels blocked.";
              key "index";
              leaf index {
                ciena-common-yang:encrypt "index";
                ciena-common-yang:encrypt-path "/ciena-common-test/encryption-test-container/instance/container-1/amp/measurement-no-power";
                type uint8;
              }
              leaf in-current-power {
                ciena-common-yang:encrypt "in-current-power";
                ciena-common-yang:encrypt-path "/ciena-common-test/encryption-test-container/instance/container-1/amp/measurement-no-power";
                type decimal64 {
                  fraction-digits 1;
                }
              }
              leaf in-min-power {
                ciena-common-yang:encrypt "in-min-power";
                ciena-common-yang:encrypt-path "/ciena-common-test/encryption-test-container/instance/container-1/amp/measurement-no-power";
                type decimal64 {
                  fraction-digits 1;
                }
              }
              config false;
            }
          }
        }
        container container-1 {
          ciena-common-yang:decrypt "result";
          ciena-common-yang:decrypt-path "/ciena-common-test/encryption-test-container/instance";
          list amp {
            ciena-common-yang:decrypt "amp";
            ciena-common-yang:decrypt-path "/ciena-common-test/encryption-test-container/instance/result";
            key "amp_name";
            leaf amp_name {
              type string {
                ciena-common-yang:stringptr "true";
              }
              ciena-common-yang:decrypt "amp_name";
              ciena-common-yang:decrypt-path "/ciena-common-test/encryption-test-container/instance/result/amp";
            }
            list measurement-no-power {
              ciena-common-yang:decrypt "measurement-no-power";
              ciena-common-yang:decrypt-path "/ciena-common-test/encryption-test-container/instance/result/amp";
              key "index";
              leaf index {
                type string {
                  ciena-common-yang:stringptr "true";
                }
                ciena-common-yang:decrypt "index";
                ciena-common-yang:decrypt-path "/ciena-common-test/encryption-test-container/instance/result/amp/measurement-no-power";
              }
              leaf in-current-power {
                type string {
                  ciena-common-yang:stringptr "true";
                }
                ciena-common-yang:decrypt "in-current-power";
                ciena-common-yang:decrypt-path "/ciena-common-test/encryption-test-container/instance/result/amp/measurement-no-power";
              }
              leaf in-min-power {
                type string {
                  ciena-common-yang:stringptr "true";
                }
                ciena-common-yang:decrypt "in-min-power";
                ciena-common-yang:decrypt-path "/ciena-common-test/encryption-test-container/instance/result/amp/measurement-no-power";
              }
              config false;
            }
          }
        }
        list some-other-list {
          key "name";
          leaf name {
            type string;
          }
          leaf measurement {
            type uint8;
          }
        }
      }
      list key-in-grouping {
        ciena-common-yang:encrypt "key-in-grouping-encrypted";
        ciena-common-yang:encrypt-path "/ciena-common-test/encryption-test-container";
        description
          "test list key leaf definition can be provided by grouping";
        key "name";
        leaf name {
          ciena-common-yang:encrypt "name";
          ciena-common-yang:encrypt-path "/ciena-common-test/encryption-test-container/key-in-grouping-encrypted";
          type string;
        }
        leaf stats {
          ciena-common-yang:encrypt "stats";
          ciena-common-yang:encrypt-path "/ciena-common-test/encryption-test-container/key-in-grouping-encrypted";
          type uint32;
        }
      }
      list key-in-grouping-encrypted {
        ciena-common-yang:decrypt "key-in-grouping";
        ciena-common-yang:decrypt-path "/ciena-common-test/encryption-test-container";
        key "name";
        leaf name {
          type string {
            ciena-common-yang:stringptr "true";
          }
          ciena-common-yang:decrypt "name";
          ciena-common-yang:decrypt-path "/ciena-common-test/encryption-test-container/key-in-grouping";
        }
        leaf stats {
          type string {
            ciena-common-yang:stringptr "true";
          }
          ciena-common-yang:decrypt "stats";
          ciena-common-yang:decrypt-path "/ciena-common-test/encryption-test-container/key-in-grouping";
        }
      }
      list list-enc-generate-with-renamed-leaves {
        ciena-common-yang:encrypt "list-enc-generate-with-renamed-leaves-enc";
        ciena-common-yang:encrypt-path "/ciena-common-test/encryption-test-container";
        description
          "test list encryption with nested containers and leaves renamed";
        key "name";
        leaf name {
          ciena-common-yang:encrypt "name";
          ciena-common-yang:encrypt-path "/ciena-common-test/encryption-test-container/list-enc-generate-with-renamed-leaves-enc";
          type string;
        }
        leaf aaa {
          ciena-common-yang:encrypt "aaa-enc";
          ciena-common-yang:encrypt-path "/ciena-common-test/encryption-test-container/list-enc-generate-with-renamed-leaves-enc";
          type uint8;
          ciena-common-yang:sensitive "true";
        }
        container ddd {
          ciena-common-yang:encrypt "ddd-enc";
          ciena-common-yang:encrypt-path "/ciena-common-test/encryption-test-container/list-enc-generate-with-renamed-leaves-enc";
          leaf eee {
            ciena-common-yang:encrypt "eee-enc";
            ciena-common-yang:encrypt-path "/ciena-common-test/encryption-test-container/list-enc-generate-with-renamed-leaves-enc/ddd-enc";
            type uint8;
          }
          leaf fff {
            ciena-common-yang:encrypt "fff";
            ciena-common-yang:encrypt-path "/ciena-common-test/encryption-test-container/list-enc-generate-with-renamed-leaves-enc/ddd-enc";
            type uint8;
          }
          config false;
        }
      }
      list list-enc-generate-with-renamed-leaves-enc {
        ciena-common-yang:decrypt "list-enc-generate-with-renamed-leaves";
        ciena-common-yang:decrypt-path "/ciena-common-test/encryption-test-container";
        key "name";
        leaf name {
          type string {
            ciena-common-yang:stringptr "true";
          }
          ciena-common-yang:decrypt "name";
          ciena-common-yang:decrypt-path "/ciena-common-test/encryption-test-container/list-enc-generate-with-renamed-leaves";
        }
        leaf aaa-enc {
          type string {
            ciena-common-yang:stringptr "true";
          }
          ciena-common-yang:decrypt "aaa";
          ciena-common-yang:decrypt-path "/ciena-common-test/encryption-test-container/list-enc-generate-with-renamed-leaves";
          ciena-common-yang:sensitive "true";
        }
        container ddd-enc {
          ciena-common-yang:decrypt "ddd";
          ciena-common-yang:decrypt-path "/ciena-common-test/encryption-test-container/list-enc-generate-with-renamed-leaves";
          leaf eee-enc {
            type string {
              ciena-common-yang:stringptr "true";
            }
            ciena-common-yang:decrypt "eee";
            ciena-common-yang:decrypt-path "/ciena-common-test/encryption-test-container/list-enc-generate-with-renamed-leaves/ddd";
          }
          leaf fff {
            type string {
              ciena-common-yang:stringptr "true";
            }
            ciena-common-yang:decrypt "fff";
            ciena-common-yang:decrypt-path "/ciena-common-test/encryption-test-container/list-enc-generate-with-renamed-leaves/ddd";
          }
          config false;
        }
      }
      list list-generate-with-enc-path-for-leaves {
        ciena-common-yang:encrypt "list-generate-with-enc-path-for-leaves-enc";
        ciena-common-yang:encrypt-path "/ciena-common-test/encryption-test-container";
        description
          "test list encryption with some leaves having encryption-path and encryption-relative-path information";
        key "index";
        leaf index {
          ciena-common-yang:encrypt "index-enc";
          ciena-common-yang:encrypt-path "/ciena-common-test/encryption-test-container/list-generate-with-enc-path-for-leaves-enc";
          type uint8;
        }
        leaf ggg {
          ciena-common-yang:encrypt "ggg";
          ciena-common-yang:encrypt-path "/ciena-common-test/encryption-test-container/list-generate-with-enc-path-for-leaves-enc";
          type uint8;
        }
        container hhh {
          ciena-common-yang:encrypt "hhh";
          ciena-common-yang:encrypt-path "/ciena-common-test/encryption-test-container/list-generate-with-enc-path-for-leaves-enc";
          leaf iii {
            ciena-common-yang:encrypt "iii-enc";
            ciena-common-yang:encrypt-path "/ciena-common-test/encryption-test-container/list-generate-with-enc-path-for-leaves-enc/hhh";
            type uint8;
          }
          leaf jjj {
            ciena-common-yang:encrypt "none-existing-leaf";
            ciena-common-yang:encrypt-path "/ciena-common-test/encryption-test-container/A/B";
            type uint8;
            ciena-common-yang:sensitive "true";
          }
          leaf kkk {
            ciena-common-yang:encrypt "none-existing-leaf-2";
            ciena-common-yang:encrypt-path "/ciena-common-test/encryption-test-container/A/B";
            type uint8;
            config false;
            ciena-common-yang:sensitive "true";
          }
        }
      }
      list list-generate-with-enc-path-for-leaves-enc {
        ciena-common-yang:decrypt "list-generate-with-enc-path-for-leaves";
        ciena-common-yang:decrypt-path "/ciena-common-test/encryption-test-container";
        key "index-enc";
        leaf index-enc {
          type string {
            ciena-common-yang:stringptr "true";
          }
          ciena-common-yang:decrypt "index";
          ciena-common-yang:decrypt-path "/ciena-common-test/encryption-test-container/list-generate-with-enc-path-for-leaves";
        }
        leaf ggg {
          type string {
            ciena-common-yang:stringptr "true";
          }
          ciena-common-yang:decrypt "ggg";
          ciena-common-yang:decrypt-path "/ciena-common-test/encryption-test-container/list-generate-with-enc-path-for-leaves";
        }
        container hhh {
          ciena-common-yang:decrypt "hhh";
          ciena-common-yang:decrypt-path "/ciena-common-test/encryption-test-container/list-generate-with-enc-path-for-leaves";
          leaf iii-enc {
            type string {
              ciena-common-yang:stringptr "true";
            }
            ciena-common-yang:decrypt "iii";
            ciena-common-yang:decrypt-path "/ciena-common-test/encryption-test-container/list-generate-with-enc-path-for-leaves/hhh";
          }
        }
      }
      container A {
        container B {
          leaf none-existing-leaf {
            ciena-common-yang:decrypt "jjj";
            ciena-common-yang:decrypt-path "/ciena-common-test/encryption-test-container/list-generate-with-enc-path-for-leaves/hhh";
            type string {
              ciena-common-yang:stringptr "true";
            }
            ciena-common-yang:sensitive "true";
          }
          leaf none-existing-leaf-2 {
            ciena-common-yang:decrypt "kkk";
            ciena-common-yang:decrypt-path "/ciena-common-test/encryption-test-container/list-generate-with-enc-path-for-leaves/hhh";
            type string {
              ciena-common-yang:stringptr "true";
            }
            ciena-common-yang:sensitive "true";
            config false;
          }
          leaf y {
            type string {
              ciena-common-yang:stringptr "true";
            }
          }
          leaf z {
            type uint8;
          }
        }
      }
      container container-generate-as-sibling {
        ciena-common-yang:encrypt "container-generate-as-sibling-enc";
        ciena-common-yang:encrypt-path "/ciena-common-test/encryption-test-container";
        description
          "test simple container encryption default generating as siblings";
        leaf a {
          ciena-common-yang:encrypt "a";
          ciena-common-yang:encrypt-path "/ciena-common-test/encryption-test-container/container-generate-as-sibling-enc";
          type uint8;
        }
        container b {
          ciena-common-yang:encrypt "b";
          ciena-common-yang:encrypt-path "/ciena-common-test/encryption-test-container/container-generate-as-sibling-enc";
          leaf c {
            ciena-common-yang:encrypt "c";
            ciena-common-yang:encrypt-path "/ciena-common-test/encryption-test-container/container-generate-as-sibling-enc/b";
            type uint8;
          }
        }
      }
      container container-generate-as-sibling-enc {
        ciena-common-yang:decrypt "container-generate-as-sibling";
        ciena-common-yang:decrypt-path "/ciena-common-test/encryption-test-container";
        leaf a {
          type string {
            ciena-common-yang:stringptr "true";
          }
          ciena-common-yang:decrypt "a";
          ciena-common-yang:decrypt-path "/ciena-common-test/encryption-test-container/container-generate-as-sibling";
        }
        container b {
          ciena-common-yang:decrypt "b";
          ciena-common-yang:decrypt-path "/ciena-common-test/encryption-test-container/container-generate-as-sibling";
          leaf c {
            type string {
              ciena-common-yang:stringptr "true";
            }
            ciena-common-yang:decrypt "c";
            ciena-common-yang:decrypt-path "/ciena-common-test/encryption-test-container/container-generate-as-sibling/b";
          }
        }
      }
      container X {
        container Z {
          container container-generate-at-relative-path {
            ciena-common-yang:encrypt "container-generate-at-relative-path-enc";
            ciena-common-yang:encrypt-path "/ciena-common-test/encryption-test-container/K";
            description
              "test container encryption with encrypt-relative-path information";
            container red {
              ciena-common-yang:encrypt "red";
              ciena-common-yang:encrypt-path "/ciena-common-test/encryption-test-container/K/container-generate-at-relative-path-enc";
              container blue {
                ciena-common-yang:encrypt "blue";
                ciena-common-yang:encrypt-path "/ciena-common-test/encryption-test-container/K/container-generate-at-relative-path-enc/red";
                leaf a {
                  ciena-common-yang:encrypt "a";
                  ciena-common-yang:encrypt-path "/ciena-common-test/encryption-test-container/K/container-generate-at-relative-path-enc/red/blue";
                  type uint8;
                }
                leaf b {
                  ciena-common-yang:encrypt "b";
                  ciena-common-yang:encrypt-path "/ciena-common-test/encryption-test-container/K/container-generate-at-relative-path-enc/red/blue";
                  type uint8;
                  default "22";
                }
                leaf c {
                  ciena-common-yang:encrypt "c";
                  ciena-common-yang:encrypt-path "/ciena-common-test/encryption-test-container/K/container-generate-at-relative-path-enc/red/blue";
                  type uint8;
                  default "44";
                }
                leaf d {
                  ciena-common-yang:encrypt "d";
                  ciena-common-yang:encrypt-path "/ciena-common-test/encryption-test-container/K/container-generate-at-relative-path-enc/red/blue";
                  type uint8;
                  default "88";
                }
              }
            }
            leaf a {
              ciena-common-yang:encrypt "a";
              ciena-common-yang:encrypt-path "/ciena-common-test/encryption-test-container/K/container-generate-at-relative-path-enc";
              type uint8;
            }
            container b {
              ciena-common-yang:encrypt "b";
              ciena-common-yang:encrypt-path "/ciena-common-test/encryption-test-container/K/container-generate-at-relative-path-enc";
              container red {
                ciena-common-yang:encrypt "red";
                ciena-common-yang:encrypt-path "/ciena-common-test/encryption-test-container/K/container-generate-at-relative-path-enc/b";
                container blue {
                  ciena-common-yang:encrypt "blue";
                  ciena-common-yang:encrypt-path "/ciena-common-test/encryption-test-container/K/container-generate-at-relative-path-enc/b/red";
                  leaf a {
                    ciena-common-yang:encrypt "a";
                    ciena-common-yang:encrypt-path "/ciena-common-test/encryption-test-container/K/container-generate-at-relative-path-enc/b/red/blue";
                    type uint8;
                  }
                  leaf b {
                    ciena-common-yang:encrypt "b";
                    ciena-common-yang:encrypt-path "/ciena-common-test/encryption-test-container/K/container-generate-at-relative-path-enc/b/red/blue";
                    type uint8;
                    default "22";
                  }
                  leaf c {
                    ciena-common-yang:encrypt "c";
                    ciena-common-yang:encrypt-path "/ciena-common-test/encryption-test-container/K/container-generate-at-relative-path-enc/b/red/blue";
                    type uint8;
                    default "44";
                  }
                  leaf d {
                    ciena-common-yang:encrypt "d";
                    ciena-common-yang:encrypt-path "/ciena-common-test/encryption-test-container/K/container-generate-at-relative-path-enc/b/red/blue";
                    type uint8;
                    default "88";
                  }
                }
              }
              leaf c {
                ciena-common-yang:encrypt "c";
                ciena-common-yang:encrypt-path "/ciena-common-test/encryption-test-container/K/container-generate-at-relative-path-enc/b";
                type uint8;
              }
            }
            config false;
          }
        }
      }
      container K {
        container container-generate-at-relative-path-enc {
          ciena-common-yang:decrypt "container-generate-at-relative-path";
          ciena-common-yang:decrypt-path "/ciena-common-test/encryption-test-container/X/Z";
          container red {
            ciena-common-yang:decrypt "red";
            ciena-common-yang:decrypt-path "/ciena-common-test/encryption-test-container/X/Z/container-generate-at-relative-path";
            container blue {
              ciena-common-yang:decrypt "blue";
              ciena-common-yang:decrypt-path "/ciena-common-test/encryption-test-container/X/Z/container-generate-at-relative-path/red";
              leaf a {
                type string {
                  ciena-common-yang:stringptr "true";
                }
                ciena-common-yang:decrypt "a";
                ciena-common-yang:decrypt-path "/ciena-common-test/encryption-test-container/X/Z/container-generate-at-relative-path/red/blue";
              }
              leaf b {
                type string {
                  ciena-common-yang:stringptr "true";
                }
                ciena-common-yang:decrypt "b";
                ciena-common-yang:decrypt-path "/ciena-common-test/encryption-test-container/X/Z/container-generate-at-relative-path/red/blue";
              }
              leaf c {
                type string {
                  ciena-common-yang:stringptr "true";
                }
                ciena-common-yang:decrypt "c";
                ciena-common-yang:decrypt-path "/ciena-common-test/encryption-test-container/X/Z/container-generate-at-relative-path/red/blue";
              }
              leaf d {
                type string {
                  ciena-common-yang:stringptr "true";
                }
                ciena-common-yang:decrypt "d";
                ciena-common-yang:decrypt-path "/ciena-common-test/encryption-test-container/X/Z/container-generate-at-relative-path/red/blue";
              }
            }
          }
          leaf a {
            type string {
              ciena-common-yang:stringptr "true";
            }
            ciena-common-yang:decrypt "a";
            ciena-common-yang:decrypt-path "/ciena-common-test/encryption-test-container/X/Z/container-generate-at-relative-path";
          }
          container b {
            ciena-common-yang:decrypt "b";
            ciena-common-yang:decrypt-path "/ciena-common-test/encryption-test-container/X/Z/container-generate-at-relative-path";
            container red {
              ciena-common-yang:decrypt "red";
              ciena-common-yang:decrypt-path "/ciena-common-test/encryption-test-container/X/Z/container-generate-at-relative-path/b";
              container blue {
                ciena-common-yang:decrypt "blue";
                ciena-common-yang:decrypt-path "/ciena-common-test/encryption-test-container/X/Z/container-generate-at-relative-path/b/red";
                leaf a {
                  type string {
                    ciena-common-yang:stringptr "true";
                  }
                  ciena-common-yang:decrypt "a";
                  ciena-common-yang:decrypt-path "/ciena-common-test/encryption-test-container/X/Z/container-generate-at-relative-path/b/red/blue";
                }
                leaf b {
                  type string {
                    ciena-common-yang:stringptr "true";
                  }
                  ciena-common-yang:decrypt "b";
                  ciena-common-yang:decrypt-path "/ciena-common-test/encryption-test-container/X/Z/container-generate-at-relative-path/b/red/blue";
                }
                leaf c {
                  type string {
                    ciena-common-yang:stringptr "true";
                  }
                  ciena-common-yang:decrypt "c";
                  ciena-common-yang:decrypt-path "/ciena-common-test/encryption-test-container/X/Z/container-generate-at-relative-path/b/red/blue";
                }
                leaf d {
                  type string {
                    ciena-common-yang:stringptr "true";
                  }
                  ciena-common-yang:decrypt "d";
                  ciena-common-yang:decrypt-path "/ciena-common-test/encryption-test-container/X/Z/container-generate-at-relative-path/b/red/blue";
                }
              }
            }
            leaf c {
              type string {
                ciena-common-yang:stringptr "true";
              }
              ciena-common-yang:decrypt "c";
              ciena-common-yang:decrypt-path "/ciena-common-test/encryption-test-container/X/Z/container-generate-at-relative-path/b";
            }
          }
          config false;
        }
        leaf l {
          type uint8;
        }
      }
      container container-generate-at-abs-path {
        ciena-common-yang:encrypt "container-generate-at-abs-path-enc";
        ciena-common-yang:encrypt-path "/ciena-common-test/encryption-test-container";
        description
          "test container encryption with absolute path encrypt-path information";
        leaf a {
          ciena-common-yang:encrypt "a";
          ciena-common-yang:encrypt-path "/ciena-common-test/encryption-test-container/container-generate-at-abs-path-enc";
          type uint8;
        }
        container b {
          ciena-common-yang:encrypt "b";
          ciena-common-yang:encrypt-path "/ciena-common-test/encryption-test-container/container-generate-at-abs-path-enc";
          leaf c {
            ciena-common-yang:encrypt "c";
            ciena-common-yang:encrypt-path "/ciena-common-test/encryption-test-container/container-generate-at-abs-path-enc/b";
            type uint8;
          }
        }
        config false;
      }
      container encrypt-to-existing-container {
        ciena-common-yang:encrypt "encrypt-to-existing-container-encrypted";
        ciena-common-yang:encrypt-path "/ciena-common-test/encryption-test-container";
        description
          "test container encryption to existing container. no generation will happen.";
        leaf a {
          ciena-common-yang:encrypt "a";
          ciena-common-yang:encrypt-path "/ciena-common-test/encryption-test-container/encrypt-to-existing-container-encrypted";
          type uint8;
        }
      }
      container encrypt-to-existing-container-encrypted {
        ciena-common-yang:decrypt "encrypt-to-existing-container";
        ciena-common-yang:decrypt-path "/ciena-common-test/encryption-test-container";
        leaf a {
          ciena-common-yang:decrypt "a";
          ciena-common-yang:decrypt-path "/ciena-common-test/encryption-test-container/encrypt-to-existing-container";
          type string {
            ciena-common-yang:stringptr "true";
          }
        }
      }
      container outter-container {
        ciena-common-yang:encrypt "outter-container-enc";
        ciena-common-yang:encrypt-path "/ciena-common-test/encryption-test-container";
        description
          "simple nested container test";
        leaf aaa {
          ciena-common-yang:encrypt "aaa";
          ciena-common-yang:encrypt-path "/ciena-common-test/encryption-test-container/outter-container-enc";
          type uint8;
        }
        container middle-container {
          ciena-common-yang:encrypt "middle-container";
          ciena-common-yang:encrypt-path "/ciena-common-test/encryption-test-container/outter-container-enc";
          leaf bbb {
            ciena-common-yang:encrypt "bbb";
            ciena-common-yang:encrypt-path "/ciena-common-test/encryption-test-container/outter-container-enc/middle-container";
            type uint8;
          }
          container inner-container {
            ciena-common-yang:encrypt "inner-container";
            ciena-common-yang:encrypt-path "/ciena-common-test/encryption-test-container/outter-container-enc/middle-container";
            leaf ccc {
              ciena-common-yang:encrypt "ccc";
              ciena-common-yang:encrypt-path "/ciena-common-test/encryption-test-container/outter-container-enc/middle-container/inner-container";
              type uint8;
            }
          }
        }
      }
      container outter-container-enc {
        ciena-common-yang:decrypt "outter-container";
        ciena-common-yang:decrypt-path "/ciena-common-test/encryption-test-container";
        leaf aaa {
          type string {
            ciena-common-yang:stringptr "true";
          }
          ciena-common-yang:decrypt "aaa";
          ciena-common-yang:decrypt-path "/ciena-common-test/encryption-test-container/outter-container";
        }
        container middle-container {
          ciena-common-yang:decrypt "middle-container";
          ciena-common-yang:decrypt-path "/ciena-common-test/encryption-test-container/outter-container";
          leaf bbb {
            type string {
              ciena-common-yang:stringptr "true";
            }
            ciena-common-yang:decrypt "bbb";
            ciena-common-yang:decrypt-path "/ciena-common-test/encryption-test-container/outter-container/middle-container";
          }
          container inner-container {
            ciena-common-yang:decrypt "inner-container";
            ciena-common-yang:decrypt-path "/ciena-common-test/encryption-test-container/outter-container/middle-container";
            leaf ccc {
              type string {
                ciena-common-yang:stringptr "true";
              }
              ciena-common-yang:decrypt "ccc";
              ciena-common-yang:decrypt-path "/ciena-common-test/encryption-test-container/outter-container/middle-container/inner-container";
            }
          }
        }
      }
      container one-to-two-container {
        ciena-common-yang:encrypt "one-to-two-container-enc";
        ciena-common-yang:encrypt-path "/ciena-common-test/encryption-test-container";
        description
          "error scenario test: leaves under one container encrypted to two containers
           is not fully supported, the leaves for one container will be missing";
        leaf aaa {
          ciena-common-yang:encrypt "aaa";
          ciena-common-yang:encrypt-path "/ciena-common-test/encryption-test-container/one-to-two-container-enc";
          type uint8;
        }
        leaf-list bbb {
          ciena-common-yang:encrypt "bbb";
          ciena-common-yang:encrypt-path "/ciena-common-test/encryption-test-container/one-to-two-container-other";
          type uint8;
        }
        container inner-container {
          ciena-common-yang:encrypt "inner-container";
          ciena-common-yang:encrypt-path "/ciena-common-test/encryption-test-container/one-to-two-container-enc";
          leaf-list ccc {
            ciena-common-yang:encrypt "ccc";
            ciena-common-yang:encrypt-path "/ciena-common-test/encryption-test-container/one-to-two-container-enc/inner-container";
            type uint8;
          }
          leaf ddd {
            ciena-common-yang:encrypt "ddd";
            ciena-common-yang:encrypt-path "/ciena-common-test/encryption-test-container/one-to-two-container-other";
            type uint8;
          }
        }
      }
      container one-to-two-container-enc {
        ciena-common-yang:decrypt "one-to-two-container";
        ciena-common-yang:decrypt-path "/ciena-common-test/encryption-test-container";
        leaf aaa {
          type string {
            ciena-common-yang:stringptr "true";
          }
          ciena-common-yang:decrypt "aaa";
          ciena-common-yang:decrypt-path "/ciena-common-test/encryption-test-container/one-to-two-container";
        }
        container inner-container {
          ciena-common-yang:decrypt "inner-container";
          ciena-common-yang:decrypt-path "/ciena-common-test/encryption-test-container/one-to-two-container";
          leaf-list ccc {
            type string {
              ciena-common-yang:stringptr "true";
            }
            ciena-common-yang:decrypt "ccc";
            ciena-common-yang:decrypt-path "/ciena-common-test/encryption-test-container/one-to-two-container/inner-container";
          }
        }
      }
      container one-to-two-container-other {
        leaf-list bbb {
          ciena-common-yang:decrypt "bbb";
          ciena-common-yang:decrypt-path "/ciena-common-test/encryption-test-container/one-to-two-container";
          type string {
            ciena-common-yang:stringptr "true";
          }
        }
        leaf ddd {
          ciena-common-yang:decrypt "ddd";
          ciena-common-yang:decrypt-path "/ciena-common-test/encryption-test-container/one-to-two-container/inner-container";
          type string {
            ciena-common-yang:stringptr "true";
          }
        }
        leaf fff {
          type uint8;
        }
      }
      list nested-list {
        ciena-common-yang:encrypt "nested-list-enc";
        ciena-common-yang:encrypt-path "/ciena-common-test/encryption-test-container";
        description
          "test nested list encryption";
        key "name";
        leaf name {
          ciena-common-yang:encrypt "name";
          ciena-common-yang:encrypt-path "/ciena-common-test/encryption-test-container/nested-list-enc";
          type stringptr;
        }
        leaf aaa {
          ciena-common-yang:encrypt "aaa";
          ciena-common-yang:encrypt-path "/ciena-common-test/encryption-test-container/nested-list-enc";
          type uint8;
        }
        list inner-list {
          ciena-common-yang:encrypt "inner-list";
          ciena-common-yang:encrypt-path "/ciena-common-test/encryption-test-container/nested-list-enc";
          key "index";
          leaf index {
            ciena-common-yang:encrypt "index";
            ciena-common-yang:encrypt-path "/ciena-common-test/encryption-test-container/nested-list-enc/inner-list";
            type uint8;
          }
          leaf-list ccc {
            ciena-common-yang:encrypt "ccc";
            ciena-common-yang:encrypt-path "/ciena-common-test/encryption-test-container/nested-list-enc/inner-list";
            type string;
          }
        }
      }
      list nested-list-enc {
        ciena-common-yang:decrypt "nested-list";
        ciena-common-yang:decrypt-path "/ciena-common-test/encryption-test-container";
        key "name";
        leaf name {
          type string {
            ciena-common-yang:stringptr "true";
          }
          ciena-common-yang:decrypt "name";
          ciena-common-yang:decrypt-path "/ciena-common-test/encryption-test-container/nested-list";
        }
        leaf aaa {
          type string {
            ciena-common-yang:stringptr "true";
          }
          ciena-common-yang:decrypt "aaa";
          ciena-common-yang:decrypt-path "/ciena-common-test/encryption-test-container/nested-list";
        }
        list inner-list {
          ciena-common-yang:decrypt "inner-list";
          ciena-common-yang:decrypt-path "/ciena-common-test/encryption-test-container/nested-list";
          key "index";
          leaf index {
            type string {
              ciena-common-yang:stringptr "true";
            }
            ciena-common-yang:decrypt "index";
            ciena-common-yang:decrypt-path "/ciena-common-test/encryption-test-container/nested-list/inner-list";
          }
          leaf-list ccc {
            type string {
              ciena-common-yang:stringptr "true";
            }
            ciena-common-yang:decrypt "ccc";
            ciena-common-yang:decrypt-path "/ciena-common-test/encryption-test-container/nested-list/inner-list";
          }
        }
      }
      container other {
        leaf ccc {
          type string;
        }
      }
      container user-defined-leaves {
        description
          "selected leaves encryption container";
        leaf a {
          ciena-common-yang:encrypt "x";
          ciena-common-yang:encrypt-path "/ciena-common-test/encryption-test-container/user-defined-leaves-encrypted";
          type string;
        }
        leaf b {
          type string;
        }
      }
      container user-defined-leaves-encrypted {
        leaf x {
          ciena-common-yang:decrypt "a";
          ciena-common-yang:decrypt-path "/ciena-common-test/encryption-test-container/user-defined-leaves";
          type string;
        }
      }
      list nested-list-leaf-encryption {
        key "name";
        leaf name {
          type string;
        }
        leaf x {
          ciena-common-yang:encrypt "x-enc";
          ciena-common-yang:encrypt-path "/ciena-common-test/encryption-test-container/nested-list-leaf-encryption";
          type string;
        }
        leaf x-enc {
          type string {
            ciena-common-yang:stringptr "true";
          }
          ciena-common-yang:decrypt "x";
          ciena-common-yang:decrypt-path "/ciena-common-test/encryption-test-container/nested-list-leaf-encryption";
        }
        list inner {
          key "index";
          leaf index {
            type uint8;
          }
          leaf u {
            ciena-common-yang:encrypt "u-enc";
            ciena-common-yang:encrypt-path "/ciena-common-test/encryption-test-container/nested-list-leaf-encryption/inner";
            type string;
          }
          leaf u-enc {
            type string {
              ciena-common-yang:stringptr "true";
            }
            ciena-common-yang:decrypt "u";
            ciena-common-yang:decrypt-path "/ciena-common-test/encryption-test-container/nested-list-leaf-encryption/inner";
          }
        }
      }
      list encryption-list-test {
        key "key1 key2";
        leaf key1 {
          type stringptr;
        }
        leaf key2 {
          type typetest;
        }
        container leaf-list-test {
          leaf-list binary-test {
            ciena-common-yang:encrypt "binary-test-encrypted";
            ciena-common-yang:encrypt-path "/ciena-common-test/encryption-test-container/encryption-list-test/leaf-list-test";
            type binary;
          }
          leaf-list binary-test-encrypted {
            type string {
              ciena-common-yang:stringptr "true";
            }
            ciena-common-yang:decrypt "binary-test";
            ciena-common-yang:decrypt-path "/ciena-common-test/encryption-test-container/encryption-list-test/leaf-list-test";
          }
          leaf-list bits-test {
            ciena-common-yang:encrypt "bits-test-encrypted";
            ciena-common-yang:encrypt-path "/ciena-common-test/encryption-test-container/encryption-list-test/leaf-list-test";
            type bits {
              bit disable-nagle {
                position 0;
              }
              bit auto-sense-speed {
                position 1;
              }
            }
          }
          leaf-list bits-test-encrypted {
            type string {
              ciena-common-yang:stringptr "true";
            }
            ciena-common-yang:decrypt "bits-test";
            ciena-common-yang:decrypt-path "/ciena-common-test/encryption-test-container/encryption-list-test/leaf-list-test";
          }
          leaf-list boolean-test {
            ciena-common-yang:encrypt "boolean-test-encrypted";
            ciena-common-yang:encrypt-path "/ciena-common-test/encryption-test-container/encryption-list-test/leaf-list-test";
            type boolean;
          }
          leaf-list boolean-test-encrypted {
            type string {
              ciena-common-yang:stringptr "true";
            }
            ciena-common-yang:decrypt "boolean-test";
            ciena-common-yang:decrypt-path "/ciena-common-test/encryption-test-container/encryption-list-test/leaf-list-test";
          }
          leaf-list decimal64-test {
            ciena-common-yang:encrypt "decimal64-test-encrypted";
            ciena-common-yang:encrypt-path "/ciena-common-test/encryption-test-container/encryption-list-test/leaf-list-test";
            type decimal64 {
              fraction-digits 10;
            }
          }
          leaf-list decimal64-test-encrypted {
            type string {
              ciena-common-yang:stringptr "true";
            }
            ciena-common-yang:decrypt "decimal64-test";
            ciena-common-yang:decrypt-path "/ciena-common-test/encryption-test-container/encryption-list-test/leaf-list-test";
          }
          leaf-list empty-test {
            ciena-common-yang:encrypt "empty-test-encrypted";
            ciena-common-yang:encrypt-path "/ciena-common-test/encryption-test-container/encryption-list-test/leaf-list-test";
            type empty;
          }
          leaf-list empty-test-encrypted {
            type string {
              ciena-common-yang:stringptr "true";
            }
            ciena-common-yang:decrypt "empty-test";
            ciena-common-yang:decrypt-path "/ciena-common-test/encryption-test-container/encryption-list-test/leaf-list-test";
          }
          leaf-list enumeration-test {
            ciena-common-yang:encrypt "enumeration-test-encrypted";
            ciena-common-yang:encrypt-path "/ciena-common-test/encryption-test-container/encryption-list-test/leaf-list-test";
            type enumeration {
              enum test-a;
              enum test-b;
              enum test-c;
              enum map;
            }
          }
          leaf-list enumeration-test-encrypted {
            type string {
              ciena-common-yang:stringptr "true";
            }
            ciena-common-yang:decrypt "enumeration-test";
            ciena-common-yang:decrypt-path "/ciena-common-test/encryption-test-container/encryption-list-test/leaf-list-test";
          }
          leaf-list identityref-test {
            ciena-common-yang:encrypt "identityref-test-encrypted";
            ciena-common-yang:encrypt-path "/ciena-common-test/encryption-test-container/encryption-list-test/leaf-list-test";
            type identityref {
              base test:crypto-alg;
            }
          }
          leaf-list identityref-test-encrypted {
            type string {
              ciena-common-yang:stringptr "true";
            }
            ciena-common-yang:decrypt "identityref-test";
            ciena-common-yang:decrypt-path "/ciena-common-test/encryption-test-container/encryption-list-test/leaf-list-test";
          }
          leaf-list instance-identifier-test {
            ciena-common-yang:encrypt "instance-identifier-test-encrypted";
            ciena-common-yang:encrypt-path "/ciena-common-test/encryption-test-container/encryption-list-test/leaf-list-test";
            type instance-identifier;
          }
          leaf-list instance-identifier-test-encrypted {
            type string {
              ciena-common-yang:stringptr "true";
            }
            ciena-common-yang:decrypt "instance-identifier-test";
            ciena-common-yang:decrypt-path "/ciena-common-test/encryption-test-container/encryption-list-test/leaf-list-test";
          }
          leaf-list leafref-test {
            ciena-common-yang:encrypt "leafref-test-encrypted";
            ciena-common-yang:encrypt-path "/ciena-common-test/encryption-test-container/encryption-list-test/leaf-list-test";
            type leafref {
              path "/test:red/test:blue/test:b";
            }
          }
          leaf-list leafref-test-encrypted {
            type string {
              ciena-common-yang:stringptr "true";
            }
            ciena-common-yang:decrypt "leafref-test";
            ciena-common-yang:decrypt-path "/ciena-common-test/encryption-test-container/encryption-list-test/leaf-list-test";
          }
          leaf-list stringptr-test {
            ciena-common-yang:encrypt "stringptr-test-encrypted";
            ciena-common-yang:encrypt-path "/ciena-common-test/encryption-test-container/encryption-list-test/leaf-list-test";
            type stringptr;
          }
          leaf-list stringptr-test-encrypted {
            type string {
              ciena-common-yang:stringptr "true";
            }
            ciena-common-yang:decrypt "stringptr-test";
            ciena-common-yang:decrypt-path "/ciena-common-test/encryption-test-container/encryption-list-test/leaf-list-test";
          }
          leaf-list string-test {
            ciena-common-yang:encrypt "string-test-encrypted";
            ciena-common-yang:encrypt-path "/ciena-common-test/encryption-test-container/encryption-list-test/leaf-list-test";
            type string;
          }
          leaf-list string-test-encrypted {
            type string {
              ciena-common-yang:stringptr "true";
            }
            ciena-common-yang:decrypt "string-test";
            ciena-common-yang:decrypt-path "/ciena-common-test/encryption-test-container/encryption-list-test/leaf-list-test";
          }
          leaf-list uint8-test {
            ciena-common-yang:encrypt "uint8-test-encrypted";
            ciena-common-yang:encrypt-path "/ciena-common-test/encryption-test-container/encryption-list-test/leaf-list-test";
            type uint8;
          }
          leaf-list uint8-test-encrypted {
            type string {
              ciena-common-yang:stringptr "true";
            }
            ciena-common-yang:decrypt "uint8-test";
            ciena-common-yang:decrypt-path "/ciena-common-test/encryption-test-container/encryption-list-test/leaf-list-test";
          }
          leaf-list union-test {
            ciena-common-yang:encrypt "union-test-encrypted";
            ciena-common-yang:encrypt-path "/ciena-common-test/encryption-test-container/encryption-list-test/leaf-list-test";
            type union {
              type int32;
              type enumeration {
                enum unbounded;
              }
            }
          }
          leaf-list union-test-encrypted {
            type string {
              ciena-common-yang:stringptr "true";
            }
            ciena-common-yang:decrypt "union-test";
            ciena-common-yang:decrypt-path "/ciena-common-test/encryption-test-container/encryption-list-test/leaf-list-test";
          }
        }
        container leaf-test {
          leaf binary-test {
            ciena-common-yang:encrypt "binary-test-encrypted";
            ciena-common-yang:encrypt-path "/ciena-common-test/encryption-test-container/encryption-list-test/leaf-test";
            type binary;
            ciena-common-yang:sensitive "true";
          }
          leaf binary-test-encrypted {
            type string {
              ciena-common-yang:stringptr "true";
            }
            ciena-common-yang:decrypt "binary-test";
            ciena-common-yang:decrypt-path "/ciena-common-test/encryption-test-container/encryption-list-test/leaf-test";
            ciena-common-yang:sensitive "true";
          }
          leaf bits-test {
            ciena-common-yang:encrypt "bits-test-encrypted";
            ciena-common-yang:encrypt-path "/ciena-common-test/encryption-test-container/encryption-list-test/leaf-test";
            ciena-common-yang:sensitive "true";
            type bits {
              bit apple {
                position 0;
              }
              bit orange {
                position 1;
              }
              bit banana {
                position 2;
              }
            }
          }
          leaf bits-test-encrypted {
            type string {
              ciena-common-yang:stringptr "true";
            }
            ciena-common-yang:decrypt "bits-test";
            ciena-common-yang:decrypt-path "/ciena-common-test/encryption-test-container/encryption-list-test/leaf-test";
            ciena-common-yang:sensitive "true";
          }
          leaf offset-bits-test {
            ciena-common-yang:encrypt "offset-bits-test-encrypted";
            ciena-common-yang:encrypt-path "/ciena-common-test/encryption-test-container/encryption-list-test/leaf-test";
            ciena-common-yang:sensitive "true";
            type bits {
              bit apple {
                position 3;
              }
              bit orange {
                position 5;
              }
              bit banana {
                position 7;
              }
            }
          }
          leaf offset-bits-test-encrypted {
            type string {
              ciena-common-yang:stringptr "true";
            }
            ciena-common-yang:decrypt "offset-bits-test";
            ciena-common-yang:decrypt-path "/ciena-common-test/encryption-test-container/encryption-list-test/leaf-test";
            ciena-common-yang:sensitive "true";
          }
          leaf boolean-test {
            ciena-common-yang:encrypt "boolean-test-encrypted";
            ciena-common-yang:encrypt-path "/ciena-common-test/encryption-test-container/encryption-list-test/leaf-test";
            ciena-common-yang:sensitive "true";
            type boolean;
          }
          leaf boolean-test-encrypted {
            type string {
              ciena-common-yang:stringptr "true";
            }
            ciena-common-yang:decrypt "boolean-test";
            ciena-common-yang:decrypt-path "/ciena-common-test/encryption-test-container/encryption-list-test/leaf-test";
            ciena-common-yang:sensitive "true";
          }
          leaf decimal64-test {
            ciena-common-yang:encrypt "decimal64-test-encrypted";
            ciena-common-yang:encrypt-path "/ciena-common-test/encryption-test-container/encryption-list-test/leaf-test";
            ciena-common-yang:sensitive "true";
            type decimal64 {
              fraction-digits 2;
            }
          }
          leaf decimal64-test-encrypted {
            type string {
              ciena-common-yang:stringptr "true";
            }
            ciena-common-yang:decrypt "decimal64-test";
            ciena-common-yang:decrypt-path "/ciena-common-test/encryption-test-container/encryption-list-test/leaf-test";
            ciena-common-yang:sensitive "true";
          }
          leaf empty-test {
            ciena-common-yang:encrypt "empty-test-encrypted";
            ciena-common-yang:encrypt-path "/ciena-common-test/encryption-test-container/encryption-list-test/leaf-test";
            ciena-common-yang:sensitive "true";
            type empty;
          }
          leaf empty-test-encrypted {
            type string {
              ciena-common-yang:stringptr "true";
            }
            ciena-common-yang:decrypt "empty-test";
            ciena-common-yang:decrypt-path "/ciena-common-test/encryption-test-container/encryption-list-test/leaf-test";
            ciena-common-yang:sensitive "true";
          }
          leaf enumeration-test {
            ciena-common-yang:encrypt "enumeration-test-encrypted";
            ciena-common-yang:encrypt-path "/ciena-common-test/encryption-test-container/encryption-list-test/leaf-test";
            ciena-common-yang:sensitive "true";
            type enumeration {
              enum test-1;
              enum test-2;
              enum test-3;
            }
          }
          leaf enumeration-test-encrypted {
            type string {
              ciena-common-yang:stringptr "true";
            }
            ciena-common-yang:decrypt "enumeration-test";
            ciena-common-yang:decrypt-path "/ciena-common-test/encryption-test-container/encryption-list-test/leaf-test";
            ciena-common-yang:sensitive "true";
          }
          leaf enumeration-extended-test {
            ciena-common-yang:encrypt "enumeration-extended-test-encrypted";
            ciena-common-yang:encrypt-path "/ciena-common-test/encryption-test-container/encryption-list-test/leaf-test";
            ciena-common-yang:sensitive "true";
            type enumeration {
              enum forty-one {
                value 41;
              }
              enum ten {
                value 10;
              }
              enum seven {
                value 7;
              }
            }
          }
          leaf enumeration-extended-test-encrypted {
            type string {
              ciena-common-yang:stringptr "true";
            }
            ciena-common-yang:decrypt "enumeration-extended-test";
            ciena-common-yang:decrypt-path "/ciena-common-test/encryption-test-container/encryption-list-test/leaf-test";
            ciena-common-yang:sensitive "true";
          }
          leaf identityref-test {
            ciena-common-yang:encrypt "identifyref-test-encrypted";
            ciena-common-yang:encrypt-path "/ciena-common-test/encryption-test-container/encryption-list-test/leaf-test";
            ciena-common-yang:sensitive "true";
            type identityref {
              base test:crypto-alg;
            }
          }
          leaf identifyref-test-encrypted {
            type string {
              ciena-common-yang:stringptr "true";
            }
            ciena-common-yang:decrypt "identityref-test";
            ciena-common-yang:decrypt-path "/ciena-common-test/encryption-test-container/encryption-list-test/leaf-test";
            ciena-common-yang:sensitive "true";
          }
          leaf instance-identifier-test {
            ciena-common-yang:encrypt "instance-identifier-test-encrypted";
            ciena-common-yang:encrypt-path "/ciena-common-test/encryption-test-container/encryption-list-test/leaf-test";
            ciena-common-yang:sensitive "true";
            type instance-identifier;
          }
          leaf instance-identifier-test-encrypted {
            type string {
              ciena-common-yang:stringptr "true";
            }
            ciena-common-yang:decrypt "instance-identifier-test";
            ciena-common-yang:decrypt-path "/ciena-common-test/encryption-test-container/encryption-list-test/leaf-test";
            ciena-common-yang:sensitive "true";
          }
          leaf int64-test {
            ciena-common-yang:encrypt "int64-test-encrypted";
            ciena-common-yang:encrypt-path "/ciena-common-test/encryption-test-container/encryption-list-test/leaf-test";
            ciena-common-yang:sensitive "true";
            type int64;
          }
          leaf int64-test-encrypted {
            type string {
              ciena-common-yang:stringptr "true";
            }
            ciena-common-yang:decrypt "int64-test";
            ciena-common-yang:decrypt-path "/ciena-common-test/encryption-test-container/encryption-list-test/leaf-test";
            ciena-common-yang:sensitive "true";
          }
          leaf leafref-test {
            ciena-common-yang:encrypt "leafref-test-encrypted";
            ciena-common-yang:encrypt-path "/ciena-common-test/encryption-test-container/encryption-list-test/leaf-test";
            ciena-common-yang:sensitive "true";
            type leafref {
              path "/test:red/test:blue/test:c";
            }
          }
          leaf leafref-test-encrypted {
            type string {
              ciena-common-yang:stringptr "true";
            }
            ciena-common-yang:decrypt "leafref-test";
            ciena-common-yang:decrypt-path "/ciena-common-test/encryption-test-container/encryption-list-test/leaf-test";
            ciena-common-yang:sensitive "true";
          }
          leaf stringptr-test {
            ciena-common-yang:encrypt "stringptr-test-encrypted";
            ciena-common-yang:encrypt-path "/ciena-common-test/encryption-test-container/encryption-list-test/leaf-test";
            ciena-common-yang:sensitive "true";
            type string {
              ciena-common-yang:stringptr "true";
            }
          }
          leaf stringptr-test-encrypted {
            type string {
              ciena-common-yang:stringptr "true";
            }
            ciena-common-yang:decrypt "stringptr-test";
            ciena-common-yang:decrypt-path "/ciena-common-test/encryption-test-container/encryption-list-test/leaf-test";
            ciena-common-yang:sensitive "true";
          }
          leaf string-test {
            ciena-common-yang:encrypt "string-test-encrypted";
            ciena-common-yang:encrypt-path "/ciena-common-test/encryption-test-container/encryption-list-test/leaf-test";
            ciena-common-yang:sensitive "true";
            type string {
              length "0..15";
            }
          }
          leaf string-test-encrypted {
            type string {
              ciena-common-yang:stringptr "true";
            }
            ciena-common-yang:decrypt "string-test";
            ciena-common-yang:decrypt-path "/ciena-common-test/encryption-test-container/encryption-list-test/leaf-test";
            ciena-common-yang:sensitive "true";
          }
          leaf union-test {
            ciena-common-yang:encrypt "union-test-encrypted";
            ciena-common-yang:encrypt-path "/ciena-common-test/encryption-test-container/encryption-list-test/leaf-test";
            type union {
              type int32;
              type enumeration {
                enum unbounded;
              }
            }
            ciena-common-yang:sensitive "true";
          }
          leaf union-test-encrypted {
            type string {
              ciena-common-yang:stringptr "true";
            }
            ciena-common-yang:decrypt "union-test";
            ciena-common-yang:decrypt-path "/ciena-common-test/encryption-test-container/encryption-list-test/leaf-test";
            ciena-common-yang:sensitive "true";
          }
        }
      }
    }
    uses grouping-test;
    container mount_test_a {
      list b {
        key "name";
        leaf name {
          type string;
        }
        anyxml c;
        container anyxml-mount {
          ciena-common-yang:mount-start "ciena-common-test";
          container string-based-return-code-list {
            config false;
            description
              "List of errors in case of command failure";
            list return-code-list {
              leaf instance {
                type string {
                  ciena-common-yang:stringptr "true";
                }
                description
                  "The instance to which the error code applies.";
              }
              leaf error {
                type string;
              }
            }
          }
          uses red-blue-group;
          uses blue-yellow-group;
          container white {
            uses abc_group;
            container cont1 {
              uses abc_group;
            }
            container cont2 {
              uses abc_group;
            }
            container cont3 {
              uses abc_group;
            }
            container cont4 {
              uses abc_group;
            }
            list list1 {
              key "k";
              leaf k {
                type uint8;
              }
              uses abc_group;
            }
          }
          container validation-test {
            uses abc_validate_group;
          }
          container to-pointer-test {
            container a {
              leaf string-test {
                type string;
              }
            }
          }
          list to-pointer-test2 {
            key "first-key";
            leaf first-key {
              type uint8;
            }
            list second-list {
              key "second-key";
              leaf second-key {
                type uint8;
              }
              leaf second-string {
                type string;
              }
              container second-container {
                leaf second-container-string {
                  type string;
                }
              }
            }
          }
          container nested-container {
            container cone {
              leaf a {
                type uint8;
                default "1";
              }
              leaf b {
                type uint8;
                default "2";
              }
              leaf c {
                type uint8;
                default "3";
              }
            }
            container ctwo {
              config false;
              leaf d {
                type uint8;
              }
              leaf e {
                type uint8;
              }
              leaf f {
                type uint8;
              }
            }
          }
          container read-only {
            config false;
            uses red-blue-group;
            container name {
              container collision {
                leaf test {
                  type uint8;
                }
                container child1 {
                  container child2 {
                    leaf test {
                      type uint8;
                    }
                  }
                }
              }
            }
            container name-collision {
              leaf test {
                type uint8;
              }
              container child1 {
                container child2 {
                  leaf test {
                    type uint8;
                  }
                }
              }
            }
          }
          container remove-via-deviation {
            uses red-blue-group;
          }
          uses ordered-lists-group;
          container simple-deadline-test {
            uses deadline-group;
          }
          container simple-test-container {
            ciena-common-yang:containerptr "true";
            list keys-only-list {
              key "name";
              leaf name {
                type string;
              }
            }
            leaf other-attribute {
              type string;
            }
            container leaf-test {
              leaf string-test {
                ciena-common-yang:encrypt "string-test-encrypted";
                ciena-common-yang:encrypt-path "/ciena-common-test/simple-test-container/leaf-test";
                type string;
              }
              leaf string-test-encrypted {
                type string {
                  ciena-common-yang:stringptr "true";
                }
                ciena-common-yang:decrypt "string-test";
                ciena-common-yang:decrypt-path "/ciena-common-test/simple-test-container/leaf-test";
              }
              leaf uint8-test {
                type uint8;
              }
            }
            container presence-test {
              presence "presense test container";
            }
            container presence-test-2 {
              choice start-time {
                mandatory true;
                container immediate {
                  presence "Start the measurement session immediately.";
                }
                leaf relative {
                  type string;
                }
                leaf absolute {
                  type string;
                }
              }
            }
            list outter {
              key "index";
              leaf index {
                type uint8;
              }
              min-elements 2;
              max-elements 3;
              list inner {
                key "name";
                leaf name {
                  type string;
                }
                max-elements 2;
                leaf value {
                  type uint16;
                }
              }
              leaf-list boolean-leaf-list {
                type boolean;
                max-elements 3;
                min-elements 2;
              }
              leaf mode {
                type uint8 {
                  range "0..10";
                }
              }
            }
            list first {
              key "key1 key2";
              leaf key1 {
                type uint8;
              }
              leaf key2 {
                type string;
              }
              list second {
                key "key1 key2";
                leaf key1 {
                  type uint8;
                }
                leaf key2 {
                  type string;
                }
                list third {
                  key "key1";
                  leaf key1 {
                    type uint8;
                  }
                  container red {
                    container blue {
                      leaf a {
                        type string;
                      }
                      leaf b {
                        type string;
                      }
                    }
                    leaf yellow-leaf {
                      type string;
                    }
                    anyxml config;
                  }
                }
              }
            }
          }
          container list-keys {
            list bits-key {
              key "bit";
              leaf bit {
                type bits {
                  bit x;
                  bit y;
                  bit z;
                }
              }
            }
          }
          container identity-test {
            leaf base-test {
              type identityref {
                base test:crypto-alg;
              }
            }
            leaf mid-level-test {
              type identityref {
                base test:des;
              }
            }
            leaf top-test {
              type identityref {
                base test:des3;
              }
            }
            leaf external-test {
              type identityref {
                base ciena-common-yang:error-does-not-exist;
              }
            }
          }
          container encryption-test-container {
            container container-generate-at-abs-path-enc {
              ciena-common-yang:decrypt "container-generate-at-abs-path";
              ciena-common-yang:decrypt-path "/ciena-common-test/encryption-test-container";
              leaf a {
                type string {
                  ciena-common-yang:stringptr "true";
                }
                ciena-common-yang:decrypt "a";
                ciena-common-yang:decrypt-path "/ciena-common-test/encryption-test-container/container-generate-at-abs-path";
              }
              container b {
                ciena-common-yang:decrypt "b";
                ciena-common-yang:decrypt-path "/ciena-common-test/encryption-test-container/container-generate-at-abs-path";
                leaf c {
                  type string {
                    ciena-common-yang:stringptr "true";
                  }
                  ciena-common-yang:decrypt "c";
                  ciena-common-yang:decrypt-path "/ciena-common-test/encryption-test-container/container-generate-at-abs-path/b";
                }
              }
              config false;
            }
            list encryption-mount-test {
              key "name";
              leaf name {
                type string;
              }
              container data {
                ciena-common-yang:mount-start "ciena-common-test";
                ciena-common-yang:mount-end "ciena-common-test";
              }
            }
            list instance {
              key "name";
              leaf name {
                type string;
              }
              container result {
                ciena-common-yang:encrypt "container-1";
                ciena-common-yang:encrypt-path "/ciena-common-test/encryption-test-container/instance";
                list amp {
                  ciena-common-yang:encrypt "amp";
                  ciena-common-yang:encrypt-path "/ciena-common-test/encryption-test-container/instance/container-1";
                  key "amp_name";
                  leaf amp_name {
                    ciena-common-yang:encrypt "amp_name";
                    ciena-common-yang:encrypt-path "/ciena-common-test/encryption-test-container/instance/container-1/amp";
                    type string;
                  }
                  list measurement-no-power {
                    ciena-common-yang:encrypt "measurement-no-power";
                    ciena-common-yang:encrypt-path "/ciena-common-test/encryption-test-container/instance/container-1/amp";
                    description
                      "Power measurements of span measured with all channels blocked.";
                    key "index";
                    leaf index {
                      ciena-common-yang:encrypt "index";
                      ciena-common-yang:encrypt-path "/ciena-common-test/encryption-test-container/instance/container-1/amp/measurement-no-power";
                      type uint8;
                    }
                    leaf in-current-power {
                      ciena-common-yang:encrypt "in-current-power";
                      ciena-common-yang:encrypt-path "/ciena-common-test/encryption-test-container/instance/container-1/amp/measurement-no-power";
                      type decimal64 {
                        fraction-digits 1;
                      }
                    }
                    leaf in-min-power {
                      ciena-common-yang:encrypt "in-min-power";
                      ciena-common-yang:encrypt-path "/ciena-common-test/encryption-test-container/instance/container-1/amp/measurement-no-power";
                      type decimal64 {
                        fraction-digits 1;
                      }
                    }
                    config false;
                  }
                }
              }
              container container-1 {
                ciena-common-yang:decrypt "result";
                ciena-common-yang:decrypt-path "/ciena-common-test/encryption-test-container/instance";
                list amp {
                  ciena-common-yang:decrypt "amp";
                  ciena-common-yang:decrypt-path "/ciena-common-test/encryption-test-container/instance/result";
                  key "amp_name";
                  leaf amp_name {
                    type string {
                      ciena-common-yang:stringptr "true";
                    }
                    ciena-common-yang:decrypt "amp_name";
                    ciena-common-yang:decrypt-path "/ciena-common-test/encryption-test-container/instance/result/amp";
                  }
                  list measurement-no-power {
                    ciena-common-yang:decrypt "measurement-no-power";
                    ciena-common-yang:decrypt-path "/ciena-common-test/encryption-test-container/instance/result/amp";
                    key "index";
                    leaf index {
                      type string {
                        ciena-common-yang:stringptr "true";
                      }
                      ciena-common-yang:decrypt "index";
                      ciena-common-yang:decrypt-path "/ciena-common-test/encryption-test-container/instance/result/amp/measurement-no-power";
                    }
                    leaf in-current-power {
                      type string {
                        ciena-common-yang:stringptr "true";
                      }
                      ciena-common-yang:decrypt "in-current-power";
                      ciena-common-yang:decrypt-path "/ciena-common-test/encryption-test-container/instance/result/amp/measurement-no-power";
                    }
                    leaf in-min-power {
                      type string {
                        ciena-common-yang:stringptr "true";
                      }
                      ciena-common-yang:decrypt "in-min-power";
                      ciena-common-yang:decrypt-path "/ciena-common-test/encryption-test-container/instance/result/amp/measurement-no-power";
                    }
                    config false;
                  }
                }
              }
              list some-other-list {
                key "name";
                leaf name {
                  type string;
                }
                leaf measurement {
                  type uint8;
                }
              }
            }
            list key-in-grouping {
              ciena-common-yang:encrypt "key-in-grouping-encrypted";
              ciena-common-yang:encrypt-path "/ciena-common-test/encryption-test-container";
              description
                "test list key leaf definition can be provided by grouping";
              key "name";
              leaf name {
                ciena-common-yang:encrypt "name";
                ciena-common-yang:encrypt-path "/ciena-common-test/encryption-test-container/key-in-grouping-encrypted";
                type string;
              }
              leaf stats {
                ciena-common-yang:encrypt "stats";
                ciena-common-yang:encrypt-path "/ciena-common-test/encryption-test-container/key-in-grouping-encrypted";
                type uint32;
              }
            }
            list key-in-grouping-encrypted {
              ciena-common-yang:decrypt "key-in-grouping";
              ciena-common-yang:decrypt-path "/ciena-common-test/encryption-test-container";
              key "name";
              leaf name {
                type string {
                  ciena-common-yang:stringptr "true";
                }
                ciena-common-yang:decrypt "name";
                ciena-common-yang:decrypt-path "/ciena-common-test/encryption-test-container/key-in-grouping";
              }
              leaf stats {
                type string {
                  ciena-common-yang:stringptr "true";
                }
                ciena-common-yang:decrypt "stats";
                ciena-common-yang:decrypt-path "/ciena-common-test/encryption-test-container/key-in-grouping";
              }
            }
            list list-enc-generate-with-renamed-leaves {
              ciena-common-yang:encrypt "list-enc-generate-with-renamed-leaves-enc";
              ciena-common-yang:encrypt-path "/ciena-common-test/encryption-test-container";
              description
                "test list encryption with nested containers and leaves renamed";
              key "name";
              leaf name {
                ciena-common-yang:encrypt "name";
                ciena-common-yang:encrypt-path "/ciena-common-test/encryption-test-container/list-enc-generate-with-renamed-leaves-enc";
                type string;
              }
              leaf aaa {
                ciena-common-yang:encrypt "aaa-enc";
                ciena-common-yang:encrypt-path "/ciena-common-test/encryption-test-container/list-enc-generate-with-renamed-leaves-enc";
                type uint8;
                ciena-common-yang:sensitive "true";
              }
              container ddd {
                ciena-common-yang:encrypt "ddd-enc";
                ciena-common-yang:encrypt-path "/ciena-common-test/encryption-test-container/list-enc-generate-with-renamed-leaves-enc";
                leaf eee {
                  ciena-common-yang:encrypt "eee-enc";
                  ciena-common-yang:encrypt-path "/ciena-common-test/encryption-test-container/list-enc-generate-with-renamed-leaves-enc/ddd-enc";
                  type uint8;
                }
                leaf fff {
                  ciena-common-yang:encrypt "fff";
                  ciena-common-yang:encrypt-path "/ciena-common-test/encryption-test-container/list-enc-generate-with-renamed-leaves-enc/ddd-enc";
                  type uint8;
                }
                config false;
              }
            }
            list list-enc-generate-with-renamed-leaves-enc {
              ciena-common-yang:decrypt "list-enc-generate-with-renamed-leaves";
              ciena-common-yang:decrypt-path "/ciena-common-test/encryption-test-container";
              key "name";
              leaf name {
                type string {
                  ciena-common-yang:stringptr "true";
                }
                ciena-common-yang:decrypt "name";
                ciena-common-yang:decrypt-path "/ciena-common-test/encryption-test-container/list-enc-generate-with-renamed-leaves";
              }
              leaf aaa-enc {
                type string {
                  ciena-common-yang:stringptr "true";
                }
                ciena-common-yang:decrypt "aaa";
                ciena-common-yang:decrypt-path "/ciena-common-test/encryption-test-container/list-enc-generate-with-renamed-leaves";
                ciena-common-yang:sensitive "true";
              }
              container ddd-enc {
                ciena-common-yang:decrypt "ddd";
                ciena-common-yang:decrypt-path "/ciena-common-test/encryption-test-container/list-enc-generate-with-renamed-leaves";
                leaf eee-enc {
                  type string {
                    ciena-common-yang:stringptr "true";
                  }
                  ciena-common-yang:decrypt "eee";
                  ciena-common-yang:decrypt-path "/ciena-common-test/encryption-test-container/list-enc-generate-with-renamed-leaves/ddd";
                }
                leaf fff {
                  type string {
                    ciena-common-yang:stringptr "true";
                  }
                  ciena-common-yang:decrypt "fff";
                  ciena-common-yang:decrypt-path "/ciena-common-test/encryption-test-container/list-enc-generate-with-renamed-leaves/ddd";
                }
                config false;
              }
            }
            list list-generate-with-enc-path-for-leaves {
              ciena-common-yang:encrypt "list-generate-with-enc-path-for-leaves-enc";
              ciena-common-yang:encrypt-path "/ciena-common-test/encryption-test-container";
              description
                "test list encryption with some leaves having encryption-path and encryption-relative-path information";
              key "index";
              leaf index {
                ciena-common-yang:encrypt "index-enc";
                ciena-common-yang:encrypt-path "/ciena-common-test/encryption-test-container/list-generate-with-enc-path-for-leaves-enc";
                type uint8;
              }
              leaf ggg {
                ciena-common-yang:encrypt "ggg";
                ciena-common-yang:encrypt-path "/ciena-common-test/encryption-test-container/list-generate-with-enc-path-for-leaves-enc";
                type uint8;
              }
              container hhh {
                ciena-common-yang:encrypt "hhh";
                ciena-common-yang:encrypt-path "/ciena-common-test/encryption-test-container/list-generate-with-enc-path-for-leaves-enc";
                leaf iii {
                  ciena-common-yang:encrypt "iii-enc";
                  ciena-common-yang:encrypt-path "/ciena-common-test/encryption-test-container/list-generate-with-enc-path-for-leaves-enc/hhh";
                  type uint8;
                }
                leaf jjj {
                  ciena-common-yang:encrypt "none-existing-leaf";
                  ciena-common-yang:encrypt-path "/ciena-common-test/encryption-test-container/A/B";
                  type uint8;
                  ciena-common-yang:sensitive "true";
                }
                leaf kkk {
                  ciena-common-yang:encrypt "none-existing-leaf-2";
                  ciena-common-yang:encrypt-path "/ciena-common-test/encryption-test-container/A/B";
                  type uint8;
                  config false;
                  ciena-common-yang:sensitive "true";
                }
              }
            }
            list list-generate-with-enc-path-for-leaves-enc {
              ciena-common-yang:decrypt "list-generate-with-enc-path-for-leaves";
              ciena-common-yang:decrypt-path "/ciena-common-test/encryption-test-container";
              key "index-enc";
              leaf index-enc {
                type string {
                  ciena-common-yang:stringptr "true";
                }
                ciena-common-yang:decrypt "index";
                ciena-common-yang:decrypt-path "/ciena-common-test/encryption-test-container/list-generate-with-enc-path-for-leaves";
              }
              leaf ggg {
                type string {
                  ciena-common-yang:stringptr "true";
                }
                ciena-common-yang:decrypt "ggg";
                ciena-common-yang:decrypt-path "/ciena-common-test/encryption-test-container/list-generate-with-enc-path-for-leaves";
              }
              container hhh {
                ciena-common-yang:decrypt "hhh";
                ciena-common-yang:decrypt-path "/ciena-common-test/encryption-test-container/list-generate-with-enc-path-for-leaves";
                leaf iii-enc {
                  type string {
                    ciena-common-yang:stringptr "true";
                  }
                  ciena-common-yang:decrypt "iii";
                  ciena-common-yang:decrypt-path "/ciena-common-test/encryption-test-container/list-generate-with-enc-path-for-leaves/hhh";
                }
              }
            }
            container A {
              container B {
                leaf none-existing-leaf {
                  ciena-common-yang:decrypt "jjj";
                  ciena-common-yang:decrypt-path "/ciena-common-test/encryption-test-container/list-generate-with-enc-path-for-leaves/hhh";
                  type string {
                    ciena-common-yang:stringptr "true";
                  }
                  ciena-common-yang:sensitive "true";
                }
                leaf none-existing-leaf-2 {
                  ciena-common-yang:decrypt "kkk";
                  ciena-common-yang:decrypt-path "/ciena-common-test/encryption-test-container/list-generate-with-enc-path-for-leaves/hhh";
                  type string {
                    ciena-common-yang:stringptr "true";
                  }
                  ciena-common-yang:sensitive "true";
                  config false;
                }
                leaf y {
                  type string {
                    ciena-common-yang:stringptr "true";
                  }
                }
                leaf z {
                  type uint8;
                }
              }
            }
            container container-generate-as-sibling {
              ciena-common-yang:encrypt "container-generate-as-sibling-enc";
              ciena-common-yang:encrypt-path "/ciena-common-test/encryption-test-container";
              description
                "test simple container encryption default generating as siblings";
              leaf a {
                ciena-common-yang:encrypt "a";
                ciena-common-yang:encrypt-path "/ciena-common-test/encryption-test-container/container-generate-as-sibling-enc";
                type uint8;
              }
              container b {
                ciena-common-yang:encrypt "b";
                ciena-common-yang:encrypt-path "/ciena-common-test/encryption-test-container/container-generate-as-sibling-enc";
                leaf c {
                  ciena-common-yang:encrypt "c";
                  ciena-common-yang:encrypt-path "/ciena-common-test/encryption-test-container/container-generate-as-sibling-enc/b";
                  type uint8;
                }
              }
            }
            container container-generate-as-sibling-enc {
              ciena-common-yang:decrypt "container-generate-as-sibling";
              ciena-common-yang:decrypt-path "/ciena-common-test/encryption-test-container";
              leaf a {
                type string {
                  ciena-common-yang:stringptr "true";
                }
                ciena-common-yang:decrypt "a";
                ciena-common-yang:decrypt-path "/ciena-common-test/encryption-test-container/container-generate-as-sibling";
              }
              container b {
                ciena-common-yang:decrypt "b";
                ciena-common-yang:decrypt-path "/ciena-common-test/encryption-test-container/container-generate-as-sibling";
                leaf c {
                  type string {
                    ciena-common-yang:stringptr "true";
                  }
                  ciena-common-yang:decrypt "c";
                  ciena-common-yang:decrypt-path "/ciena-common-test/encryption-test-container/container-generate-as-sibling/b";
                }
              }
            }
            container X {
              container Z {
                container container-generate-at-relative-path {
                  ciena-common-yang:encrypt "container-generate-at-relative-path-enc";
                  ciena-common-yang:encrypt-path "/ciena-common-test/encryption-test-container/K";
                  description
                    "test container encryption with encrypt-relative-path information";
                  container red {
                    ciena-common-yang:encrypt "red";
                    ciena-common-yang:encrypt-path "/ciena-common-test/encryption-test-container/K/container-generate-at-relative-path-enc";
                    container blue {
                      ciena-common-yang:encrypt "blue";
                      ciena-common-yang:encrypt-path "/ciena-common-test/encryption-test-container/K/container-generate-at-relative-path-enc/red";
                      leaf a {
                        ciena-common-yang:encrypt "a";
                        ciena-common-yang:encrypt-path "/ciena-common-test/encryption-test-container/K/container-generate-at-relative-path-enc/red/blue";
                        type uint8;
                      }
                      leaf b {
                        ciena-common-yang:encrypt "b";
                        ciena-common-yang:encrypt-path "/ciena-common-test/encryption-test-container/K/container-generate-at-relative-path-enc/red/blue";
                        type uint8;
                        default "22";
                      }
                      leaf c {
                        ciena-common-yang:encrypt "c";
                        ciena-common-yang:encrypt-path "/ciena-common-test/encryption-test-container/K/container-generate-at-relative-path-enc/red/blue";
                        type uint8;
                        default "44";
                      }
                      leaf d {
                        ciena-common-yang:encrypt "d";
                        ciena-common-yang:encrypt-path "/ciena-common-test/encryption-test-container/K/container-generate-at-relative-path-enc/red/blue";
                        type uint8;
                        default "88";
                      }
                    }
                  }
                  leaf a {
                    ciena-common-yang:encrypt "a";
                    ciena-common-yang:encrypt-path "/ciena-common-test/encryption-test-container/K/container-generate-at-relative-path-enc";
                    type uint8;
                  }
                  container b {
                    ciena-common-yang:encrypt "b";
                    ciena-common-yang:encrypt-path "/ciena-common-test/encryption-test-container/K/container-generate-at-relative-path-enc";
                    container red {
                      ciena-common-yang:encrypt "red";
                      ciena-common-yang:encrypt-path "/ciena-common-test/encryption-test-container/K/container-generate-at-relative-path-enc/b";
                      container blue {
                        ciena-common-yang:encrypt "blue";
                        ciena-common-yang:encrypt-path "/ciena-common-test/encryption-test-container/K/container-generate-at-relative-path-enc/b/red";
                        leaf a {
                          ciena-common-yang:encrypt "a";
                          ciena-common-yang:encrypt-path "/ciena-common-test/encryption-test-container/K/container-generate-at-relative-path-enc/b/red/blue";
                          type uint8;
                        }
                        leaf b {
                          ciena-common-yang:encrypt "b";
                          ciena-common-yang:encrypt-path "/ciena-common-test/encryption-test-container/K/container-generate-at-relative-path-enc/b/red/blue";
                          type uint8;
                          default "22";
                        }
                        leaf c {
                          ciena-common-yang:encrypt "c";
                          ciena-common-yang:encrypt-path "/ciena-common-test/encryption-test-container/K/container-generate-at-relative-path-enc/b/red/blue";
                          type uint8;
                          default "44";
                        }
                        leaf d {
                          ciena-common-yang:encrypt "d";
                          ciena-common-yang:encrypt-path "/ciena-common-test/encryption-test-container/K/container-generate-at-relative-path-enc/b/red/blue";
                          type uint8;
                          default "88";
                        }
                      }
                    }
                    leaf c {
                      ciena-common-yang:encrypt "c";
                      ciena-common-yang:encrypt-path "/ciena-common-test/encryption-test-container/K/container-generate-at-relative-path-enc/b";
                      type uint8;
                    }
                  }
                  config false;
                }
              }
            }
            container K {
              container container-generate-at-relative-path-enc {
                ciena-common-yang:decrypt "container-generate-at-relative-path";
                ciena-common-yang:decrypt-path "/ciena-common-test/encryption-test-container/X/Z";
                container red {
                  ciena-common-yang:decrypt "red";
                  ciena-common-yang:decrypt-path "/ciena-common-test/encryption-test-container/X/Z/container-generate-at-relative-path";
                  container blue {
                    ciena-common-yang:decrypt "blue";
                    ciena-common-yang:decrypt-path "/ciena-common-test/encryption-test-container/X/Z/container-generate-at-relative-path/red";
                    leaf a {
                      type string {
                        ciena-common-yang:stringptr "true";
                      }
                      ciena-common-yang:decrypt "a";
                      ciena-common-yang:decrypt-path "/ciena-common-test/encryption-test-container/X/Z/container-generate-at-relative-path/red/blue";
                    }
                    leaf b {
                      type string {
                        ciena-common-yang:stringptr "true";
                      }
                      ciena-common-yang:decrypt "b";
                      ciena-common-yang:decrypt-path "/ciena-common-test/encryption-test-container/X/Z/container-generate-at-relative-path/red/blue";
                    }
                    leaf c {
                      type string {
                        ciena-common-yang:stringptr "true";
                      }
                      ciena-common-yang:decrypt "c";
                      ciena-common-yang:decrypt-path "/ciena-common-test/encryption-test-container/X/Z/container-generate-at-relative-path/red/blue";
                    }
                    leaf d {
                      type string {
                        ciena-common-yang:stringptr "true";
                      }
                      ciena-common-yang:decrypt "d";
                      ciena-common-yang:decrypt-path "/ciena-common-test/encryption-test-container/X/Z/container-generate-at-relative-path/red/blue";
                    }
                  }
                }
                leaf a {
                  type string {
                    ciena-common-yang:stringptr "true";
                  }
                  ciena-common-yang:decrypt "a";
                  ciena-common-yang:decrypt-path "/ciena-common-test/encryption-test-container/X/Z/container-generate-at-relative-path";
                }
                container b {
                  ciena-common-yang:decrypt "b";
                  ciena-common-yang:decrypt-path "/ciena-common-test/encryption-test-container/X/Z/container-generate-at-relative-path";
                  container red {
                    ciena-common-yang:decrypt "red";
                    ciena-common-yang:decrypt-path "/ciena-common-test/encryption-test-container/X/Z/container-generate-at-relative-path/b";
                    container blue {
                      ciena-common-yang:decrypt "blue";
                      ciena-common-yang:decrypt-path "/ciena-common-test/encryption-test-container/X/Z/container-generate-at-relative-path/b/red";
                      leaf a {
                        type string {
                          ciena-common-yang:stringptr "true";
                        }
                        ciena-common-yang:decrypt "a";
                        ciena-common-yang:decrypt-path "/ciena-common-test/encryption-test-container/X/Z/container-generate-at-relative-path/b/red/blue";
                      }
                      leaf b {
                        type string {
                          ciena-common-yang:stringptr "true";
                        }
                        ciena-common-yang:decrypt "b";
                        ciena-common-yang:decrypt-path "/ciena-common-test/encryption-test-container/X/Z/container-generate-at-relative-path/b/red/blue";
                      }
                      leaf c {
                        type string {
                          ciena-common-yang:stringptr "true";
                        }
                        ciena-common-yang:decrypt "c";
                        ciena-common-yang:decrypt-path "/ciena-common-test/encryption-test-container/X/Z/container-generate-at-relative-path/b/red/blue";
                      }
                      leaf d {
                        type string {
                          ciena-common-yang:stringptr "true";
                        }
                        ciena-common-yang:decrypt "d";
                        ciena-common-yang:decrypt-path "/ciena-common-test/encryption-test-container/X/Z/container-generate-at-relative-path/b/red/blue";
                      }
                    }
                  }
                  leaf c {
                    type string {
                      ciena-common-yang:stringptr "true";
                    }
                    ciena-common-yang:decrypt "c";
                    ciena-common-yang:decrypt-path "/ciena-common-test/encryption-test-container/X/Z/container-generate-at-relative-path/b";
                  }
                }
                config false;
              }
              leaf l {
                type uint8;
              }
            }
            container container-generate-at-abs-path {
              ciena-common-yang:encrypt "container-generate-at-abs-path-enc";
              ciena-common-yang:encrypt-path "/ciena-common-test/encryption-test-container";
              description
                "test container encryption with absolute path encrypt-path information";
              leaf a {
                ciena-common-yang:encrypt "a";
                ciena-common-yang:encrypt-path "/ciena-common-test/encryption-test-container/container-generate-at-abs-path-enc";
                type uint8;
              }
              container b {
                ciena-common-yang:encrypt "b";
                ciena-common-yang:encrypt-path "/ciena-common-test/encryption-test-container/container-generate-at-abs-path-enc";
                leaf c {
                  ciena-common-yang:encrypt "c";
                  ciena-common-yang:encrypt-path "/ciena-common-test/encryption-test-container/container-generate-at-abs-path-enc/b";
                  type uint8;
                }
              }
              config false;
            }
            container encrypt-to-existing-container {
              ciena-common-yang:encrypt "encrypt-to-existing-container-encrypted";
              ciena-common-yang:encrypt-path "/ciena-common-test/encryption-test-container";
              description
                "test container encryption to existing container. no generation will happen.";
              leaf a {
                ciena-common-yang:encrypt "a";
                ciena-common-yang:encrypt-path "/ciena-common-test/encryption-test-container/encrypt-to-existing-container-encrypted";
                type uint8;
              }
            }
            container encrypt-to-existing-container-encrypted {
              ciena-common-yang:decrypt "encrypt-to-existing-container";
              ciena-common-yang:decrypt-path "/ciena-common-test/encryption-test-container";
              leaf a {
                ciena-common-yang:decrypt "a";
                ciena-common-yang:decrypt-path "/ciena-common-test/encryption-test-container/encrypt-to-existing-container";
                type string {
                  ciena-common-yang:stringptr "true";
                }
              }
            }
            container outter-container {
              ciena-common-yang:encrypt "outter-container-enc";
              ciena-common-yang:encrypt-path "/ciena-common-test/encryption-test-container";
              description
                "simple nested container test";
              leaf aaa {
                ciena-common-yang:encrypt "aaa";
                ciena-common-yang:encrypt-path "/ciena-common-test/encryption-test-container/outter-container-enc";
                type uint8;
              }
              container middle-container {
                ciena-common-yang:encrypt "middle-container";
                ciena-common-yang:encrypt-path "/ciena-common-test/encryption-test-container/outter-container-enc";
                leaf bbb {
                  ciena-common-yang:encrypt "bbb";
                  ciena-common-yang:encrypt-path "/ciena-common-test/encryption-test-container/outter-container-enc/middle-container";
                  type uint8;
                }
                container inner-container {
                  ciena-common-yang:encrypt "inner-container";
                  ciena-common-yang:encrypt-path "/ciena-common-test/encryption-test-container/outter-container-enc/middle-container";
                  leaf ccc {
                    ciena-common-yang:encrypt "ccc";
                    ciena-common-yang:encrypt-path "/ciena-common-test/encryption-test-container/outter-container-enc/middle-container/inner-container";
                    type uint8;
                  }
                }
              }
            }
            container outter-container-enc {
              ciena-common-yang:decrypt "outter-container";
              ciena-common-yang:decrypt-path "/ciena-common-test/encryption-test-container";
              leaf aaa {
                type string {
                  ciena-common-yang:stringptr "true";
                }
                ciena-common-yang:decrypt "aaa";
                ciena-common-yang:decrypt-path "/ciena-common-test/encryption-test-container/outter-container";
              }
              container middle-container {
                ciena-common-yang:decrypt "middle-container";
                ciena-common-yang:decrypt-path "/ciena-common-test/encryption-test-container/outter-container";
                leaf bbb {
                  type string {
                    ciena-common-yang:stringptr "true";
                  }
                  ciena-common-yang:decrypt "bbb";
                  ciena-common-yang:decrypt-path "/ciena-common-test/encryption-test-container/outter-container/middle-container";
                }
                container inner-container {
                  ciena-common-yang:decrypt "inner-container";
                  ciena-common-yang:decrypt-path "/ciena-common-test/encryption-test-container/outter-container/middle-container";
                  leaf ccc {
                    type string {
                      ciena-common-yang:stringptr "true";
                    }
                    ciena-common-yang:decrypt "ccc";
                    ciena-common-yang:decrypt-path "/ciena-common-test/encryption-test-container/outter-container/middle-container/inner-container";
                  }
                }
              }
            }
            container one-to-two-container {
              ciena-common-yang:encrypt "one-to-two-container-enc";
              ciena-common-yang:encrypt-path "/ciena-common-test/encryption-test-container";
              description
                "error scenario test: leaves under one container encrypted to two containers
                 is not fully supported, the leaves for one container will be missing";
              leaf aaa {
                ciena-common-yang:encrypt "aaa";
                ciena-common-yang:encrypt-path "/ciena-common-test/encryption-test-container/one-to-two-container-enc";
                type uint8;
              }
              leaf-list bbb {
                ciena-common-yang:encrypt "bbb";
                ciena-common-yang:encrypt-path "/ciena-common-test/encryption-test-container/one-to-two-container-other";
                type uint8;
              }
              container inner-container {
                ciena-common-yang:encrypt "inner-container";
                ciena-common-yang:encrypt-path "/ciena-common-test/encryption-test-container/one-to-two-container-enc";
                leaf-list ccc {
                  ciena-common-yang:encrypt "ccc";
                  ciena-common-yang:encrypt-path "/ciena-common-test/encryption-test-container/one-to-two-container-enc/inner-container";
                  type uint8;
                }
                leaf ddd {
                  ciena-common-yang:encrypt "ddd";
                  ciena-common-yang:encrypt-path "/ciena-common-test/encryption-test-container/one-to-two-container-other";
                  type uint8;
                }
              }
            }
            container one-to-two-container-enc {
              ciena-common-yang:decrypt "one-to-two-container";
              ciena-common-yang:decrypt-path "/ciena-common-test/encryption-test-container";
              leaf aaa {
                type string {
                  ciena-common-yang:stringptr "true";
                }
                ciena-common-yang:decrypt "aaa";
                ciena-common-yang:decrypt-path "/ciena-common-test/encryption-test-container/one-to-two-container";
              }
              container inner-container {
                ciena-common-yang:decrypt "inner-container";
                ciena-common-yang:decrypt-path "/ciena-common-test/encryption-test-container/one-to-two-container";
                leaf-list ccc {
                  type string {
                    ciena-common-yang:stringptr "true";
                  }
                  ciena-common-yang:decrypt "ccc";
                  ciena-common-yang:decrypt-path "/ciena-common-test/encryption-test-container/one-to-two-container/inner-container";
                }
              }
            }
            container one-to-two-container-other {
              leaf-list bbb {
                ciena-common-yang:decrypt "bbb";
                ciena-common-yang:decrypt-path "/ciena-common-test/encryption-test-container/one-to-two-container";
                type string {
                  ciena-common-yang:stringptr "true";
                }
              }
              leaf ddd {
                ciena-common-yang:decrypt "ddd";
                ciena-common-yang:decrypt-path "/ciena-common-test/encryption-test-container/one-to-two-container/inner-container";
                type string {
                  ciena-common-yang:stringptr "true";
                }
              }
              leaf fff {
                type uint8;
              }
            }
            list nested-list {
              ciena-common-yang:encrypt "nested-list-enc";
              ciena-common-yang:encrypt-path "/ciena-common-test/encryption-test-container";
              description
                "test nested list encryption";
              key "name";
              leaf name {
                ciena-common-yang:encrypt "name";
                ciena-common-yang:encrypt-path "/ciena-common-test/encryption-test-container/nested-list-enc";
                type stringptr;
              }
              leaf aaa {
                ciena-common-yang:encrypt "aaa";
                ciena-common-yang:encrypt-path "/ciena-common-test/encryption-test-container/nested-list-enc";
                type uint8;
              }
              list inner-list {
                ciena-common-yang:encrypt "inner-list";
                ciena-common-yang:encrypt-path "/ciena-common-test/encryption-test-container/nested-list-enc";
                key "index";
                leaf index {
                  ciena-common-yang:encrypt "index";
                  ciena-common-yang:encrypt-path "/ciena-common-test/encryption-test-container/nested-list-enc/inner-list";
                  type uint8;
                }
                leaf-list ccc {
                  ciena-common-yang:encrypt "ccc";
                  ciena-common-yang:encrypt-path "/ciena-common-test/encryption-test-container/nested-list-enc/inner-list";
                  type string;
                }
              }
            }
            list nested-list-enc {
              ciena-common-yang:decrypt "nested-list";
              ciena-common-yang:decrypt-path "/ciena-common-test/encryption-test-container";
              key "name";
              leaf name {
                type string {
                  ciena-common-yang:stringptr "true";
                }
                ciena-common-yang:decrypt "name";
                ciena-common-yang:decrypt-path "/ciena-common-test/encryption-test-container/nested-list";
              }
              leaf aaa {
                type string {
                  ciena-common-yang:stringptr "true";
                }
                ciena-common-yang:decrypt "aaa";
                ciena-common-yang:decrypt-path "/ciena-common-test/encryption-test-container/nested-list";
              }
              list inner-list {
                ciena-common-yang:decrypt "inner-list";
                ciena-common-yang:decrypt-path "/ciena-common-test/encryption-test-container/nested-list";
                key "index";
                leaf index {
                  type string {
                    ciena-common-yang:stringptr "true";
                  }
                  ciena-common-yang:decrypt "index";
                  ciena-common-yang:decrypt-path "/ciena-common-test/encryption-test-container/nested-list/inner-list";
                }
                leaf-list ccc {
                  type string {
                    ciena-common-yang:stringptr "true";
                  }
                  ciena-common-yang:decrypt "ccc";
                  ciena-common-yang:decrypt-path "/ciena-common-test/encryption-test-container/nested-list/inner-list";
                }
              }
            }
            container other {
              leaf ccc {
                type string;
              }
            }
            container user-defined-leaves {
              description
                "selected leaves encryption container";
              leaf a {
                ciena-common-yang:encrypt "x";
                ciena-common-yang:encrypt-path "/ciena-common-test/encryption-test-container/user-defined-leaves-encrypted";
                type string;
              }
              leaf b {
                type string;
              }
            }
            container user-defined-leaves-encrypted {
              leaf x {
                ciena-common-yang:decrypt "a";
                ciena-common-yang:decrypt-path "/ciena-common-test/encryption-test-container/user-defined-leaves";
                type string;
              }
            }
            list nested-list-leaf-encryption {
              key "name";
              leaf name {
                type string;
              }
              leaf x {
                ciena-common-yang:encrypt "x-enc";
                ciena-common-yang:encrypt-path "/ciena-common-test/encryption-test-container/nested-list-leaf-encryption";
                type string;
              }
              leaf x-enc {
                type string {
                  ciena-common-yang:stringptr "true";
                }
                ciena-common-yang:decrypt "x";
                ciena-common-yang:decrypt-path "/ciena-common-test/encryption-test-container/nested-list-leaf-encryption";
              }
              list inner {
                key "index";
                leaf index {
                  type uint8;
                }
                leaf u {
                  ciena-common-yang:encrypt "u-enc";
                  ciena-common-yang:encrypt-path "/ciena-common-test/encryption-test-container/nested-list-leaf-encryption/inner";
                  type string;
                }
                leaf u-enc {
                  type string {
                    ciena-common-yang:stringptr "true";
                  }
                  ciena-common-yang:decrypt "u";
                  ciena-common-yang:decrypt-path "/ciena-common-test/encryption-test-container/nested-list-leaf-encryption/inner";
                }
              }
            }
            list encryption-list-test {
              key "key1 key2";
              leaf key1 {
                type stringptr;
              }
              leaf key2 {
                type typetest;
              }
              container leaf-list-test {
                leaf-list binary-test {
                  ciena-common-yang:encrypt "binary-test-encrypted";
                  ciena-common-yang:encrypt-path "/ciena-common-test/encryption-test-container/encryption-list-test/leaf-list-test";
                  type binary;
                }
                leaf-list binary-test-encrypted {
                  type string {
                    ciena-common-yang:stringptr "true";
                  }
                  ciena-common-yang:decrypt "binary-test";
                  ciena-common-yang:decrypt-path "/ciena-common-test/encryption-test-container/encryption-list-test/leaf-list-test";
                }
                leaf-list bits-test {
                  ciena-common-yang:encrypt "bits-test-encrypted";
                  ciena-common-yang:encrypt-path "/ciena-common-test/encryption-test-container/encryption-list-test/leaf-list-test";
                  type bits {
                    bit disable-nagle {
                      position 0;
                    }
                    bit auto-sense-speed {
                      position 1;
                    }
                  }
                }
                leaf-list bits-test-encrypted {
                  type string {
                    ciena-common-yang:stringptr "true";
                  }
                  ciena-common-yang:decrypt "bits-test";
                  ciena-common-yang:decrypt-path "/ciena-common-test/encryption-test-container/encryption-list-test/leaf-list-test";
                }
                leaf-list boolean-test {
                  ciena-common-yang:encrypt "boolean-test-encrypted";
                  ciena-common-yang:encrypt-path "/ciena-common-test/encryption-test-container/encryption-list-test/leaf-list-test";
                  type boolean;
                }
                leaf-list boolean-test-encrypted {
                  type string {
                    ciena-common-yang:stringptr "true";
                  }
                  ciena-common-yang:decrypt "boolean-test";
                  ciena-common-yang:decrypt-path "/ciena-common-test/encryption-test-container/encryption-list-test/leaf-list-test";
                }
                leaf-list decimal64-test {
                  ciena-common-yang:encrypt "decimal64-test-encrypted";
                  ciena-common-yang:encrypt-path "/ciena-common-test/encryption-test-container/encryption-list-test/leaf-list-test";
                  type decimal64 {
                    fraction-digits 10;
                  }
                }
                leaf-list decimal64-test-encrypted {
                  type string {
                    ciena-common-yang:stringptr "true";
                  }
                  ciena-common-yang:decrypt "decimal64-test";
                  ciena-common-yang:decrypt-path "/ciena-common-test/encryption-test-container/encryption-list-test/leaf-list-test";
                }
                leaf-list empty-test {
                  ciena-common-yang:encrypt "empty-test-encrypted";
                  ciena-common-yang:encrypt-path "/ciena-common-test/encryption-test-container/encryption-list-test/leaf-list-test";
                  type empty;
                }
                leaf-list empty-test-encrypted {
                  type string {
                    ciena-common-yang:stringptr "true";
                  }
                  ciena-common-yang:decrypt "empty-test";
                  ciena-common-yang:decrypt-path "/ciena-common-test/encryption-test-container/encryption-list-test/leaf-list-test";
                }
                leaf-list enumeration-test {
                  ciena-common-yang:encrypt "enumeration-test-encrypted";
                  ciena-common-yang:encrypt-path "/ciena-common-test/encryption-test-container/encryption-list-test/leaf-list-test";
                  type enumeration {
                    enum test-a;
                    enum test-b;
                    enum test-c;
                    enum map;
                  }
                }
                leaf-list enumeration-test-encrypted {
                  type string {
                    ciena-common-yang:stringptr "true";
                  }
                  ciena-common-yang:decrypt "enumeration-test";
                  ciena-common-yang:decrypt-path "/ciena-common-test/encryption-test-container/encryption-list-test/leaf-list-test";
                }
                leaf-list identityref-test {
                  ciena-common-yang:encrypt "identityref-test-encrypted";
                  ciena-common-yang:encrypt-path "/ciena-common-test/encryption-test-container/encryption-list-test/leaf-list-test";
                  type identityref {
                    base test:crypto-alg;
                  }
                }
                leaf-list identityref-test-encrypted {
                  type string {
                    ciena-common-yang:stringptr "true";
                  }
                  ciena-common-yang:decrypt "identityref-test";
                  ciena-common-yang:decrypt-path "/ciena-common-test/encryption-test-container/encryption-list-test/leaf-list-test";
                }
                leaf-list instance-identifier-test {
                  ciena-common-yang:encrypt "instance-identifier-test-encrypted";
                  ciena-common-yang:encrypt-path "/ciena-common-test/encryption-test-container/encryption-list-test/leaf-list-test";
                  type instance-identifier;
                }
                leaf-list instance-identifier-test-encrypted {
                  type string {
                    ciena-common-yang:stringptr "true";
                  }
                  ciena-common-yang:decrypt "instance-identifier-test";
                  ciena-common-yang:decrypt-path "/ciena-common-test/encryption-test-container/encryption-list-test/leaf-list-test";
                }
                leaf-list leafref-test {
                  ciena-common-yang:encrypt "leafref-test-encrypted";
                  ciena-common-yang:encrypt-path "/ciena-common-test/encryption-test-container/encryption-list-test/leaf-list-test";
                  type leafref {
                    path "/test:red/test:blue/test:b";
                  }
                }
                leaf-list leafref-test-encrypted {
                  type string {
                    ciena-common-yang:stringptr "true";
                  }
                  ciena-common-yang:decrypt "leafref-test";
                  ciena-common-yang:decrypt-path "/ciena-common-test/encryption-test-container/encryption-list-test/leaf-list-test";
                }
                leaf-list stringptr-test {
                  ciena-common-yang:encrypt "stringptr-test-encrypted";
                  ciena-common-yang:encrypt-path "/ciena-common-test/encryption-test-container/encryption-list-test/leaf-list-test";
                  type stringptr;
                }
                leaf-list stringptr-test-encrypted {
                  type string {
                    ciena-common-yang:stringptr "true";
                  }
                  ciena-common-yang:decrypt "stringptr-test";
                  ciena-common-yang:decrypt-path "/ciena-common-test/encryption-test-container/encryption-list-test/leaf-list-test";
                }
                leaf-list string-test {
                  ciena-common-yang:encrypt "string-test-encrypted";
                  ciena-common-yang:encrypt-path "/ciena-common-test/encryption-test-container/encryption-list-test/leaf-list-test";
                  type string;
                }
                leaf-list string-test-encrypted {
                  type string {
                    ciena-common-yang:stringptr "true";
                  }
                  ciena-common-yang:decrypt "string-test";
                  ciena-common-yang:decrypt-path "/ciena-common-test/encryption-test-container/encryption-list-test/leaf-list-test";
                }
                leaf-list uint8-test {
                  ciena-common-yang:encrypt "uint8-test-encrypted";
                  ciena-common-yang:encrypt-path "/ciena-common-test/encryption-test-container/encryption-list-test/leaf-list-test";
                  type uint8;
                }
                leaf-list uint8-test-encrypted {
                  type string {
                    ciena-common-yang:stringptr "true";
                  }
                  ciena-common-yang:decrypt "uint8-test";
                  ciena-common-yang:decrypt-path "/ciena-common-test/encryption-test-container/encryption-list-test/leaf-list-test";
                }
                leaf-list union-test {
                  ciena-common-yang:encrypt "union-test-encrypted";
                  ciena-common-yang:encrypt-path "/ciena-common-test/encryption-test-container/encryption-list-test/leaf-list-test";
                  type union {
                    type int32;
                    type enumeration {
                      enum unbounded;
                    }
                  }
                }
                leaf-list union-test-encrypted {
                  type string {
                    ciena-common-yang:stringptr "true";
                  }
                  ciena-common-yang:decrypt "union-test";
                  ciena-common-yang:decrypt-path "/ciena-common-test/encryption-test-container/encryption-list-test/leaf-list-test";
                }
              }
              container leaf-test {
                leaf binary-test {
                  ciena-common-yang:encrypt "binary-test-encrypted";
                  ciena-common-yang:encrypt-path "/ciena-common-test/encryption-test-container/encryption-list-test/leaf-test";
                  type binary;
                  ciena-common-yang:sensitive "true";
                }
                leaf binary-test-encrypted {
                  type string {
                    ciena-common-yang:stringptr "true";
                  }
                  ciena-common-yang:decrypt "binary-test";
                  ciena-common-yang:decrypt-path "/ciena-common-test/encryption-test-container/encryption-list-test/leaf-test";
                  ciena-common-yang:sensitive "true";
                }
                leaf bits-test {
                  ciena-common-yang:encrypt "bits-test-encrypted";
                  ciena-common-yang:encrypt-path "/ciena-common-test/encryption-test-container/encryption-list-test/leaf-test";
                  ciena-common-yang:sensitive "true";
                  type bits {
                    bit apple {
                      position 0;
                    }
                    bit orange {
                      position 1;
                    }
                    bit banana {
                      position 2;
                    }
                  }
                }
                leaf bits-test-encrypted {
                  type string {
                    ciena-common-yang:stringptr "true";
                  }
                  ciena-common-yang:decrypt "bits-test";
                  ciena-common-yang:decrypt-path "/ciena-common-test/encryption-test-container/encryption-list-test/leaf-test";
                  ciena-common-yang:sensitive "true";
                }
                leaf offset-bits-test {
                  ciena-common-yang:encrypt "offset-bits-test-encrypted";
                  ciena-common-yang:encrypt-path "/ciena-common-test/encryption-test-container/encryption-list-test/leaf-test";
                  ciena-common-yang:sensitive "true";
                  type bits {
                    bit apple {
                      position 3;
                    }
                    bit orange {
                      position 5;
                    }
                    bit banana {
                      position 7;
                    }
                  }
                }
                leaf offset-bits-test-encrypted {
                  type string {
                    ciena-common-yang:stringptr "true";
                  }
                  ciena-common-yang:decrypt "offset-bits-test";
                  ciena-common-yang:decrypt-path "/ciena-common-test/encryption-test-container/encryption-list-test/leaf-test";
                  ciena-common-yang:sensitive "true";
                }
                leaf boolean-test {
                  ciena-common-yang:encrypt "boolean-test-encrypted";
                  ciena-common-yang:encrypt-path "/ciena-common-test/encryption-test-container/encryption-list-test/leaf-test";
                  ciena-common-yang:sensitive "true";
                  type boolean;
                }
                leaf boolean-test-encrypted {
                  type string {
                    ciena-common-yang:stringptr "true";
                  }
                  ciena-common-yang:decrypt "boolean-test";
                  ciena-common-yang:decrypt-path "/ciena-common-test/encryption-test-container/encryption-list-test/leaf-test";
                  ciena-common-yang:sensitive "true";
                }
                leaf decimal64-test {
                  ciena-common-yang:encrypt "decimal64-test-encrypted";
                  ciena-common-yang:encrypt-path "/ciena-common-test/encryption-test-container/encryption-list-test/leaf-test";
                  ciena-common-yang:sensitive "true";
                  type decimal64 {
                    fraction-digits 2;
                  }
                }
                leaf decimal64-test-encrypted {
                  type string {
                    ciena-common-yang:stringptr "true";
                  }
                  ciena-common-yang:decrypt "decimal64-test";
                  ciena-common-yang:decrypt-path "/ciena-common-test/encryption-test-container/encryption-list-test/leaf-test";
                  ciena-common-yang:sensitive "true";
                }
                leaf empty-test {
                  ciena-common-yang:encrypt "empty-test-encrypted";
                  ciena-common-yang:encrypt-path "/ciena-common-test/encryption-test-container/encryption-list-test/leaf-test";
                  ciena-common-yang:sensitive "true";
                  type empty;
                }
                leaf empty-test-encrypted {
                  type string {
                    ciena-common-yang:stringptr "true";
                  }
                  ciena-common-yang:decrypt "empty-test";
                  ciena-common-yang:decrypt-path "/ciena-common-test/encryption-test-container/encryption-list-test/leaf-test";
                  ciena-common-yang:sensitive "true";
                }
                leaf enumeration-test {
                  ciena-common-yang:encrypt "enumeration-test-encrypted";
                  ciena-common-yang:encrypt-path "/ciena-common-test/encryption-test-container/encryption-list-test/leaf-test";
                  ciena-common-yang:sensitive "true";
                  type enumeration {
                    enum test-1;
                    enum test-2;
                    enum test-3;
                  }
                }
                leaf enumeration-test-encrypted {
                  type string {
                    ciena-common-yang:stringptr "true";
                  }
                  ciena-common-yang:decrypt "enumeration-test";
                  ciena-common-yang:decrypt-path "/ciena-common-test/encryption-test-container/encryption-list-test/leaf-test";
                  ciena-common-yang:sensitive "true";
                }
                leaf enumeration-extended-test {
                  ciena-common-yang:encrypt "enumeration-extended-test-encrypted";
                  ciena-common-yang:encrypt-path "/ciena-common-test/encryption-test-container/encryption-list-test/leaf-test";
                  ciena-common-yang:sensitive "true";
                  type enumeration {
                    enum forty-one {
                      value 41;
                    }
                    enum ten {
                      value 10;
                    }
                    enum seven {
                      value 7;
                    }
                  }
                }
                leaf enumeration-extended-test-encrypted {
                  type string {
                    ciena-common-yang:stringptr "true";
                  }
                  ciena-common-yang:decrypt "enumeration-extended-test";
                  ciena-common-yang:decrypt-path "/ciena-common-test/encryption-test-container/encryption-list-test/leaf-test";
                  ciena-common-yang:sensitive "true";
                }
                leaf identityref-test {
                  ciena-common-yang:encrypt "identifyref-test-encrypted";
                  ciena-common-yang:encrypt-path "/ciena-common-test/encryption-test-container/encryption-list-test/leaf-test";
                  ciena-common-yang:sensitive "true";
                  type identityref {
                    base test:crypto-alg;
                  }
                }
                leaf identifyref-test-encrypted {
                  type string {
                    ciena-common-yang:stringptr "true";
                  }
                  ciena-common-yang:decrypt "identityref-test";
                  ciena-common-yang:decrypt-path "/ciena-common-test/encryption-test-container/encryption-list-test/leaf-test";
                  ciena-common-yang:sensitive "true";
                }
                leaf instance-identifier-test {
                  ciena-common-yang:encrypt "instance-identifier-test-encrypted";
                  ciena-common-yang:encrypt-path "/ciena-common-test/encryption-test-container/encryption-list-test/leaf-test";
                  ciena-common-yang:sensitive "true";
                  type instance-identifier;
                }
                leaf instance-identifier-test-encrypted {
                  type string {
                    ciena-common-yang:stringptr "true";
                  }
                  ciena-common-yang:decrypt "instance-identifier-test";
                  ciena-common-yang:decrypt-path "/ciena-common-test/encryption-test-container/encryption-list-test/leaf-test";
                  ciena-common-yang:sensitive "true";
                }
                leaf int64-test {
                  ciena-common-yang:encrypt "int64-test-encrypted";
                  ciena-common-yang:encrypt-path "/ciena-common-test/encryption-test-container/encryption-list-test/leaf-test";
                  ciena-common-yang:sensitive "true";
                  type int64;
                }
                leaf int64-test-encrypted {
                  type string {
                    ciena-common-yang:stringptr "true";
                  }
                  ciena-common-yang:decrypt "int64-test";
                  ciena-common-yang:decrypt-path "/ciena-common-test/encryption-test-container/encryption-list-test/leaf-test";
                  ciena-common-yang:sensitive "true";
                }
                leaf leafref-test {
                  ciena-common-yang:encrypt "leafref-test-encrypted";
                  ciena-common-yang:encrypt-path "/ciena-common-test/encryption-test-container/encryption-list-test/leaf-test";
                  ciena-common-yang:sensitive "true";
                  type leafref {
                    path "/test:red/test:blue/test:c";
                  }
                }
                leaf leafref-test-encrypted {
                  type string {
                    ciena-common-yang:stringptr "true";
                  }
                  ciena-common-yang:decrypt "leafref-test";
                  ciena-common-yang:decrypt-path "/ciena-common-test/encryption-test-container/encryption-list-test/leaf-test";
                  ciena-common-yang:sensitive "true";
                }
                leaf stringptr-test {
                  ciena-common-yang:encrypt "stringptr-test-encrypted";
                  ciena-common-yang:encrypt-path "/ciena-common-test/encryption-test-container/encryption-list-test/leaf-test";
                  ciena-common-yang:sensitive "true";
                  type string {
                    ciena-common-yang:stringptr "true";
                  }
                }
                leaf stringptr-test-encrypted {
                  type string {
                    ciena-common-yang:stringptr "true";
                  }
                  ciena-common-yang:decrypt "stringptr-test";
                  ciena-common-yang:decrypt-path "/ciena-common-test/encryption-test-container/encryption-list-test/leaf-test";
                  ciena-common-yang:sensitive "true";
                }
                leaf string-test {
                  ciena-common-yang:encrypt "string-test-encrypted";
                  ciena-common-yang:encrypt-path "/ciena-common-test/encryption-test-container/encryption-list-test/leaf-test";
                  ciena-common-yang:sensitive "true";
                  type string {
                    length "0..15";
                  }
                }
                leaf string-test-encrypted {
                  type string {
                    ciena-common-yang:stringptr "true";
                  }
                  ciena-common-yang:decrypt "string-test";
                  ciena-common-yang:decrypt-path "/ciena-common-test/encryption-test-container/encryption-list-test/leaf-test";
                  ciena-common-yang:sensitive "true";
                }
                leaf union-test {
                  ciena-common-yang:encrypt "union-test-encrypted";
                  ciena-common-yang:encrypt-path "/ciena-common-test/encryption-test-container/encryption-list-test/leaf-test";
                  type union {
                    type int32;
                    type enumeration {
                      enum unbounded;
                    }
                  }
                  ciena-common-yang:sensitive "true";
                }
                leaf union-test-encrypted {
                  type string {
                    ciena-common-yang:stringptr "true";
                  }
                  ciena-common-yang:decrypt "union-test";
                  ciena-common-yang:decrypt-path "/ciena-common-test/encryption-test-container/encryption-list-test/leaf-test";
                  ciena-common-yang:sensitive "true";
                }
              }
            }
          }
          container toggle-sleep {
            container input {
              ciena-common-yang:containerptr "true";
            }
          }
          uses grouping-test;
          container rpc-test-empty;
          container rpc-test-no-output {
            container input {
              ciena-common-yang:containerptr "true";
            }
          }
          container rpc-test-no-input {
            container output {
              ciena-common-yang:containerptr "true";
            }
          }
          container rpc-test {
            container input {
              ciena-common-yang:containerptr "true";
            }
            container output {
              ciena-common-yang:containerptr "true";
            }
          }
          container rpc-trigger-encryption-set {
            container input {
              ciena-common-yang:containerptr "true";
            }
          }
          container notification-test {
            ciena-common-yang:containerptr "true";
            uses red-blue-group;
          }
          container encryption-notification-test {
            ciena-common-yang:containerptr "true";
            container X {
              leaf y {
                ciena-common-yang:encrypt "y-encrypted";
                ciena-common-yang:encrypt-path "/ciena-common-test/encryption-notification-test/X";
                type string;
              }
              leaf y-encrypted {
                type string {
                  ciena-common-yang:stringptr "true";
                }
                ciena-common-yang:decrypt "y";
                ciena-common-yang:decrypt-path "/ciena-common-test/encryption-notification-test/X";
              }
            }
          }
          container stack-push {
            description
              "Push into thread specific stack";
            container input {
              ciena-common-yang:containerptr "true";
            }
            container output {
              ciena-common-yang:containerptr "true";
            }
          }
          container stack-pop {
            description
              "Pop from thread specific stack";
            container input {
              ciena-common-yang:containerptr "true";
            }
            container output {
              ciena-common-yang:containerptr "true";
            }
          }
          container stack-get {
            description
              "Get pushed data for an attribute";
            container input {
              ciena-common-yang:containerptr "true";
            }
            container output {
              ciena-common-yang:containerptr "true";
            }
          }
          container stack-merge {
            description
              "Merge thread specific stacks";
            container input {
              ciena-common-yang:containerptr "true";
            }
            container output {
              ciena-common-yang:containerptr "true";
            }
          }
          container return-code-set {
            description
              "Set the return code in the response";
            container input {
              ciena-common-yang:containerptr "true";
            }
            container output {
              ciena-common-yang:containerptr "true";
            }
          }
          container validate-test {
            description
              "Set the return code in the response";
            container input {
              ciena-common-yang:containerptr "true";
            }
            container output {
              ciena-common-yang:containerptr "true";
            }
          }
          container test-deadline-timeout {
            description
              "Take input as timeout and handler will wait till this time
                based on test scenario type and return pass as true/false.";
            container input {
              ciena-common-yang:containerptr "true";
            }
            container output {
              ciena-common-yang:containerptr "true";
            }
          }
          container mount_test_a {
            list b {
              key "name";
              leaf name {
                type string;
              }
              anyxml c;
              container anyxml-mount {
                ciena-common-yang:mount-start "ciena-common-test";
                ciena-common-yang:mount-end "ciena-common-test";
              }
              anydata d;
              container anydata-mount {
                ciena-common-yang:mount-start "ciena-common-test";
                ciena-common-yang:mount-end "ciena-common-test";
              }
            }
          }
          container mount_test_b {
            list b {
              key "name";
              leaf name {
                type string;
              }
              anyxml c;
              container anyxml-mount {
                ciena-common-yang:mount-start "ciena-common-test-list";
                uses ciena-common-test-list:ciena-common-test-list-mount-data-actions-notifs-as-cont;
                ciena-common-yang:mount-end "ciena-common-test-list";
              }
            }
          }
          container i_love_big_data {
            list big_list {
              key "name";
              leaf name {
                type uint64;
              }
              leaf some_data {
                type decimal64 {
                  fraction-digits 10;
                }
              }
            }
          }
          container i_love_instance_id_for_keys {
            list some_list {
              key "instance_id_name";
              leaf instance_id_name {
                type instance-identifier;
              }
              leaf some_data {
                type decimal64 {
                  fraction-digits 10;
                }
              }
              container some_container {
                description
                  "Dummy container to have same context as parent";
                list sub_list {
                  description
                    "Another keyed list to have instance-id in parent context";
                  key "some_sub_key";
                  leaf some_sub_key {
                    type uint32;
                  }
                  leaf some_sub_leaf {
                    type uint32;
                  }
                }
              }
            }
          }
          container test-restconf-a {
            leaf b {
              type string;
            }
            leaf c {
              type uint8;
            }
            leaf awesome-wildcard-field {
              type string;
            }
            list d {
              key "name";
              leaf name {
                type string;
              }
              leaf test-state {
                type boolean;
              }
              container awesome-wildcard-field {
                leaf awesome-wildcard-field {
                  type boolean;
                }
                leaf awesome-wildcard-field-not {
                  type string;
                }
              }
              list e {
                key "index";
                leaf index {
                  type uint8;
                }
                leaf name {
                  type string;
                }
                list awesome-wildcard-field {
                  key "awesome-wildcard-field";
                  leaf awesome-wildcard-field {
                    type uint8;
                  }
                }
              }
            }
          }
          container test-colon-container {
            leaf enumeration-test {
              ciena-common-yang:sensitive "true";
              type enumeration {
                enum "1:n Mux type";
                enum "2:n Mux type";
                enum "3:n Mux type";
              }
            }
          }
          container multi-augment;
          container ddy-test-server-config {
            leaf handle-complete-transaction {
              type enumeration {
                enum none {
                  description
                    "complete-transaction not handled at all";
                }
                enum local {
                  description
                    "complete-transaction bound to local service";
                }
                enum service {
                  description
                    "complete-transaction bound to ddy-test-server";
                }
              }
              default "none";
            }
          }
          container client-activations {
            description
              "Sometimes you are testing something and you just need a simple way to execute a task.";
            container input {
              ciena-common-yang:containerptr "true";
            }
          }
          ciena-common-yang:mount-end "ciena-common-test";
        }
        anydata d;
        container anydata-mount {
          ciena-common-yang:mount-start "ciena-common-test";
          container string-based-return-code-list {
            config false;
            description
              "List of errors in case of command failure";
            list return-code-list {
              leaf instance {
                type string {
                  ciena-common-yang:stringptr "true";
                }
                description
                  "The instance to which the error code applies.";
              }
              leaf error {
                type string;
              }
            }
          }
          uses red-blue-group;
          uses blue-yellow-group;
          container white {
            uses abc_group;
            container cont1 {
              uses abc_group;
            }
            container cont2 {
              uses abc_group;
            }
            container cont3 {
              uses abc_group;
            }
            container cont4 {
              uses abc_group;
            }
            list list1 {
              key "k";
              leaf k {
                type uint8;
              }
              uses abc_group;
            }
          }
          container validation-test {
            uses abc_validate_group;
          }
          container to-pointer-test {
            container a {
              leaf string-test {
                type string;
              }
            }
          }
          list to-pointer-test2 {
            key "first-key";
            leaf first-key {
              type uint8;
            }
            list second-list {
              key "second-key";
              leaf second-key {
                type uint8;
              }
              leaf second-string {
                type string;
              }
              container second-container {
                leaf second-container-string {
                  type string;
                }
              }
            }
          }
          container nested-container {
            container cone {
              leaf a {
                type uint8;
                default "1";
              }
              leaf b {
                type uint8;
                default "2";
              }
              leaf c {
                type uint8;
                default "3";
              }
            }
            container ctwo {
              config false;
              leaf d {
                type uint8;
              }
              leaf e {
                type uint8;
              }
              leaf f {
                type uint8;
              }
            }
          }
          container read-only {
            config false;
            uses red-blue-group;
            container name {
              container collision {
                leaf test {
                  type uint8;
                }
                container child1 {
                  container child2 {
                    leaf test {
                      type uint8;
                    }
                  }
                }
              }
            }
            container name-collision {
              leaf test {
                type uint8;
              }
              container child1 {
                container child2 {
                  leaf test {
                    type uint8;
                  }
                }
              }
            }
          }
          container remove-via-deviation {
            uses red-blue-group;
          }
          uses ordered-lists-group;
          container simple-deadline-test {
            uses deadline-group;
          }
          container simple-test-container {
            ciena-common-yang:containerptr "true";
            list keys-only-list {
              key "name";
              leaf name {
                type string;
              }
            }
            leaf other-attribute {
              type string;
            }
            container leaf-test {
              leaf string-test {
                ciena-common-yang:encrypt "string-test-encrypted";
                ciena-common-yang:encrypt-path "/ciena-common-test/simple-test-container/leaf-test";
                type string;
              }
              leaf string-test-encrypted {
                type string {
                  ciena-common-yang:stringptr "true";
                }
                ciena-common-yang:decrypt "string-test";
                ciena-common-yang:decrypt-path "/ciena-common-test/simple-test-container/leaf-test";
              }
              leaf uint8-test {
                type uint8;
              }
            }
            container presence-test {
              presence "presense test container";
            }
            container presence-test-2 {
              choice start-time {
                mandatory true;
                container immediate {
                  presence "Start the measurement session immediately.";
                }
                leaf relative {
                  type string;
                }
                leaf absolute {
                  type string;
                }
              }
            }
            list outter {
              key "index";
              leaf index {
                type uint8;
              }
              min-elements 2;
              max-elements 3;
              list inner {
                key "name";
                leaf name {
                  type string;
                }
                max-elements 2;
                leaf value {
                  type uint16;
                }
              }
              leaf-list boolean-leaf-list {
                type boolean;
                max-elements 3;
                min-elements 2;
              }
              leaf mode {
                type uint8 {
                  range "0..10";
                }
              }
            }
            list first {
              key "key1 key2";
              leaf key1 {
                type uint8;
              }
              leaf key2 {
                type string;
              }
              list second {
                key "key1 key2";
                leaf key1 {
                  type uint8;
                }
                leaf key2 {
                  type string;
                }
                list third {
                  key "key1";
                  leaf key1 {
                    type uint8;
                  }
                  container red {
                    container blue {
                      leaf a {
                        type string;
                      }
                      leaf b {
                        type string;
                      }
                    }
                    leaf yellow-leaf {
                      type string;
                    }
                    anyxml config;
                  }
                }
              }
            }
          }
          container list-keys {
            list bits-key {
              key "bit";
              leaf bit {
                type bits {
                  bit x;
                  bit y;
                  bit z;
                }
              }
            }
          }
          container identity-test {
            leaf base-test {
              type identityref {
                base test:crypto-alg;
              }
            }
            leaf mid-level-test {
              type identityref {
                base test:des;
              }
            }
            leaf top-test {
              type identityref {
                base test:des3;
              }
            }
            leaf external-test {
              type identityref {
                base ciena-common-yang:error-does-not-exist;
              }
            }
          }
          container encryption-test-container {
            container container-generate-at-abs-path-enc {
              ciena-common-yang:decrypt "container-generate-at-abs-path";
              ciena-common-yang:decrypt-path "/ciena-common-test/encryption-test-container";
              leaf a {
                type string {
                  ciena-common-yang:stringptr "true";
                }
                ciena-common-yang:decrypt "a";
                ciena-common-yang:decrypt-path "/ciena-common-test/encryption-test-container/container-generate-at-abs-path";
              }
              container b {
                ciena-common-yang:decrypt "b";
                ciena-common-yang:decrypt-path "/ciena-common-test/encryption-test-container/container-generate-at-abs-path";
                leaf c {
                  type string {
                    ciena-common-yang:stringptr "true";
                  }
                  ciena-common-yang:decrypt "c";
                  ciena-common-yang:decrypt-path "/ciena-common-test/encryption-test-container/container-generate-at-abs-path/b";
                }
              }
              config false;
            }
            list encryption-mount-test {
              key "name";
              leaf name {
                type string;
              }
              container data {
                ciena-common-yang:mount-start "ciena-common-test";
                ciena-common-yang:mount-end "ciena-common-test";
              }
            }
            list instance {
              key "name";
              leaf name {
                type string;
              }
              container result {
                ciena-common-yang:encrypt "container-1";
                ciena-common-yang:encrypt-path "/ciena-common-test/encryption-test-container/instance";
                list amp {
                  ciena-common-yang:encrypt "amp";
                  ciena-common-yang:encrypt-path "/ciena-common-test/encryption-test-container/instance/container-1";
                  key "amp_name";
                  leaf amp_name {
                    ciena-common-yang:encrypt "amp_name";
                    ciena-common-yang:encrypt-path "/ciena-common-test/encryption-test-container/instance/container-1/amp";
                    type string;
                  }
                  list measurement-no-power {
                    ciena-common-yang:encrypt "measurement-no-power";
                    ciena-common-yang:encrypt-path "/ciena-common-test/encryption-test-container/instance/container-1/amp";
                    description
                      "Power measurements of span measured with all channels blocked.";
                    key "index";
                    leaf index {
                      ciena-common-yang:encrypt "index";
                      ciena-common-yang:encrypt-path "/ciena-common-test/encryption-test-container/instance/container-1/amp/measurement-no-power";
                      type uint8;
                    }
                    leaf in-current-power {
                      ciena-common-yang:encrypt "in-current-power";
                      ciena-common-yang:encrypt-path "/ciena-common-test/encryption-test-container/instance/container-1/amp/measurement-no-power";
                      type decimal64 {
                        fraction-digits 1;
                      }
                    }
                    leaf in-min-power {
                      ciena-common-yang:encrypt "in-min-power";
                      ciena-common-yang:encrypt-path "/ciena-common-test/encryption-test-container/instance/container-1/amp/measurement-no-power";
                      type decimal64 {
                        fraction-digits 1;
                      }
                    }
                    config false;
                  }
                }
              }
              container container-1 {
                ciena-common-yang:decrypt "result";
                ciena-common-yang:decrypt-path "/ciena-common-test/encryption-test-container/instance";
                list amp {
                  ciena-common-yang:decrypt "amp";
                  ciena-common-yang:decrypt-path "/ciena-common-test/encryption-test-container/instance/result";
                  key "amp_name";
                  leaf amp_name {
                    type string {
                      ciena-common-yang:stringptr "true";
                    }
                    ciena-common-yang:decrypt "amp_name";
                    ciena-common-yang:decrypt-path "/ciena-common-test/encryption-test-container/instance/result/amp";
                  }
                  list measurement-no-power {
                    ciena-common-yang:decrypt "measurement-no-power";
                    ciena-common-yang:decrypt-path "/ciena-common-test/encryption-test-container/instance/result/amp";
                    key "index";
                    leaf index {
                      type string {
                        ciena-common-yang:stringptr "true";
                      }
                      ciena-common-yang:decrypt "index";
                      ciena-common-yang:decrypt-path "/ciena-common-test/encryption-test-container/instance/result/amp/measurement-no-power";
                    }
                    leaf in-current-power {
                      type string {
                        ciena-common-yang:stringptr "true";
                      }
                      ciena-common-yang:decrypt "in-current-power";
                      ciena-common-yang:decrypt-path "/ciena-common-test/encryption-test-container/instance/result/amp/measurement-no-power";
                    }
                    leaf in-min-power {
                      type string {
                        ciena-common-yang:stringptr "true";
                      }
                      ciena-common-yang:decrypt "in-min-power";
                      ciena-common-yang:decrypt-path "/ciena-common-test/encryption-test-container/instance/result/amp/measurement-no-power";
                    }
                    config false;
                  }
                }
              }
              list some-other-list {
                key "name";
                leaf name {
                  type string;
                }
                leaf measurement {
                  type uint8;
                }
              }
            }
            list key-in-grouping {
              ciena-common-yang:encrypt "key-in-grouping-encrypted";
              ciena-common-yang:encrypt-path "/ciena-common-test/encryption-test-container";
              description
                "test list key leaf definition can be provided by grouping";
              key "name";
              leaf name {
                ciena-common-yang:encrypt "name";
                ciena-common-yang:encrypt-path "/ciena-common-test/encryption-test-container/key-in-grouping-encrypted";
                type string;
              }
              leaf stats {
                ciena-common-yang:encrypt "stats";
                ciena-common-yang:encrypt-path "/ciena-common-test/encryption-test-container/key-in-grouping-encrypted";
                type uint32;
              }
            }
            list key-in-grouping-encrypted {
              ciena-common-yang:decrypt "key-in-grouping";
              ciena-common-yang:decrypt-path "/ciena-common-test/encryption-test-container";
              key "name";
              leaf name {
                type string {
                  ciena-common-yang:stringptr "true";
                }
                ciena-common-yang:decrypt "name";
                ciena-common-yang:decrypt-path "/ciena-common-test/encryption-test-container/key-in-grouping";
              }
              leaf stats {
                type string {
                  ciena-common-yang:stringptr "true";
                }
                ciena-common-yang:decrypt "stats";
                ciena-common-yang:decrypt-path "/ciena-common-test/encryption-test-container/key-in-grouping";
              }
            }
            list list-enc-generate-with-renamed-leaves {
              ciena-common-yang:encrypt "list-enc-generate-with-renamed-leaves-enc";
              ciena-common-yang:encrypt-path "/ciena-common-test/encryption-test-container";
              description
                "test list encryption with nested containers and leaves renamed";
              key "name";
              leaf name {
                ciena-common-yang:encrypt "name";
                ciena-common-yang:encrypt-path "/ciena-common-test/encryption-test-container/list-enc-generate-with-renamed-leaves-enc";
                type string;
              }
              leaf aaa {
                ciena-common-yang:encrypt "aaa-enc";
                ciena-common-yang:encrypt-path "/ciena-common-test/encryption-test-container/list-enc-generate-with-renamed-leaves-enc";
                type uint8;
                ciena-common-yang:sensitive "true";
              }
              container ddd {
                ciena-common-yang:encrypt "ddd-enc";
                ciena-common-yang:encrypt-path "/ciena-common-test/encryption-test-container/list-enc-generate-with-renamed-leaves-enc";
                leaf eee {
                  ciena-common-yang:encrypt "eee-enc";
                  ciena-common-yang:encrypt-path "/ciena-common-test/encryption-test-container/list-enc-generate-with-renamed-leaves-enc/ddd-enc";
                  type uint8;
                }
                leaf fff {
                  ciena-common-yang:encrypt "fff";
                  ciena-common-yang:encrypt-path "/ciena-common-test/encryption-test-container/list-enc-generate-with-renamed-leaves-enc/ddd-enc";
                  type uint8;
                }
                config false;
              }
            }
            list list-enc-generate-with-renamed-leaves-enc {
              ciena-common-yang:decrypt "list-enc-generate-with-renamed-leaves";
              ciena-common-yang:decrypt-path "/ciena-common-test/encryption-test-container";
              key "name";
              leaf name {
                type string {
                  ciena-common-yang:stringptr "true";
                }
                ciena-common-yang:decrypt "name";
                ciena-common-yang:decrypt-path "/ciena-common-test/encryption-test-container/list-enc-generate-with-renamed-leaves";
              }
              leaf aaa-enc {
                type string {
                  ciena-common-yang:stringptr "true";
                }
                ciena-common-yang:decrypt "aaa";
                ciena-common-yang:decrypt-path "/ciena-common-test/encryption-test-container/list-enc-generate-with-renamed-leaves";
                ciena-common-yang:sensitive "true";
              }
              container ddd-enc {
                ciena-common-yang:decrypt "ddd";
                ciena-common-yang:decrypt-path "/ciena-common-test/encryption-test-container/list-enc-generate-with-renamed-leaves";
                leaf eee-enc {
                  type string {
                    ciena-common-yang:stringptr "true";
                  }
                  ciena-common-yang:decrypt "eee";
                  ciena-common-yang:decrypt-path "/ciena-common-test/encryption-test-container/list-enc-generate-with-renamed-leaves/ddd";
                }
                leaf fff {
                  type string {
                    ciena-common-yang:stringptr "true";
                  }
                  ciena-common-yang:decrypt "fff";
                  ciena-common-yang:decrypt-path "/ciena-common-test/encryption-test-container/list-enc-generate-with-renamed-leaves/ddd";
                }
                config false;
              }
            }
            list list-generate-with-enc-path-for-leaves {
              ciena-common-yang:encrypt "list-generate-with-enc-path-for-leaves-enc";
              ciena-common-yang:encrypt-path "/ciena-common-test/encryption-test-container";
              description
                "test list encryption with some leaves having encryption-path and encryption-relative-path information";
              key "index";
              leaf index {
                ciena-common-yang:encrypt "index-enc";
                ciena-common-yang:encrypt-path "/ciena-common-test/encryption-test-container/list-generate-with-enc-path-for-leaves-enc";
                type uint8;
              }
              leaf ggg {
                ciena-common-yang:encrypt "ggg";
                ciena-common-yang:encrypt-path "/ciena-common-test/encryption-test-container/list-generate-with-enc-path-for-leaves-enc";
                type uint8;
              }
              container hhh {
                ciena-common-yang:encrypt "hhh";
                ciena-common-yang:encrypt-path "/ciena-common-test/encryption-test-container/list-generate-with-enc-path-for-leaves-enc";
                leaf iii {
                  ciena-common-yang:encrypt "iii-enc";
                  ciena-common-yang:encrypt-path "/ciena-common-test/encryption-test-container/list-generate-with-enc-path-for-leaves-enc/hhh";
                  type uint8;
                }
                leaf jjj {
                  ciena-common-yang:encrypt "none-existing-leaf";
                  ciena-common-yang:encrypt-path "/ciena-common-test/encryption-test-container/A/B";
                  type uint8;
                  ciena-common-yang:sensitive "true";
                }
                leaf kkk {
                  ciena-common-yang:encrypt "none-existing-leaf-2";
                  ciena-common-yang:encrypt-path "/ciena-common-test/encryption-test-container/A/B";
                  type uint8;
                  config false;
                  ciena-common-yang:sensitive "true";
                }
              }
            }
            list list-generate-with-enc-path-for-leaves-enc {
              ciena-common-yang:decrypt "list-generate-with-enc-path-for-leaves";
              ciena-common-yang:decrypt-path "/ciena-common-test/encryption-test-container";
              key "index-enc";
              leaf index-enc {
                type string {
                  ciena-common-yang:stringptr "true";
                }
                ciena-common-yang:decrypt "index";
                ciena-common-yang:decrypt-path "/ciena-common-test/encryption-test-container/list-generate-with-enc-path-for-leaves";
              }
              leaf ggg {
                type string {
                  ciena-common-yang:stringptr "true";
                }
                ciena-common-yang:decrypt "ggg";
                ciena-common-yang:decrypt-path "/ciena-common-test/encryption-test-container/list-generate-with-enc-path-for-leaves";
              }
              container hhh {
                ciena-common-yang:decrypt "hhh";
                ciena-common-yang:decrypt-path "/ciena-common-test/encryption-test-container/list-generate-with-enc-path-for-leaves";
                leaf iii-enc {
                  type string {
                    ciena-common-yang:stringptr "true";
                  }
                  ciena-common-yang:decrypt "iii";
                  ciena-common-yang:decrypt-path "/ciena-common-test/encryption-test-container/list-generate-with-enc-path-for-leaves/hhh";
                }
              }
            }
            container A {
              container B {
                leaf none-existing-leaf {
                  ciena-common-yang:decrypt "jjj";
                  ciena-common-yang:decrypt-path "/ciena-common-test/encryption-test-container/list-generate-with-enc-path-for-leaves/hhh";
                  type string {
                    ciena-common-yang:stringptr "true";
                  }
                  ciena-common-yang:sensitive "true";
                }
                leaf none-existing-leaf-2 {
                  ciena-common-yang:decrypt "kkk";
                  ciena-common-yang:decrypt-path "/ciena-common-test/encryption-test-container/list-generate-with-enc-path-for-leaves/hhh";
                  type string {
                    ciena-common-yang:stringptr "true";
                  }
                  ciena-common-yang:sensitive "true";
                  config false;
                }
                leaf y {
                  type string {
                    ciena-common-yang:stringptr "true";
                  }
                }
                leaf z {
                  type uint8;
                }
              }
            }
            container container-generate-as-sibling {
              ciena-common-yang:encrypt "container-generate-as-sibling-enc";
              ciena-common-yang:encrypt-path "/ciena-common-test/encryption-test-container";
              description
                "test simple container encryption default generating as siblings";
              leaf a {
                ciena-common-yang:encrypt "a";
                ciena-common-yang:encrypt-path "/ciena-common-test/encryption-test-container/container-generate-as-sibling-enc";
                type uint8;
              }
              container b {
                ciena-common-yang:encrypt "b";
                ciena-common-yang:encrypt-path "/ciena-common-test/encryption-test-container/container-generate-as-sibling-enc";
                leaf c {
                  ciena-common-yang:encrypt "c";
                  ciena-common-yang:encrypt-path "/ciena-common-test/encryption-test-container/container-generate-as-sibling-enc/b";
                  type uint8;
                }
              }
            }
            container container-generate-as-sibling-enc {
              ciena-common-yang:decrypt "container-generate-as-sibling";
              ciena-common-yang:decrypt-path "/ciena-common-test/encryption-test-container";
              leaf a {
                type string {
                  ciena-common-yang:stringptr "true";
                }
                ciena-common-yang:decrypt "a";
                ciena-common-yang:decrypt-path "/ciena-common-test/encryption-test-container/container-generate-as-sibling";
              }
              container b {
                ciena-common-yang:decrypt "b";
                ciena-common-yang:decrypt-path "/ciena-common-test/encryption-test-container/container-generate-as-sibling";
                leaf c {
                  type string {
                    ciena-common-yang:stringptr "true";
                  }
                  ciena-common-yang:decrypt "c";
                  ciena-common-yang:decrypt-path "/ciena-common-test/encryption-test-container/container-generate-as-sibling/b";
                }
              }
            }
            container X {
              container Z {
                container container-generate-at-relative-path {
                  ciena-common-yang:encrypt "container-generate-at-relative-path-enc";
                  ciena-common-yang:encrypt-path "/ciena-common-test/encryption-test-container/K";
                  description
                    "test container encryption with encrypt-relative-path information";
                  container red {
                    ciena-common-yang:encrypt "red";
                    ciena-common-yang:encrypt-path "/ciena-common-test/encryption-test-container/K/container-generate-at-relative-path-enc";
                    container blue {
                      ciena-common-yang:encrypt "blue";
                      ciena-common-yang:encrypt-path "/ciena-common-test/encryption-test-container/K/container-generate-at-relative-path-enc/red";
                      leaf a {
                        ciena-common-yang:encrypt "a";
                        ciena-common-yang:encrypt-path "/ciena-common-test/encryption-test-container/K/container-generate-at-relative-path-enc/red/blue";
                        type uint8;
                      }
                      leaf b {
                        ciena-common-yang:encrypt "b";
                        ciena-common-yang:encrypt-path "/ciena-common-test/encryption-test-container/K/container-generate-at-relative-path-enc/red/blue";
                        type uint8;
                        default "22";
                      }
                      leaf c {
                        ciena-common-yang:encrypt "c";
                        ciena-common-yang:encrypt-path "/ciena-common-test/encryption-test-container/K/container-generate-at-relative-path-enc/red/blue";
                        type uint8;
                        default "44";
                      }
                      leaf d {
                        ciena-common-yang:encrypt "d";
                        ciena-common-yang:encrypt-path "/ciena-common-test/encryption-test-container/K/container-generate-at-relative-path-enc/red/blue";
                        type uint8;
                        default "88";
                      }
                    }
                  }
                  leaf a {
                    ciena-common-yang:encrypt "a";
                    ciena-common-yang:encrypt-path "/ciena-common-test/encryption-test-container/K/container-generate-at-relative-path-enc";
                    type uint8;
                  }
                  container b {
                    ciena-common-yang:encrypt "b";
                    ciena-common-yang:encrypt-path "/ciena-common-test/encryption-test-container/K/container-generate-at-relative-path-enc";
                    container red {
                      ciena-common-yang:encrypt "red";
                      ciena-common-yang:encrypt-path "/ciena-common-test/encryption-test-container/K/container-generate-at-relative-path-enc/b";
                      container blue {
                        ciena-common-yang:encrypt "blue";
                        ciena-common-yang:encrypt-path "/ciena-common-test/encryption-test-container/K/container-generate-at-relative-path-enc/b/red";
                        leaf a {
                          ciena-common-yang:encrypt "a";
                          ciena-common-yang:encrypt-path "/ciena-common-test/encryption-test-container/K/container-generate-at-relative-path-enc/b/red/blue";
                          type uint8;
                        }
                        leaf b {
                          ciena-common-yang:encrypt "b";
                          ciena-common-yang:encrypt-path "/ciena-common-test/encryption-test-container/K/container-generate-at-relative-path-enc/b/red/blue";
                          type uint8;
                          default "22";
                        }
                        leaf c {
                          ciena-common-yang:encrypt "c";
                          ciena-common-yang:encrypt-path "/ciena-common-test/encryption-test-container/K/container-generate-at-relative-path-enc/b/red/blue";
                          type uint8;
                          default "44";
                        }
                        leaf d {
                          ciena-common-yang:encrypt "d";
                          ciena-common-yang:encrypt-path "/ciena-common-test/encryption-test-container/K/container-generate-at-relative-path-enc/b/red/blue";
                          type uint8;
                          default "88";
                        }
                      }
                    }
                    leaf c {
                      ciena-common-yang:encrypt "c";
                      ciena-common-yang:encrypt-path "/ciena-common-test/encryption-test-container/K/container-generate-at-relative-path-enc/b";
                      type uint8;
                    }
                  }
                  config false;
                }
              }
            }
            container K {
              container container-generate-at-relative-path-enc {
                ciena-common-yang:decrypt "container-generate-at-relative-path";
                ciena-common-yang:decrypt-path "/ciena-common-test/encryption-test-container/X/Z";
                container red {
                  ciena-common-yang:decrypt "red";
                  ciena-common-yang:decrypt-path "/ciena-common-test/encryption-test-container/X/Z/container-generate-at-relative-path";
                  container blue {
                    ciena-common-yang:decrypt "blue";
                    ciena-common-yang:decrypt-path "/ciena-common-test/encryption-test-container/X/Z/container-generate-at-relative-path/red";
                    leaf a {
                      type string {
                        ciena-common-yang:stringptr "true";
                      }
                      ciena-common-yang:decrypt "a";
                      ciena-common-yang:decrypt-path "/ciena-common-test/encryption-test-container/X/Z/container-generate-at-relative-path/red/blue";
                    }
                    leaf b {
                      type string {
                        ciena-common-yang:stringptr "true";
                      }
                      ciena-common-yang:decrypt "b";
                      ciena-common-yang:decrypt-path "/ciena-common-test/encryption-test-container/X/Z/container-generate-at-relative-path/red/blue";
                    }
                    leaf c {
                      type string {
                        ciena-common-yang:stringptr "true";
                      }
                      ciena-common-yang:decrypt "c";
                      ciena-common-yang:decrypt-path "/ciena-common-test/encryption-test-container/X/Z/container-generate-at-relative-path/red/blue";
                    }
                    leaf d {
                      type string {
                        ciena-common-yang:stringptr "true";
                      }
                      ciena-common-yang:decrypt "d";
                      ciena-common-yang:decrypt-path "/ciena-common-test/encryption-test-container/X/Z/container-generate-at-relative-path/red/blue";
                    }
                  }
                }
                leaf a {
                  type string {
                    ciena-common-yang:stringptr "true";
                  }
                  ciena-common-yang:decrypt "a";
                  ciena-common-yang:decrypt-path "/ciena-common-test/encryption-test-container/X/Z/container-generate-at-relative-path";
                }
                container b {
                  ciena-common-yang:decrypt "b";
                  ciena-common-yang:decrypt-path "/ciena-common-test/encryption-test-container/X/Z/container-generate-at-relative-path";
                  container red {
                    ciena-common-yang:decrypt "red";
                    ciena-common-yang:decrypt-path "/ciena-common-test/encryption-test-container/X/Z/container-generate-at-relative-path/b";
                    container blue {
                      ciena-common-yang:decrypt "blue";
                      ciena-common-yang:decrypt-path "/ciena-common-test/encryption-test-container/X/Z/container-generate-at-relative-path/b/red";
                      leaf a {
                        type string {
                          ciena-common-yang:stringptr "true";
                        }
                        ciena-common-yang:decrypt "a";
                        ciena-common-yang:decrypt-path "/ciena-common-test/encryption-test-container/X/Z/container-generate-at-relative-path/b/red/blue";
                      }
                      leaf b {
                        type string {
                          ciena-common-yang:stringptr "true";
                        }
                        ciena-common-yang:decrypt "b";
                        ciena-common-yang:decrypt-path "/ciena-common-test/encryption-test-container/X/Z/container-generate-at-relative-path/b/red/blue";
                      }
                      leaf c {
                        type string {
                          ciena-common-yang:stringptr "true";
                        }
                        ciena-common-yang:decrypt "c";
                        ciena-common-yang:decrypt-path "/ciena-common-test/encryption-test-container/X/Z/container-generate-at-relative-path/b/red/blue";
                      }
                      leaf d {
                        type string {
                          ciena-common-yang:stringptr "true";
                        }
                        ciena-common-yang:decrypt "d";
                        ciena-common-yang:decrypt-path "/ciena-common-test/encryption-test-container/X/Z/container-generate-at-relative-path/b/red/blue";
                      }
                    }
                  }
                  leaf c {
                    type string {
                      ciena-common-yang:stringptr "true";
                    }
                    ciena-common-yang:decrypt "c";
                    ciena-common-yang:decrypt-path "/ciena-common-test/encryption-test-container/X/Z/container-generate-at-relative-path/b";
                  }
                }
                config false;
              }
              leaf l {
                type uint8;
              }
            }
            container container-generate-at-abs-path {
              ciena-common-yang:encrypt "container-generate-at-abs-path-enc";
              ciena-common-yang:encrypt-path "/ciena-common-test/encryption-test-container";
              description
                "test container encryption with absolute path encrypt-path information";
              leaf a {
                ciena-common-yang:encrypt "a";
                ciena-common-yang:encrypt-path "/ciena-common-test/encryption-test-container/container-generate-at-abs-path-enc";
                type uint8;
              }
              container b {
                ciena-common-yang:encrypt "b";
                ciena-common-yang:encrypt-path "/ciena-common-test/encryption-test-container/container-generate-at-abs-path-enc";
                leaf c {
                  ciena-common-yang:encrypt "c";
                  ciena-common-yang:encrypt-path "/ciena-common-test/encryption-test-container/container-generate-at-abs-path-enc/b";
                  type uint8;
                }
              }
              config false;
            }
            container encrypt-to-existing-container {
              ciena-common-yang:encrypt "encrypt-to-existing-container-encrypted";
              ciena-common-yang:encrypt-path "/ciena-common-test/encryption-test-container";
              description
                "test container encryption to existing container. no generation will happen.";
              leaf a {
                ciena-common-yang:encrypt "a";
                ciena-common-yang:encrypt-path "/ciena-common-test/encryption-test-container/encrypt-to-existing-container-encrypted";
                type uint8;
              }
            }
            container encrypt-to-existing-container-encrypted {
              ciena-common-yang:decrypt "encrypt-to-existing-container";
              ciena-common-yang:decrypt-path "/ciena-common-test/encryption-test-container";
              leaf a {
                ciena-common-yang:decrypt "a";
                ciena-common-yang:decrypt-path "/ciena-common-test/encryption-test-container/encrypt-to-existing-container";
                type string {
                  ciena-common-yang:stringptr "true";
                }
              }
            }
            container outter-container {
              ciena-common-yang:encrypt "outter-container-enc";
              ciena-common-yang:encrypt-path "/ciena-common-test/encryption-test-container";
              description
                "simple nested container test";
              leaf aaa {
                ciena-common-yang:encrypt "aaa";
                ciena-common-yang:encrypt-path "/ciena-common-test/encryption-test-container/outter-container-enc";
                type uint8;
              }
              container middle-container {
                ciena-common-yang:encrypt "middle-container";
                ciena-common-yang:encrypt-path "/ciena-common-test/encryption-test-container/outter-container-enc";
                leaf bbb {
                  ciena-common-yang:encrypt "bbb";
                  ciena-common-yang:encrypt-path "/ciena-common-test/encryption-test-container/outter-container-enc/middle-container";
                  type uint8;
                }
                container inner-container {
                  ciena-common-yang:encrypt "inner-container";
                  ciena-common-yang:encrypt-path "/ciena-common-test/encryption-test-container/outter-container-enc/middle-container";
                  leaf ccc {
                    ciena-common-yang:encrypt "ccc";
                    ciena-common-yang:encrypt-path "/ciena-common-test/encryption-test-container/outter-container-enc/middle-container/inner-container";
                    type uint8;
                  }
                }
              }
            }
            container outter-container-enc {
              ciena-common-yang:decrypt "outter-container";
              ciena-common-yang:decrypt-path "/ciena-common-test/encryption-test-container";
              leaf aaa {
                type string {
                  ciena-common-yang:stringptr "true";
                }
                ciena-common-yang:decrypt "aaa";
                ciena-common-yang:decrypt-path "/ciena-common-test/encryption-test-container/outter-container";
              }
              container middle-container {
                ciena-common-yang:decrypt "middle-container";
                ciena-common-yang:decrypt-path "/ciena-common-test/encryption-test-container/outter-container";
                leaf bbb {
                  type string {
                    ciena-common-yang:stringptr "true";
                  }
                  ciena-common-yang:decrypt "bbb";
                  ciena-common-yang:decrypt-path "/ciena-common-test/encryption-test-container/outter-container/middle-container";
                }
                container inner-container {
                  ciena-common-yang:decrypt "inner-container";
                  ciena-common-yang:decrypt-path "/ciena-common-test/encryption-test-container/outter-container/middle-container";
                  leaf ccc {
                    type string {
                      ciena-common-yang:stringptr "true";
                    }
                    ciena-common-yang:decrypt "ccc";
                    ciena-common-yang:decrypt-path "/ciena-common-test/encryption-test-container/outter-container/middle-container/inner-container";
                  }
                }
              }
            }
            container one-to-two-container {
              ciena-common-yang:encrypt "one-to-two-container-enc";
              ciena-common-yang:encrypt-path "/ciena-common-test/encryption-test-container";
              description
                "error scenario test: leaves under one container encrypted to two containers
                 is not fully supported, the leaves for one container will be missing";
              leaf aaa {
                ciena-common-yang:encrypt "aaa";
                ciena-common-yang:encrypt-path "/ciena-common-test/encryption-test-container/one-to-two-container-enc";
                type uint8;
              }
              leaf-list bbb {
                ciena-common-yang:encrypt "bbb";
                ciena-common-yang:encrypt-path "/ciena-common-test/encryption-test-container/one-to-two-container-other";
                type uint8;
              }
              container inner-container {
                ciena-common-yang:encrypt "inner-container";
                ciena-common-yang:encrypt-path "/ciena-common-test/encryption-test-container/one-to-two-container-enc";
                leaf-list ccc {
                  ciena-common-yang:encrypt "ccc";
                  ciena-common-yang:encrypt-path "/ciena-common-test/encryption-test-container/one-to-two-container-enc/inner-container";
                  type uint8;
                }
                leaf ddd {
                  ciena-common-yang:encrypt "ddd";
                  ciena-common-yang:encrypt-path "/ciena-common-test/encryption-test-container/one-to-two-container-other";
                  type uint8;
                }
              }
            }
            container one-to-two-container-enc {
              ciena-common-yang:decrypt "one-to-two-container";
              ciena-common-yang:decrypt-path "/ciena-common-test/encryption-test-container";
              leaf aaa {
                type string {
                  ciena-common-yang:stringptr "true";
                }
                ciena-common-yang:decrypt "aaa";
                ciena-common-yang:decrypt-path "/ciena-common-test/encryption-test-container/one-to-two-container";
              }
              container inner-container {
                ciena-common-yang:decrypt "inner-container";
                ciena-common-yang:decrypt-path "/ciena-common-test/encryption-test-container/one-to-two-container";
                leaf-list ccc {
                  type string {
                    ciena-common-yang:stringptr "true";
                  }
                  ciena-common-yang:decrypt "ccc";
                  ciena-common-yang:decrypt-path "/ciena-common-test/encryption-test-container/one-to-two-container/inner-container";
                }
              }
            }
            container one-to-two-container-other {
              leaf-list bbb {
                ciena-common-yang:decrypt "bbb";
                ciena-common-yang:decrypt-path "/ciena-common-test/encryption-test-container/one-to-two-container";
                type string {
                  ciena-common-yang:stringptr "true";
                }
              }
              leaf ddd {
                ciena-common-yang:decrypt "ddd";
                ciena-common-yang:decrypt-path "/ciena-common-test/encryption-test-container/one-to-two-container/inner-container";
                type string {
                  ciena-common-yang:stringptr "true";
                }
              }
              leaf fff {
                type uint8;
              }
            }
            list nested-list {
              ciena-common-yang:encrypt "nested-list-enc";
              ciena-common-yang:encrypt-path "/ciena-common-test/encryption-test-container";
              description
                "test nested list encryption";
              key "name";
              leaf name {
                ciena-common-yang:encrypt "name";
                ciena-common-yang:encrypt-path "/ciena-common-test/encryption-test-container/nested-list-enc";
                type stringptr;
              }
              leaf aaa {
                ciena-common-yang:encrypt "aaa";
                ciena-common-yang:encrypt-path "/ciena-common-test/encryption-test-container/nested-list-enc";
                type uint8;
              }
              list inner-list {
                ciena-common-yang:encrypt "inner-list";
                ciena-common-yang:encrypt-path "/ciena-common-test/encryption-test-container/nested-list-enc";
                key "index";
                leaf index {
                  ciena-common-yang:encrypt "index";
                  ciena-common-yang:encrypt-path "/ciena-common-test/encryption-test-container/nested-list-enc/inner-list";
                  type uint8;
                }
                leaf-list ccc {
                  ciena-common-yang:encrypt "ccc";
                  ciena-common-yang:encrypt-path "/ciena-common-test/encryption-test-container/nested-list-enc/inner-list";
                  type string;
                }
              }
            }
            list nested-list-enc {
              ciena-common-yang:decrypt "nested-list";
              ciena-common-yang:decrypt-path "/ciena-common-test/encryption-test-container";
              key "name";
              leaf name {
                type string {
                  ciena-common-yang:stringptr "true";
                }
                ciena-common-yang:decrypt "name";
                ciena-common-yang:decrypt-path "/ciena-common-test/encryption-test-container/nested-list";
              }
              leaf aaa {
                type string {
                  ciena-common-yang:stringptr "true";
                }
                ciena-common-yang:decrypt "aaa";
                ciena-common-yang:decrypt-path "/ciena-common-test/encryption-test-container/nested-list";
              }
              list inner-list {
                ciena-common-yang:decrypt "inner-list";
                ciena-common-yang:decrypt-path "/ciena-common-test/encryption-test-container/nested-list";
                key "index";
                leaf index {
                  type string {
                    ciena-common-yang:stringptr "true";
                  }
                  ciena-common-yang:decrypt "index";
                  ciena-common-yang:decrypt-path "/ciena-common-test/encryption-test-container/nested-list/inner-list";
                }
                leaf-list ccc {
                  type string {
                    ciena-common-yang:stringptr "true";
                  }
                  ciena-common-yang:decrypt "ccc";
                  ciena-common-yang:decrypt-path "/ciena-common-test/encryption-test-container/nested-list/inner-list";
                }
              }
            }
            container other {
              leaf ccc {
                type string;
              }
            }
            container user-defined-leaves {
              description
                "selected leaves encryption container";
              leaf a {
                ciena-common-yang:encrypt "x";
                ciena-common-yang:encrypt-path "/ciena-common-test/encryption-test-container/user-defined-leaves-encrypted";
                type string;
              }
              leaf b {
                type string;
              }
            }
            container user-defined-leaves-encrypted {
              leaf x {
                ciena-common-yang:decrypt "a";
                ciena-common-yang:decrypt-path "/ciena-common-test/encryption-test-container/user-defined-leaves";
                type string;
              }
            }
            list nested-list-leaf-encryption {
              key "name";
              leaf name {
                type string;
              }
              leaf x {
                ciena-common-yang:encrypt "x-enc";
                ciena-common-yang:encrypt-path "/ciena-common-test/encryption-test-container/nested-list-leaf-encryption";
                type string;
              }
              leaf x-enc {
                type string {
                  ciena-common-yang:stringptr "true";
                }
                ciena-common-yang:decrypt "x";
                ciena-common-yang:decrypt-path "/ciena-common-test/encryption-test-container/nested-list-leaf-encryption";
              }
              list inner {
                key "index";
                leaf index {
                  type uint8;
                }
                leaf u {
                  ciena-common-yang:encrypt "u-enc";
                  ciena-common-yang:encrypt-path "/ciena-common-test/encryption-test-container/nested-list-leaf-encryption/inner";
                  type string;
                }
                leaf u-enc {
                  type string {
                    ciena-common-yang:stringptr "true";
                  }
                  ciena-common-yang:decrypt "u";
                  ciena-common-yang:decrypt-path "/ciena-common-test/encryption-test-container/nested-list-leaf-encryption/inner";
                }
              }
            }
            list encryption-list-test {
              key "key1 key2";
              leaf key1 {
                type stringptr;
              }
              leaf key2 {
                type typetest;
              }
              container leaf-list-test {
                leaf-list binary-test {
                  ciena-common-yang:encrypt "binary-test-encrypted";
                  ciena-common-yang:encrypt-path "/ciena-common-test/encryption-test-container/encryption-list-test/leaf-list-test";
                  type binary;
                }
                leaf-list binary-test-encrypted {
                  type string {
                    ciena-common-yang:stringptr "true";
                  }
                  ciena-common-yang:decrypt "binary-test";
                  ciena-common-yang:decrypt-path "/ciena-common-test/encryption-test-container/encryption-list-test/leaf-list-test";
                }
                leaf-list bits-test {
                  ciena-common-yang:encrypt "bits-test-encrypted";
                  ciena-common-yang:encrypt-path "/ciena-common-test/encryption-test-container/encryption-list-test/leaf-list-test";
                  type bits {
                    bit disable-nagle {
                      position 0;
                    }
                    bit auto-sense-speed {
                      position 1;
                    }
                  }
                }
                leaf-list bits-test-encrypted {
                  type string {
                    ciena-common-yang:stringptr "true";
                  }
                  ciena-common-yang:decrypt "bits-test";
                  ciena-common-yang:decrypt-path "/ciena-common-test/encryption-test-container/encryption-list-test/leaf-list-test";
                }
                leaf-list boolean-test {
                  ciena-common-yang:encrypt "boolean-test-encrypted";
                  ciena-common-yang:encrypt-path "/ciena-common-test/encryption-test-container/encryption-list-test/leaf-list-test";
                  type boolean;
                }
                leaf-list boolean-test-encrypted {
                  type string {
                    ciena-common-yang:stringptr "true";
                  }
                  ciena-common-yang:decrypt "boolean-test";
                  ciena-common-yang:decrypt-path "/ciena-common-test/encryption-test-container/encryption-list-test/leaf-list-test";
                }
                leaf-list decimal64-test {
                  ciena-common-yang:encrypt "decimal64-test-encrypted";
                  ciena-common-yang:encrypt-path "/ciena-common-test/encryption-test-container/encryption-list-test/leaf-list-test";
                  type decimal64 {
                    fraction-digits 10;
                  }
                }
                leaf-list decimal64-test-encrypted {
                  type string {
                    ciena-common-yang:stringptr "true";
                  }
                  ciena-common-yang:decrypt "decimal64-test";
                  ciena-common-yang:decrypt-path "/ciena-common-test/encryption-test-container/encryption-list-test/leaf-list-test";
                }
                leaf-list empty-test {
                  ciena-common-yang:encrypt "empty-test-encrypted";
                  ciena-common-yang:encrypt-path "/ciena-common-test/encryption-test-container/encryption-list-test/leaf-list-test";
                  type empty;
                }
                leaf-list empty-test-encrypted {
                  type string {
                    ciena-common-yang:stringptr "true";
                  }
                  ciena-common-yang:decrypt "empty-test";
                  ciena-common-yang:decrypt-path "/ciena-common-test/encryption-test-container/encryption-list-test/leaf-list-test";
                }
                leaf-list enumeration-test {
                  ciena-common-yang:encrypt "enumeration-test-encrypted";
                  ciena-common-yang:encrypt-path "/ciena-common-test/encryption-test-container/encryption-list-test/leaf-list-test";
                  type enumeration {
                    enum test-a;
                    enum test-b;
                    enum test-c;
                    enum map;
                  }
                }
                leaf-list enumeration-test-encrypted {
                  type string {
                    ciena-common-yang:stringptr "true";
                  }
                  ciena-common-yang:decrypt "enumeration-test";
                  ciena-common-yang:decrypt-path "/ciena-common-test/encryption-test-container/encryption-list-test/leaf-list-test";
                }
                leaf-list identityref-test {
                  ciena-common-yang:encrypt "identityref-test-encrypted";
                  ciena-common-yang:encrypt-path "/ciena-common-test/encryption-test-container/encryption-list-test/leaf-list-test";
                  type identityref {
                    base test:crypto-alg;
                  }
                }
                leaf-list identityref-test-encrypted {
                  type string {
                    ciena-common-yang:stringptr "true";
                  }
                  ciena-common-yang:decrypt "identityref-test";
                  ciena-common-yang:decrypt-path "/ciena-common-test/encryption-test-container/encryption-list-test/leaf-list-test";
                }
                leaf-list instance-identifier-test {
                  ciena-common-yang:encrypt "instance-identifier-test-encrypted";
                  ciena-common-yang:encrypt-path "/ciena-common-test/encryption-test-container/encryption-list-test/leaf-list-test";
                  type instance-identifier;
                }
                leaf-list instance-identifier-test-encrypted {
                  type string {
                    ciena-common-yang:stringptr "true";
                  }
                  ciena-common-yang:decrypt "instance-identifier-test";
                  ciena-common-yang:decrypt-path "/ciena-common-test/encryption-test-container/encryption-list-test/leaf-list-test";
                }
                leaf-list leafref-test {
                  ciena-common-yang:encrypt "leafref-test-encrypted";
                  ciena-common-yang:encrypt-path "/ciena-common-test/encryption-test-container/encryption-list-test/leaf-list-test";
                  type leafref {
                    path "/test:red/test:blue/test:b";
                  }
                }
                leaf-list leafref-test-encrypted {
                  type string {
                    ciena-common-yang:stringptr "true";
                  }
                  ciena-common-yang:decrypt "leafref-test";
                  ciena-common-yang:decrypt-path "/ciena-common-test/encryption-test-container/encryption-list-test/leaf-list-test";
                }
                leaf-list stringptr-test {
                  ciena-common-yang:encrypt "stringptr-test-encrypted";
                  ciena-common-yang:encrypt-path "/ciena-common-test/encryption-test-container/encryption-list-test/leaf-list-test";
                  type stringptr;
                }
                leaf-list stringptr-test-encrypted {
                  type string {
                    ciena-common-yang:stringptr "true";
                  }
                  ciena-common-yang:decrypt "stringptr-test";
                  ciena-common-yang:decrypt-path "/ciena-common-test/encryption-test-container/encryption-list-test/leaf-list-test";
                }
                leaf-list string-test {
                  ciena-common-yang:encrypt "string-test-encrypted";
                  ciena-common-yang:encrypt-path "/ciena-common-test/encryption-test-container/encryption-list-test/leaf-list-test";
                  type string;
                }
                leaf-list string-test-encrypted {
                  type string {
                    ciena-common-yang:stringptr "true";
                  }
                  ciena-common-yang:decrypt "string-test";
                  ciena-common-yang:decrypt-path "/ciena-common-test/encryption-test-container/encryption-list-test/leaf-list-test";
                }
                leaf-list uint8-test {
                  ciena-common-yang:encrypt "uint8-test-encrypted";
                  ciena-common-yang:encrypt-path "/ciena-common-test/encryption-test-container/encryption-list-test/leaf-list-test";
                  type uint8;
                }
                leaf-list uint8-test-encrypted {
                  type string {
                    ciena-common-yang:stringptr "true";
                  }
                  ciena-common-yang:decrypt "uint8-test";
                  ciena-common-yang:decrypt-path "/ciena-common-test/encryption-test-container/encryption-list-test/leaf-list-test";
                }
                leaf-list union-test {
                  ciena-common-yang:encrypt "union-test-encrypted";
                  ciena-common-yang:encrypt-path "/ciena-common-test/encryption-test-container/encryption-list-test/leaf-list-test";
                  type union {
                    type int32;
                    type enumeration {
                      enum unbounded;
                    }
                  }
                }
                leaf-list union-test-encrypted {
                  type string {
                    ciena-common-yang:stringptr "true";
                  }
                  ciena-common-yang:decrypt "union-test";
                  ciena-common-yang:decrypt-path "/ciena-common-test/encryption-test-container/encryption-list-test/leaf-list-test";
                }
              }
              container leaf-test {
                leaf binary-test {
                  ciena-common-yang:encrypt "binary-test-encrypted";
                  ciena-common-yang:encrypt-path "/ciena-common-test/encryption-test-container/encryption-list-test/leaf-test";
                  type binary;
                  ciena-common-yang:sensitive "true";
                }
                leaf binary-test-encrypted {
                  type string {
                    ciena-common-yang:stringptr "true";
                  }
                  ciena-common-yang:decrypt "binary-test";
                  ciena-common-yang:decrypt-path "/ciena-common-test/encryption-test-container/encryption-list-test/leaf-test";
                  ciena-common-yang:sensitive "true";
                }
                leaf bits-test {
                  ciena-common-yang:encrypt "bits-test-encrypted";
                  ciena-common-yang:encrypt-path "/ciena-common-test/encryption-test-container/encryption-list-test/leaf-test";
                  ciena-common-yang:sensitive "true";
                  type bits {
                    bit apple {
                      position 0;
                    }
                    bit orange {
                      position 1;
                    }
                    bit banana {
                      position 2;
                    }
                  }
                }
                leaf bits-test-encrypted {
                  type string {
                    ciena-common-yang:stringptr "true";
                  }
                  ciena-common-yang:decrypt "bits-test";
                  ciena-common-yang:decrypt-path "/ciena-common-test/encryption-test-container/encryption-list-test/leaf-test";
                  ciena-common-yang:sensitive "true";
                }
                leaf offset-bits-test {
                  ciena-common-yang:encrypt "offset-bits-test-encrypted";
                  ciena-common-yang:encrypt-path "/ciena-common-test/encryption-test-container/encryption-list-test/leaf-test";
                  ciena-common-yang:sensitive "true";
                  type bits {
                    bit apple {
                      position 3;
                    }
                    bit orange {
                      position 5;
                    }
                    bit banana {
                      position 7;
                    }
                  }
                }
                leaf offset-bits-test-encrypted {
                  type string {
                    ciena-common-yang:stringptr "true";
                  }
                  ciena-common-yang:decrypt "offset-bits-test";
                  ciena-common-yang:decrypt-path "/ciena-common-test/encryption-test-container/encryption-list-test/leaf-test";
                  ciena-common-yang:sensitive "true";
                }
                leaf boolean-test {
                  ciena-common-yang:encrypt "boolean-test-encrypted";
                  ciena-common-yang:encrypt-path "/ciena-common-test/encryption-test-container/encryption-list-test/leaf-test";
                  ciena-common-yang:sensitive "true";
                  type boolean;
                }
                leaf boolean-test-encrypted {
                  type string {
                    ciena-common-yang:stringptr "true";
                  }
                  ciena-common-yang:decrypt "boolean-test";
                  ciena-common-yang:decrypt-path "/ciena-common-test/encryption-test-container/encryption-list-test/leaf-test";
                  ciena-common-yang:sensitive "true";
                }
                leaf decimal64-test {
                  ciena-common-yang:encrypt "decimal64-test-encrypted";
                  ciena-common-yang:encrypt-path "/ciena-common-test/encryption-test-container/encryption-list-test/leaf-test";
                  ciena-common-yang:sensitive "true";
                  type decimal64 {
                    fraction-digits 2;
                  }
                }
                leaf decimal64-test-encrypted {
                  type string {
                    ciena-common-yang:stringptr "true";
                  }
                  ciena-common-yang:decrypt "decimal64-test";
                  ciena-common-yang:decrypt-path "/ciena-common-test/encryption-test-container/encryption-list-test/leaf-test";
                  ciena-common-yang:sensitive "true";
                }
                leaf empty-test {
                  ciena-common-yang:encrypt "empty-test-encrypted";
                  ciena-common-yang:encrypt-path "/ciena-common-test/encryption-test-container/encryption-list-test/leaf-test";
                  ciena-common-yang:sensitive "true";
                  type empty;
                }
                leaf empty-test-encrypted {
                  type string {
                    ciena-common-yang:stringptr "true";
                  }
                  ciena-common-yang:decrypt "empty-test";
                  ciena-common-yang:decrypt-path "/ciena-common-test/encryption-test-container/encryption-list-test/leaf-test";
                  ciena-common-yang:sensitive "true";
                }
                leaf enumeration-test {
                  ciena-common-yang:encrypt "enumeration-test-encrypted";
                  ciena-common-yang:encrypt-path "/ciena-common-test/encryption-test-container/encryption-list-test/leaf-test";
                  ciena-common-yang:sensitive "true";
                  type enumeration {
                    enum test-1;
                    enum test-2;
                    enum test-3;
                  }
                }
                leaf enumeration-test-encrypted {
                  type string {
                    ciena-common-yang:stringptr "true";
                  }
                  ciena-common-yang:decrypt "enumeration-test";
                  ciena-common-yang:decrypt-path "/ciena-common-test/encryption-test-container/encryption-list-test/leaf-test";
                  ciena-common-yang:sensitive "true";
                }
                leaf enumeration-extended-test {
                  ciena-common-yang:encrypt "enumeration-extended-test-encrypted";
                  ciena-common-yang:encrypt-path "/ciena-common-test/encryption-test-container/encryption-list-test/leaf-test";
                  ciena-common-yang:sensitive "true";
                  type enumeration {
                    enum forty-one {
                      value 41;
                    }
                    enum ten {
                      value 10;
                    }
                    enum seven {
                      value 7;
                    }
                  }
                }
                leaf enumeration-extended-test-encrypted {
                  type string {
                    ciena-common-yang:stringptr "true";
                  }
                  ciena-common-yang:decrypt "enumeration-extended-test";
                  ciena-common-yang:decrypt-path "/ciena-common-test/encryption-test-container/encryption-list-test/leaf-test";
                  ciena-common-yang:sensitive "true";
                }
                leaf identityref-test {
                  ciena-common-yang:encrypt "identifyref-test-encrypted";
                  ciena-common-yang:encrypt-path "/ciena-common-test/encryption-test-container/encryption-list-test/leaf-test";
                  ciena-common-yang:sensitive "true";
                  type identityref {
                    base test:crypto-alg;
                  }
                }
                leaf identifyref-test-encrypted {
                  type string {
                    ciena-common-yang:stringptr "true";
                  }
                  ciena-common-yang:decrypt "identityref-test";
                  ciena-common-yang:decrypt-path "/ciena-common-test/encryption-test-container/encryption-list-test/leaf-test";
                  ciena-common-yang:sensitive "true";
                }
                leaf instance-identifier-test {
                  ciena-common-yang:encrypt "instance-identifier-test-encrypted";
                  ciena-common-yang:encrypt-path "/ciena-common-test/encryption-test-container/encryption-list-test/leaf-test";
                  ciena-common-yang:sensitive "true";
                  type instance-identifier;
                }
                leaf instance-identifier-test-encrypted {
                  type string {
                    ciena-common-yang:stringptr "true";
                  }
                  ciena-common-yang:decrypt "instance-identifier-test";
                  ciena-common-yang:decrypt-path "/ciena-common-test/encryption-test-container/encryption-list-test/leaf-test";
                  ciena-common-yang:sensitive "true";
                }
                leaf int64-test {
                  ciena-common-yang:encrypt "int64-test-encrypted";
                  ciena-common-yang:encrypt-path "/ciena-common-test/encryption-test-container/encryption-list-test/leaf-test";
                  ciena-common-yang:sensitive "true";
                  type int64;
                }
                leaf int64-test-encrypted {
                  type string {
                    ciena-common-yang:stringptr "true";
                  }
                  ciena-common-yang:decrypt "int64-test";
                  ciena-common-yang:decrypt-path "/ciena-common-test/encryption-test-container/encryption-list-test/leaf-test";
                  ciena-common-yang:sensitive "true";
                }
                leaf leafref-test {
                  ciena-common-yang:encrypt "leafref-test-encrypted";
                  ciena-common-yang:encrypt-path "/ciena-common-test/encryption-test-container/encryption-list-test/leaf-test";
                  ciena-common-yang:sensitive "true";
                  type leafref {
                    path "/test:red/test:blue/test:c";
                  }
                }
                leaf leafref-test-encrypted {
                  type string {
                    ciena-common-yang:stringptr "true";
                  }
                  ciena-common-yang:decrypt "leafref-test";
                  ciena-common-yang:decrypt-path "/ciena-common-test/encryption-test-container/encryption-list-test/leaf-test";
                  ciena-common-yang:sensitive "true";
                }
                leaf stringptr-test {
                  ciena-common-yang:encrypt "stringptr-test-encrypted";
                  ciena-common-yang:encrypt-path "/ciena-common-test/encryption-test-container/encryption-list-test/leaf-test";
                  ciena-common-yang:sensitive "true";
                  type string {
                    ciena-common-yang:stringptr "true";
                  }
                }
                leaf stringptr-test-encrypted {
                  type string {
                    ciena-common-yang:stringptr "true";
                  }
                  ciena-common-yang:decrypt "stringptr-test";
                  ciena-common-yang:decrypt-path "/ciena-common-test/encryption-test-container/encryption-list-test/leaf-test";
                  ciena-common-yang:sensitive "true";
                }
                leaf string-test {
                  ciena-common-yang:encrypt "string-test-encrypted";
                  ciena-common-yang:encrypt-path "/ciena-common-test/encryption-test-container/encryption-list-test/leaf-test";
                  ciena-common-yang:sensitive "true";
                  type string {
                    length "0..15";
                  }
                }
                leaf string-test-encrypted {
                  type string {
                    ciena-common-yang:stringptr "true";
                  }
                  ciena-common-yang:decrypt "string-test";
                  ciena-common-yang:decrypt-path "/ciena-common-test/encryption-test-container/encryption-list-test/leaf-test";
                  ciena-common-yang:sensitive "true";
                }
                leaf union-test {
                  ciena-common-yang:encrypt "union-test-encrypted";
                  ciena-common-yang:encrypt-path "/ciena-common-test/encryption-test-container/encryption-list-test/leaf-test";
                  type union {
                    type int32;
                    type enumeration {
                      enum unbounded;
                    }
                  }
                  ciena-common-yang:sensitive "true";
                }
                leaf union-test-encrypted {
                  type string {
                    ciena-common-yang:stringptr "true";
                  }
                  ciena-common-yang:decrypt "union-test";
                  ciena-common-yang:decrypt-path "/ciena-common-test/encryption-test-container/encryption-list-test/leaf-test";
                  ciena-common-yang:sensitive "true";
                }
              }
            }
          }
          container toggle-sleep {
            container input {
              ciena-common-yang:containerptr "true";
            }
          }
          uses grouping-test;
          container rpc-test-empty;
          container rpc-test-no-output {
            container input {
              ciena-common-yang:containerptr "true";
            }
          }
          container rpc-test-no-input {
            container output {
              ciena-common-yang:containerptr "true";
            }
          }
          container rpc-test {
            container input {
              ciena-common-yang:containerptr "true";
            }
            container output {
              ciena-common-yang:containerptr "true";
            }
          }
          container rpc-trigger-encryption-set {
            container input {
              ciena-common-yang:containerptr "true";
            }
          }
          container notification-test {
            ciena-common-yang:containerptr "true";
            uses red-blue-group;
          }
          container encryption-notification-test {
            ciena-common-yang:containerptr "true";
            container X {
              leaf y {
                ciena-common-yang:encrypt "y-encrypted";
                ciena-common-yang:encrypt-path "/ciena-common-test/encryption-notification-test/X";
                type string;
              }
              leaf y-encrypted {
                type string {
                  ciena-common-yang:stringptr "true";
                }
                ciena-common-yang:decrypt "y";
                ciena-common-yang:decrypt-path "/ciena-common-test/encryption-notification-test/X";
              }
            }
          }
          container stack-push {
            description
              "Push into thread specific stack";
            container input {
              ciena-common-yang:containerptr "true";
            }
            container output {
              ciena-common-yang:containerptr "true";
            }
          }
          container stack-pop {
            description
              "Pop from thread specific stack";
            container input {
              ciena-common-yang:containerptr "true";
            }
            container output {
              ciena-common-yang:containerptr "true";
            }
          }
          container stack-get {
            description
              "Get pushed data for an attribute";
            container input {
              ciena-common-yang:containerptr "true";
            }
            container output {
              ciena-common-yang:containerptr "true";
            }
          }
          container stack-merge {
            description
              "Merge thread specific stacks";
            container input {
              ciena-common-yang:containerptr "true";
            }
            container output {
              ciena-common-yang:containerptr "true";
            }
          }
          container return-code-set {
            description
              "Set the return code in the response";
            container input {
              ciena-common-yang:containerptr "true";
            }
            container output {
              ciena-common-yang:containerptr "true";
            }
          }
          container validate-test {
            description
              "Set the return code in the response";
            container input {
              ciena-common-yang:containerptr "true";
            }
            container output {
              ciena-common-yang:containerptr "true";
            }
          }
          container test-deadline-timeout {
            description
              "Take input as timeout and handler will wait till this time
                based on test scenario type and return pass as true/false.";
            container input {
              ciena-common-yang:containerptr "true";
            }
            container output {
              ciena-common-yang:containerptr "true";
            }
          }
          container mount_test_a {
            list b {
              key "name";
              leaf name {
                type string;
              }
              anyxml c;
              container anyxml-mount {
                ciena-common-yang:mount-start "ciena-common-test";
                ciena-common-yang:mount-end "ciena-common-test";
              }
              anydata d;
              container anydata-mount {
                ciena-common-yang:mount-start "ciena-common-test";
                ciena-common-yang:mount-end "ciena-common-test";
              }
            }
          }
          container mount_test_b {
            list b {
              key "name";
              leaf name {
                type string;
              }
              anyxml c;
              container anyxml-mount {
                ciena-common-yang:mount-start "ciena-common-test-list";
                uses ciena-common-test-list:ciena-common-test-list-mount-data-actions-notifs-as-cont;
                ciena-common-yang:mount-end "ciena-common-test-list";
              }
            }
          }
          container i_love_big_data {
            list big_list {
              key "name";
              leaf name {
                type uint64;
              }
              leaf some_data {
                type decimal64 {
                  fraction-digits 10;
                }
              }
            }
          }
          container i_love_instance_id_for_keys {
            list some_list {
              key "instance_id_name";
              leaf instance_id_name {
                type instance-identifier;
              }
              leaf some_data {
                type decimal64 {
                  fraction-digits 10;
                }
              }
              container some_container {
                description
                  "Dummy container to have same context as parent";
                list sub_list {
                  description
                    "Another keyed list to have instance-id in parent context";
                  key "some_sub_key";
                  leaf some_sub_key {
                    type uint32;
                  }
                  leaf some_sub_leaf {
                    type uint32;
                  }
                }
              }
            }
          }
          container test-restconf-a {
            leaf b {
              type string;
            }
            leaf c {
              type uint8;
            }
            leaf awesome-wildcard-field {
              type string;
            }
            list d {
              key "name";
              leaf name {
                type string;
              }
              leaf test-state {
                type boolean;
              }
              container awesome-wildcard-field {
                leaf awesome-wildcard-field {
                  type boolean;
                }
                leaf awesome-wildcard-field-not {
                  type string;
                }
              }
              list e {
                key "index";
                leaf index {
                  type uint8;
                }
                leaf name {
                  type string;
                }
                list awesome-wildcard-field {
                  key "awesome-wildcard-field";
                  leaf awesome-wildcard-field {
                    type uint8;
                  }
                }
              }
            }
          }
          container test-colon-container {
            leaf enumeration-test {
              ciena-common-yang:sensitive "true";
              type enumeration {
                enum "1:n Mux type";
                enum "2:n Mux type";
                enum "3:n Mux type";
              }
            }
          }
          container multi-augment;
          container ddy-test-server-config {
            leaf handle-complete-transaction {
              type enumeration {
                enum none {
                  description
                    "complete-transaction not handled at all";
                }
                enum local {
                  description
                    "complete-transaction bound to local service";
                }
                enum service {
                  description
                    "complete-transaction bound to ddy-test-server";
                }
              }
              default "none";
            }
          }
          container client-activations {
            description
              "Sometimes you are testing something and you just need a simple way to execute a task.";
            container input {
              ciena-common-yang:containerptr "true";
            }
          }
          ciena-common-yang:mount-end "ciena-common-test";
        }
      }
    }
    container mount_test_b {
      list b {
        key "name";
        leaf name {
          type string;
        }
        anyxml c;
        container anyxml-mount {
          ciena-common-yang:mount-start "ciena-common-test-list";
          uses ciena-common-test-list:ciena-common-test-list-mount-data-actions-notifs-as-cont;
          ciena-common-yang:mount-end "ciena-common-test-list";
        }
      }
    }
    container i_love_big_data {
      list big_list {
        key "name";
        leaf name {
          type uint64;
        }
        leaf some_data {
          type decimal64 {
            fraction-digits 10;
          }
        }
      }
    }
    container i_love_instance_id_for_keys {
      list some_list {
        key "instance_id_name";
        leaf instance_id_name {
          type instance-identifier;
        }
        leaf some_data {
          type decimal64 {
            fraction-digits 10;
          }
        }
        container some_container {
          description
            "Dummy container to have same context as parent";
          list sub_list {
            description
              "Another keyed list to have instance-id in parent context";
            key "some_sub_key";
            leaf some_sub_key {
              type uint32;
            }
            leaf some_sub_leaf {
              type uint32;
            }
          }
        }
      }
    }
    container test-restconf-a {
      leaf b {
        type string;
      }
      leaf c {
        type uint8;
      }
      leaf awesome-wildcard-field {
        type string;
      }
      list d {
        key "name";
        leaf name {
          type string;
        }
        leaf test-state {
          type boolean;
        }
        container awesome-wildcard-field {
          leaf awesome-wildcard-field {
            type boolean;
          }
          leaf awesome-wildcard-field-not {
            type string;
          }
        }
        list e {
          key "index";
          leaf index {
            type uint8;
          }
          leaf name {
            type string;
          }
          list awesome-wildcard-field {
            key "awesome-wildcard-field";
            leaf awesome-wildcard-field {
              type uint8;
            }
          }
        }
      }
    }
    container test-colon-container {
      leaf enumeration-test {
        ciena-common-yang:sensitive "true";
        type enumeration {
          enum "1:n Mux type";
          enum "2:n Mux type";
          enum "3:n Mux type";
        }
      }
    }
    container multi-augment;
    container ddy-test-server-config {
      leaf handle-complete-transaction {
        type enumeration {
          enum none {
            description
              "complete-transaction not handled at all";
          }
          enum local {
            description
              "complete-transaction bound to local service";
          }
          enum service {
            description
              "complete-transaction bound to ddy-test-server";
          }
        }
        default "none";
      }
    }
    container toggle-sleep {
      container input {
        ciena-common-yang:containerptr "true";
      }
    }
    container rpc-test-empty;
    container rpc-test-no-output {
      container input {
        ciena-common-yang:containerptr "true";
      }
    }
    container rpc-test-no-input {
      container output {
        ciena-common-yang:containerptr "true";
      }
    }
    container rpc-test {
      container input {
        ciena-common-yang:containerptr "true";
      }
      container output {
        ciena-common-yang:containerptr "true";
      }
    }
    container rpc-trigger-encryption-set {
      container input {
        ciena-common-yang:containerptr "true";
      }
    }
    container notification-test {
      ciena-common-yang:containerptr "true";
      uses red-blue-group;
    }
    container encryption-notification-test {
      ciena-common-yang:containerptr "true";
      container X {
        leaf y {
          ciena-common-yang:encrypt "y-encrypted";
          ciena-common-yang:encrypt-path "/ciena-common-test/encryption-notification-test/X";
          type string;
        }
        leaf y-encrypted {
          type string {
            ciena-common-yang:stringptr "true";
          }
          ciena-common-yang:decrypt "y";
          ciena-common-yang:decrypt-path "/ciena-common-test/encryption-notification-test/X";
        }
      }
    }
    container stack-push {
      description
        "Push into thread specific stack";
      container input {
        ciena-common-yang:containerptr "true";
      }
      container output {
        ciena-common-yang:containerptr "true";
      }
    }
    container stack-pop {
      description
        "Pop from thread specific stack";
      container input {
        ciena-common-yang:containerptr "true";
      }
      container output {
        ciena-common-yang:containerptr "true";
      }
    }
    container stack-get {
      description
        "Get pushed data for an attribute";
      container input {
        ciena-common-yang:containerptr "true";
      }
      container output {
        ciena-common-yang:containerptr "true";
      }
    }
    container stack-merge {
      description
        "Merge thread specific stacks";
      container input {
        ciena-common-yang:containerptr "true";
      }
      container output {
        ciena-common-yang:containerptr "true";
      }
    }
    container return-code-set {
      description
        "Set the return code in the response";
      container input {
        ciena-common-yang:containerptr "true";
      }
      container output {
        ciena-common-yang:containerptr "true";
      }
    }
    container validate-test {
      description
        "Set the return code in the response";
      container input {
        ciena-common-yang:containerptr "true";
      }
      container output {
        ciena-common-yang:containerptr "true";
      }
    }
    container test-deadline-timeout {
      description
        "Take input as timeout and handler will wait till this time
          based on test scenario type and return pass as true/false.";
      container input {
        ciena-common-yang:containerptr "true";
      }
      container output {
        ciena-common-yang:containerptr "true";
      }
    }
    container client-activations {
      description
        "Sometimes you are testing something and you just need a simple way to execute a task.";
      container input {
        ciena-common-yang:containerptr "true";
      }
    }
  }

  uses ciena-common-test-mount-data;

  grouping deadline-group {
    leaf wait-time {
      type uint8 {
        range "5..30";
      }
    }
    leaf test-scenario {
      type enumeration {
        enum sunny;
        enum rainy;
      }
    }
  }

  grouping abc_group {
    leaf a {
      type uint8;
    }
    leaf b {
      type uint8;
      default "22";
    }
    leaf c {
      type uint8;
      default "44";
    }
    leaf d {
      type uint8;
      default "88";
    }
  }

  grouping abc_validate_group {
    leaf a {
      type uint8;
      mandatory true;
    }
    leaf b {
      type uint8;
      default "22";
    }
    leaf c {
      type uint8;
      default "44";
    }
    leaf d {
      type uint8;
      default "88";
    }
  }

  grouping red-blue-group {
    container red {
      container blue {
        uses abc_group;
      }
    }
  }

  grouping blue-yellow-group {
    container blue {
      container yellow {
        uses abc_group;
      }
    }
  }

  grouping ordered-lists-group {
    container ordered-lists {
      list ordered-list {
        key "index";
        ordered-by user;
        leaf index {
          type uint8;
        }
        leaf value {
          type uint8;
        }
      }
      leaf-list ordered-leaf-list {
        ordered-by user;
        type uint8;
      }
    }
  }

  identity crypto-alg;

  identity des {
    base crypto-alg;
  }

  identity exception-a {
    base ciena-common-exceptions:exception;
  }

  identity exception-b {
    base ciena-common-exceptions:exception;
  }

  identity exception-c {
    base ciena-common-exceptions:exception;
  }

  identity exception-d {
    base exception-c;
  }

  identity des3 {
    base des;
  }

  identity des4 {
    base des3;
  }

  identity des3-unused;

  typedef typetest {
    type decimal64 {
      fraction-digits 2;
    }
  }

  typedef stringptr {
    type string {
      ciena-common-yang:stringptr "true";
    }
  }

  grouping small-grouping {
    list root-list-test {
      key "index";
      leaf index {
        type uint8;
      }
      leaf color {
        type enumeration {
          enum red;
          enum green;
          enum blue;
        }
      }
    }
  }

  grouping grouping-test {
    leaf root-leaf-test {
      type uint8;
    }
    leaf root-instance-identifier-test {
      type instance-identifier;
    }
    uses small-grouping;
    container root-container {
      leaf sibling {
        type string;
        description
          "This leaf is a sibling of the list list-test so that list replaces
           can easily tested, ensuring that a replace on the list won't unset
           this leaf";
      }
      list list-test {
        key "key1 key2";
        leaf key1 {
          type stringptr;
        }
        leaf key2 {
          type typetest;
        }
        action no-inout-action-test;
        action action-test {
          input {
            leaf in {
              type string;
            }
          }
          output {
            leaf out {
              type string;
            }
          }
        }
        uses list-test-inner;
      }
    }
  }

  grouping grouping-no-action-test {
    leaf root-leaf-test {
      type uint8;
    }
    uses small-grouping;
    container root-container {
      list list-test {
        key "key1 key2";
        leaf key1 {
          type string;
        }
        leaf key2 {
          type typetest;
        }
        uses list-test-inner;
      }
    }
  }

  grouping list-test-inner {
    container leaf-list-test {
      leaf-list binary-test {
        type binary;
      }
      leaf-list bits-test {
        type bits {
          bit disable-nagle {
            position 0;
          }
          bit auto-sense-speed {
            position 1;
          }
        }
      }
      leaf-list boolean-test {
        type boolean;
      }
      leaf-list decimal64-test {
        type decimal64 {
          fraction-digits 10;
        }
      }
      leaf-list empty-test {
        type empty;
      }
      leaf-list enumeration-test {
        type enumeration {
          enum test-a;
          enum test-b;
          enum test-c;
          enum map;
        }
      }
      leaf-list identityref-test {
        type identityref {
          base test:crypto-alg;
        }
      }
      leaf-list instance-identifier-test {
        type instance-identifier;
      }
      leaf-list target-node-test {
        type ciena-common-yang:target-node;
      }
      leaf-list int8-test {
        type int8;
      }
      leaf-list int16-test {
        type int16;
      }
      leaf-list int32-test {
        type int32;
      }
      leaf-list int64-test {
        type int64;
      }
      leaf-list leafref-test {
        type leafref {
          path "/test:red/test:blue/test:b";
        }
      }
      leaf-list stringptr-test {
        type stringptr;
      }
      leaf-list string-test {
        type string;
      }
      leaf-list uint8-test {
        type uint8;
      }
      leaf-list uint16-test {
        type uint16;
      }
      leaf-list uint32-test {
        type uint32;
      }
      leaf-list uint64-test {
        type uint64;
      }
      leaf-list union-test {
        type union {
          type int32;
          type enumeration {
            enum unbounded;
          }
        }
      }
    }
    container leaf-test {
      leaf binary-test {
        type binary;
        ciena-common-yang:sensitive "true";
      }
      leaf bits-test {
        ciena-common-yang:sensitive "true";
        type bits {
          bit apple {
            position 0;
          }
          bit orange {
            position 1;
          }
          bit banana {
            position 2;
          }
        }
      }
      leaf offset-bits-test {
        ciena-common-yang:sensitive "true";
        type bits {
          bit apple {
            position 3;
          }
          bit orange {
            position 5;
          }
          bit banana {
            position 60;
          }
        }
      }
      leaf boolean-test {
        ciena-common-yang:sensitive "true";
        type boolean;
      }
      leaf decimal64-test {
        ciena-common-yang:sensitive "true";
        type decimal64 {
          fraction-digits 2;
        }
      }
      leaf empty-test {
        ciena-common-yang:sensitive "true";
        type empty;
      }
      leaf enumeration-test {
        ciena-common-yang:sensitive "true";
        type enumeration {
          enum test-1;
          enum test-2;
          enum test-3;
        }
      }
      leaf enumeration-extended-test {
        ciena-common-yang:sensitive "true";
        type enumeration {
          enum forty-one {
            value 41;
          }
          enum ten {
            value 10;
          }
          enum seven {
            value 7;
          }
        }
      }
      leaf identityref-test {
        ciena-common-yang:sensitive "true";
        type identityref {
          base test:crypto-alg;
        }
      }
      leaf instance-identifier-test {
        ciena-common-yang:sensitive "true";
        type instance-identifier;
      }
      leaf target-node-test {
        ciena-common-yang:sensitive "true";
        type ciena-common-yang:target-node;
      }
      leaf int8-test {
        ciena-common-yang:sensitive "true";
        type int8;
      }
      leaf int16-test {
        ciena-common-yang:sensitive "true";
        type int16;
      }
      leaf int32-test {
        ciena-common-yang:sensitive "true";
        type int32;
      }
      leaf int64-test {
        ciena-common-yang:sensitive "true";
        type int64;
      }
      leaf leafref-test {
        ciena-common-yang:sensitive "true";
        type leafref {
          path "/test:red/test:blue/test:c";
        }
      }
      leaf stringptr-test {
        ciena-common-yang:sensitive "true";
        type string {
          ciena-common-yang:stringptr "true";
        }
      }
      leaf string-test {
        ciena-common-yang:sensitive "true";
        type string {
          length "0..15";
        }
      }
      leaf uint8-test {
        ciena-common-yang:sensitive "true";
        type uint8;
      }
      leaf uint16-test {
        type uint16;
        ciena-common-yang:sensitive "true";
      }
      leaf uint32-test {
        type uint32;
        ciena-common-yang:sensitive "true";
      }
      leaf uint64-test {
        type uint64;
        ciena-common-yang:sensitive "true";
      }
      leaf union-test {
        type union {
          type int32;
          type enumeration {
            enum unbounded;
          }
        }
        ciena-common-yang:sensitive "true";
      }
    }
    anyxml anyxml-test;
    anydata anydata-test;
    list nested-list {
      key "key1 key2";
      leaf key1 {
        type string;
      }
      leaf key2 {
        type instance-identifier;
      }
      list nested-list-two {
        key "key";
        leaf key {
          type string;
        }
        leaf leaf {
          type uint8;
        }
      }
      choice snack {
        case sports-arena {
          leaf pretzel {
            type empty;
          }
          leaf beer {
            type empty;
          }
        }
        case late-night {
          leaf chocolate {
            type enumeration {
              enum dark;
              enum milk;
              enum first-available;
            }
          }
        }
      }
    }
    list nested-list2 {
      key "key1 key2";
      leaf key1 {
        type string;
      }
      leaf key2 {
        type uint8;
      }
      container c1 {
        ciena-common-yang:containerptr "true";
        list l3 {
          key "key1";
          leaf key1 {
            type string;
          }
          container c2 {
            ciena-common-yang:containerptr "true";
            list l4 {
              key "key1";
              leaf key1 {
                type string;
              }
              leaf a {
                type string;
              }
            }
          }
        }
      }
      leaf a {
        type string;
      }
      leaf b {
        type uint8;
      }
      list nested-list3 {
        key "key1 key2";
        leaf key1 {
          type string;
        }
        leaf key2 {
          type uint8;
        }
        leaf a {
          type string;
        }
        leaf b {
          type uint8;
        }
        leaf c {
          type uint16;
        }
        anyxml config;
        list nested-list4 {
          key "key1 key2";
          leaf key1 {
            type string;
          }
          leaf key2 {
            type uint8;
          }
          leaf aa {
            type string;
          }
          leaf bb {
            type uint8;
          }
        }
      }
    }
  }

  grouping enc-test-grouping-1 {
    leaf name {
      type string;
    }
    leaf stats {
      type uint32;
    }
  }

  grouping power-measurement {
    description
      "Power measurements.";
    leaf in-current-power {
      type decimal64 {
        fraction-digits 1;
      }
    }
    leaf in-min-power {
      type decimal64 {
        fraction-digits 1;
      }
    }
  }

  grouping result-grouping {
    list amp {
      key "amp_name";
      leaf amp_name {
        type string;
      }
      list measurement-no-power {
        description
          "Power measurements of span measured with all channels blocked.";
        key "index";
        leaf index {
          type uint8;
        }
        uses power-measurement;
        config false;
      }
    }
  }

  rpc toggle-sleep {
    input {
      leaf sleep {
        type boolean;
      }
    }
  }

  rpc rpc-test-empty;

  rpc rpc-test-no-output {
    input {
      leaf input-test {
        type string;
      }
    }
  }

  rpc rpc-test-no-input {
    output {
      leaf input-test {
        type string;
      }
    }
  }

  rpc rpc-test {
    input {
      uses grouping-no-action-test;
    }
    output {
      uses grouping-no-action-test;
    }
  }

  rpc rpc-trigger-encryption-set {
    input {
      leaf path {
        type instance-identifier;
      }
    }
  }

  notification notification-test {
    uses red-blue-group;
  }

  notification encryption-notification-test {
    container X {
      leaf y {
        ciena-common-yang:encrypt "y-encrypted";
        ciena-common-yang:encrypt-path "/ciena-common-test/encryption-notification-test/X";
        type string;
      }
      leaf y-encrypted {
        type string {
          ciena-common-yang:stringptr "true";
        }
        ciena-common-yang:decrypt "y";
        ciena-common-yang:decrypt-path "/ciena-common-test/encryption-notification-test/X";
      }
    }
  }

  augment "/test:root-container/test:list-test/test:leaf-list-test" {
    leaf augment-leaf {
      type uint16;
    }
  }

  rpc stack-push {
    description
      "Push into thread specific stack";
    input {
      leaf attr {
        type string;
        default "ddy_stack_test";
      }
      leaf recursive {
        type uint64;
        default "10";
      }
      leaf multistack {
        type uint64;
        default "0";
      }
    }
    output {
      leaf pass {
        type boolean;
      }
    }
  }

  rpc stack-pop {
    description
      "Pop from thread specific stack";
    input {
      leaf attr {
        type string;
        default "ddy_stack_test";
      }
      leaf recursive {
        type uint64;
        default "10";
      }
      leaf multistack {
        type uint64;
        default "0";
      }
    }
    output {
      leaf pass {
        type boolean;
      }
      leaf-list pop {
        type string;
      }
    }
  }

  rpc stack-get {
    description
      "Get pushed data for an attribute";
    input {
      leaf attr {
        type string;
        default "ddy_stack_test";
      }
      leaf recursive {
        type uint64;
        default "10";
      }
      leaf multistack {
        type uint64;
        default "0";
      }
    }
    output {
      leaf pass {
        type boolean;
      }
      leaf-list get {
        type string;
      }
    }
  }

  rpc stack-merge {
    description
      "Merge thread specific stacks";
    input {
      leaf attr {
        type string;
        default "ddy_stack_test";
      }
      leaf count {
        type uint64;
        default "0";
      }
      leaf all {
        type boolean;
      }
    }
    output {
      leaf pass {
        type boolean;
      }
    }
  }

  rpc return-code-set {
    description
      "Set the return code in the response";
    input {
      leaf return-code {
        type identityref {
          base ciena-common-yang:error-code;
        }
      }
    }
    output {
      leaf pass {
        type boolean;
      }
    }
  }

  rpc validate-test {
    description
      "Set the return code in the response";
    input {
      uses abc_validate_group;
      container sub-group {
        uses abc_validate_group;
      }
    }
    output {
      uses ciena-common-yang:rpc-result-common;
    }
  }

  rpc test-deadline-timeout {
    description
      "Take input as timeout and handler will wait till this time
        based on test scenario type and return pass as true/false.";
    input {
      uses deadline-group;
    }
    output {
      leaf pass {
        type boolean;
      }
    }
  }

  augment "/test:root-container/test:list-test/test:nested-list/test:snack/test:sports-arena" {
    ciena-common-yang:augment-name "poutine";
    leaf poutine {
      type empty;
    }
  }

  augment "/test:root-container/test:list-test/test:nested-list/test:snack" {
    ciena-common-yang:augment-name "case-test";
    case fancy {
      leaf caviar {
        type empty;
      }
    }
  }

  augment "/test:root-container/test:list-test/test:nested-list/test:snack/test:sports-arena" {
    ddf:ddf-struct-version "hot-dog";
    leaf hot-dog {
      type empty;
    }
  }

  augment "/test:root-container/test:list-test" {
    leaf augment-enum {
      type enumeration {
        enum zero {
          value 0;
        }
        enum ten {
          value 10;
        }
        enum seven {
          value 7;
        }
      }
    }
  }

  rpc client-activations {
    description
      "Sometimes you are testing something and you just need a simple way to execute a task.";
    input {
      leaf number {
        description
          "This number can be used to call a specific function.";
        type uint64;
      }
    }
  }
}
