module ciena-pro-mc-path {
  namespace "urn:ciena:params:xml:ns:yang:ciena-pro-mc-path";
  prefix pro-mc-path;

  import ciena-common-version {
    prefix ciena-common-version;
  }
  import ciena-pro-optical-types {
    prefix ciena-pro-optical-types;
  }

  organization
    "Ciena Corporation";
  contact
    "Web URL: http://www.ciena.com/
     Postal:  7035 Ridge Road
             Hanover, Maryland 21076
             U.S.A.
     Phone:   +1 800-921-1144
     Fax:     +1 410-694-5750";
  description
    "This module implements a construct to represent a stitched
     path of mc elements.";

  revision 2021-03-24 {
    description
      "Initial version";
    ciena-common-version:version "version" {
      ciena-common-version:string "1.0.0";
    }
  }

  grouping mc-path {
    leaf name {
      type string;
      description
        "This is a path that is constituted by mc elements";
    }
    leaf owner {
      type string;
      description
        "This identifies the provisioning ownership";
    }
    leaf from {
      type instance-identifier;
      mandatory true;
      description
        "From port identifier";
    }
    leaf to {
      type instance-identifier;
      mandatory true;
      description
        "To port identifier";
    }
    leaf min-freq {
      type ciena-pro-optical-types:frequency;
      mandatory true;
      description
        "Minimum frequency edge of the media channel";
    }
    leaf low-freq-deadband {
      type ciena-pro-optical-types:frequency;
      default "6.250";
      description
        "Deadband associated with min-freq edge to account for filter roll off. ";
    }
    leaf max-freq {
      type ciena-pro-optical-types:frequency;
      mandatory true;
      description
        "Maximum frequency edge of the media channel";
    }
    leaf high-freq-deadband {
      type ciena-pro-optical-types:frequency;
      default "6.250";
      description
        "Deadband associated with max-freq edge to account for filter roll off. ";
    }
    leaf user-label {
      type string;
      description
        "a user provisioned label used by discrete MC path elements.";
    }
    list path {
      key "element";
      leaf element {
        type instance-identifier;
        description
          "The identifer of the path element";
      }
    }
  }
}
