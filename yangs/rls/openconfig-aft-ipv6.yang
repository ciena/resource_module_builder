submodule openconfig-aft-ipv6 {
  belongs-to openconfig-aft {
    prefix oc-aft;
  }

  import openconfig-extensions {
    prefix oc-ext;
  }

  import openconfig-inet-types {
    prefix oc-inet;
  }

  include "openconfig-aft-common";

  organization
    "OpenConfig working group";
  contact
    "OpenConfig working group
     www.openconfig.net";
  description
    "Submodule containing definitions of groupings for the abstract
     forwarding tables for IPv6.";

  revision 2019-11-07 {
    description
      "Move lsp-name leaf out of aft-common-entry-nexthop-state group.";
    reference
      "0.4.1";
  }
  revision 2019-08-02 {
    description
      "Add installing protocol for IPv[46] unicast entries.
       Add the ability to describe conditional next-hop groups
       outside of the policy forwarding module to allow for efficient
       handling of CBTS, where many prefixes may share the same next-hop
       criteria.";
    reference
      "0.4.0";
  }
  revision 2019-08-01 {
    description
      "Add lsp-name leaf to AFT next-hop.";
    reference
      "0.3.3";
  }
  revision 2018-11-21 {
    description
      "Add OpenConfig module metadata extensions.";
    reference
      "0.3.2";
  }
  revision 2017-08-24 {
    description
      "Formatting fixes";
    reference
      "0.3.1";
  }
  revision 2017-05-10 {
    description
      "Refactor to provide concretised per-AF schemas per AFT.";
    reference
      "0.3.0";
  }

  oc-ext:openconfig-version "0.4.1";

  grouping aft-ipv6-unicast-structural {
    description
      "Structural grouping defining the schema for the IPv6 unicast
       abstract forwarding table.";
    list ipv6-entry {
      key "prefix";
      description
        "List of the IPv6 unicast entries within the abstract
         forwarding table. This list is keyed by the destination IPv6
         prefix.";
      leaf prefix {
        type leafref {
          path "../config/prefix";
        }
        description
          "Reference to the IPv6 unicast destination prefix which
           must be matched to utilise the AFT entry.";
      }

      container config {
        description
          "Configuration parameters for the IPv6 unicast AFT entry.";
        uses aft-ipv6-unicast-entry-config;
      }

      container state {
        config false;
        description
          "Operational state parameters for the IPv6 unicast AFT
           entry.";
        uses aft-ipv6-unicast-entry-config;

        uses aft-ipv6-unicast-entry-state;
      }
    }
  }

  grouping aft-ipv6-unicast-entry-config {
    description
      "Configuration parameters for the IPv6 unicast entry.";
    leaf prefix {
      type oc-inet:ipv6-prefix;
      description
        "The IPv6 destination prefix that should be matched to
         utilise the AFT entry.";
    }
  }

  grouping aft-ipv6-unicast-entry-state {
    description
      "Operational state parameters for the IPv6 unicast entry.";
    uses aft-common-entry-state;

    uses aft-common-ip-state;
  }
}
