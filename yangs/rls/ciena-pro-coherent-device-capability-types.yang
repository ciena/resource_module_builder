module ciena-pro-coherent-device-capability-types {
  namespace "urn:ciena:ns:yang:coherent-device-capability-types";
  prefix coherent-device-capability-types;

  import ciena-common-version {
    prefix version;
  }
  import ciena-pro-coherent-device-types {
    prefix coherent-device-types;
  }
  import ciena-pro-coherent-device-common-types {
    prefix coherent-device-common-types;
  }

  organization
    "Ciena Corporation";
  contact
    "Web URL: http://www.ciena.com/
     Postal:  7035 Ridge Road
              Hanover, Maryland 21076
              U.S.A.
     Phone:   +1 800-921-1144
     Fax:     +1 410-694-5750";
  description
    "Device capability definitions for coherent device.";

  revision 2024-01-01 {
    description
      "Initial version.";
    version:version "version" {
      version:string "1.0.0";
    }
    reference
      "1.0.0";
  }

  typedef coherent-device-capability-host-interface-format-bits {
    type bits {
      bit OTL4.4 {
        position 1;
        description
          "OTL4.4";
      }
      bit OTL4.2 {
        position 2;
        description
          "OTL4.2";
      }
      bit OTLC.4 {
        position 3;
        description
          "OTLC.4";
      }
      bit OTLC.2 {
        position 4;
        description
          "OTLC.2";
      }
      bit CAUI-4 {
        position 5;
        description
          "CAUI-4";
      }
      bit _100GAUI-2 {
        position 6;
        description
          "100GAUI-2";
      }
      bit _200GAUI-4 {
        position 8;
        description
          "200GAUI-4";
      }
      bit _400GAUI-8 {
        position 10;
        description
          "400GAUI-8";
      }
      bit FOIC1.2 {
        position 12;
        description
          "FOIC1.2";
      }
      bit FOIC1.4 {
        position 13;
        description
          "FOIC1.4";
      }
      bit FOIC2.4 {
        position 14;
        description
          "FOIC2.4";
      }
      bit FOIC2.8 {
        position 15;
        description
          "FOIC2.8";
      }
      bit FOIC4.8 {
        position 16;
        description
          "FOIC4.8";
      }
    }
    description
      "A bit-field defining the supported electrical interface formats
       on the host-interface of a Ciena WaveLogic device";
  }

  typedef coherent-device-capability-host-service-mapping-bits {
    type bits {
      bit CBR {
        position 1;
        description
          "The WaveLogic device supports a CBR mapping of host-interface services
           to/from the device media-interface. This format is supported by WaveLogic Nano devices.";
      }
      bit PKT {
        position 2;
        description
          "The WaveLogic device supports a PKT mapping of host-interface services
           to/from the device media-interface. This format is supported by WaveLogic Nano devices.";
      }
      bit proprietary-400GE {
        position 10;
        description
          "The WaveLogic device supports a proprietary mapping for 400GE. This format is supported by
           some WaveLogic Nano devices.Some Ciena devices and platforms do not support use or interoperability
           with this legacy mapping.";
      }
    }
    description
      "A bit-field defining the supported host-service mappings for a Ciena WaveLogic device.";
  }

  grouping coherent-device-capability-basic-group {
    list transmission-mode-support {
      key "transmission-mode";
      config false;
      leaf transmission-mode {
        type coherent-device-types:coherent-device-media-modes-enum;
        description
          "The transmission mode to which the capabilities defined here are ascribed.
           If a mode is not listed then it is not supported by this specific device.";
      }
      leaf default-link-optimization-mode {
        type coherent-device-types:coherent-device-link-opt-mode-enum;
        description
          "The default link optimization mode for this transmission-mode.";
      }
      list link-optimization-modes {
        key "link-optimization-mode";
        leaf link-optimization-mode {
          type coherent-device-types:coherent-device-link-opt-mode-enum;
          description
            "The name of a link optimization mode.";
        }
        leaf effective-signal-to-noise-ratio-reference {
          type coherent-device-common-types:decimal-3-dig;
          description
            "The effective signal-to-noise ration (ESNR) reference for this transmission-mode
             when using a specific link-optimization-mode.";
        }
        description
          "The link optimization modes and associated attributes supported by this transmission-mode
           and a specific Ciena WaveLogic device instance.";
      }
      description
        "A matrix of supported capabilities of each supported transmission-mode.";
    }
    description
      "Definition of basic Ciena WaveLogic device capabilities.";
  }

  grouping coherent-device-tm-and-lom-performance-spec-group {
    description
      "WaveLogic device transmission-mode and link-optimization-mode related
       performance specification data.";
    leaf spectral-bandwidth-3db {
      type coherent-device-common-types:decimal-3-dig;
      units "GHz";
      description
        "3dB Spectral Bandwidth in units of GHz";
    }
    leaf spectral-bandwidth-10db {
      type coherent-device-common-types:decimal-3-dig;
      units "GHz";
      description
        "10dB Spectral Bandwidth in units of GHz";
    }
    leaf spectral-bandwidth-min {
      type coherent-device-common-types:decimal-3-dig;
      units "GHz";
      description
        "Minimum Spectral Bandwidth in units of GHz";
    }
    leaf tx-power-max {
      type coherent-device-common-types:decimal-2-dig;
      units "dBm";
      description
        "Maximum power output in units of dBm";
    }
    leaf tx-power-min {
      type coherent-device-common-types:decimal-2-dig;
      units "dBm";
      description
        "Minimum power output in units of dBm";
    }
    leaf rx-total-power-high-alarm-threshold {
      type coherent-device-common-types:decimal-2-dig;
      units "dBm";
      description
        "Maximum total power input alarm in units of dBm";
    }
    leaf rx-total-power-high-warning-threshold {
      type coherent-device-common-types:decimal-2-dig;
      units "dBm";
      description
        "Maximum total power input warning in units of dBm";
    }
    leaf rx-total-power-low-alarm-threshold {
      type coherent-device-common-types:decimal-2-dig;
      units "dBm";
      description
        "Minimum total power input alarm in units of dBm";
    }
    leaf rx-total-power-low-warning-threshold {
      type coherent-device-common-types:decimal-2-dig;
      units "dBm";
      description
        "Minimum total power input warning in units of dBm";
    }
    leaf rx-channel-power-high-alarm-threshold {
      type coherent-device-common-types:decimal-2-dig;
      units "dBm";
      description
        "Maximum channel power input alarm in units of dBm";
    }
    leaf rx-channel-power-high-warning-threshold {
      type coherent-device-common-types:decimal-2-dig;
      units "dBm";
      description
        "Maximum channel power input warning in units of dBm";
    }
    leaf rx-channel-power-low-alarm-threshold {
      type coherent-device-common-types:decimal-2-dig;
      units "dBm";
      description
        "Minimum channel power input alarm in units of dBm";
    }
    leaf rx-channel-power-low-warning-threshold {
      type coherent-device-common-types:decimal-2-dig;
      units "dBm";
      description
        "Minimum channel power input warning in units of dBm";
    }
    leaf max-power-consumption {
      type coherent-device-common-types:decimal-1-dig;
      units "Watts";
      description
        "Module max power consumption in units of Watts";
    }
  }

  grouping coherent-device-static-ranges-group {
    description
      "WaveLogic device static range data";
    leaf frequency-resolution {
      type coherent-device-common-types:decimal-1-dig;
      units "GHz";
      description
        "Modem transmitter frequency resolution in units of GHz.";
    }
    leaf tx-frequency-max {
      type coherent-device-common-types:decimal-3-dig;
      units "GHz";
      description
        "Maximum TX frequency in units of GHz";
    }
    leaf tx-frequency-min {
      type coherent-device-common-types:decimal-3-dig;
      units "GHz";
      description
        "Minimum TX frequency in units of GHz";
    }
    leaf tx-wavelength-max {
      type coherent-device-common-types:decimal-3-dig;
      units "nm";
      description
        "Maximum TX wavelength in units of nm";
    }
    leaf tx-wavelength-min {
      type coherent-device-common-types:decimal-3-dig;
      units "nm";
      description
        "Minimum TX wavelength in units of nm";
    }
  }

  grouping coherent-device-capability-raw-group {
    leaf host-interface-format-support {
      type uint32;
      description
        "Raw 32-bit value of Supported Client Interface Types.";
    }
    leaf host-service-mapping-support {
      type uint16;
      description
        "Raw 16-bit value of Supported Client Mappings.";
    }
    description
      "Raw capability data as retrieved directly from the Ciena WaveLogic device.
       Currently only supported for WaveLogic Nano devices.";
  }

  grouping coherent-device-host-interface-capability-group {
    description
      "WaveLogic device host interface capabilities.";
    leaf coherent-host-interface-format-support {
      type coherent-device-capability-host-interface-format-bits;
      description
        "Ciena WaveLogic device host-interface electrical signal formats supported.";
    }
    leaf coherent-host-service-mapping-support {
      type coherent-device-capability-host-service-mapping-bits;
      description
        "Ciena WaveLogic device host-interface service mappings supported.";
    }
    container raw {
      uses coherent-device-capability-raw-group;
      description
        "Raw byte value in the format of a HEX string";
    }
  }

  grouping coherent-device-capability-full-group {
    list transmission-mode-support {
      key "transmission-mode";
      config false;
      leaf transmission-mode {
        type coherent-device-types:coherent-device-media-modes-enum;
        description
          "The transmission mode to which the capabilities defined here are ascribed.
           If a mode is not listed then it is not supported by this specific device.";
      }
      leaf default-link-optimization-mode {
        type coherent-device-types:coherent-device-link-opt-mode-enum;
        description
          "The default link optimization mode for this transmission-mode.";
      }
      list link-optimization-modes {
        key "link-optimization-mode";
        leaf link-optimization-mode {
          type coherent-device-types:coherent-device-link-opt-mode-enum;
          description
            "The name of a link optimization mode.";
        }
        leaf effective-signal-to-noise-ratio-reference {
          type coherent-device-common-types:decimal-3-dig;
          description
            "The effecitive signal-to-noise ration (ESNR) reference for this transmission-mode
             when using a specific link-optimization-mode.";
        }
        uses coherent-device-tm-and-lom-performance-spec-group;
        description
          "The link optimization modes supported and associated attributes for a transmission-mode
           and a specific Ciena WaveLogic device instance.";
      }
      description
        "A matrix of supported capabilities of each supported transmission-mode.";
    }
    uses coherent-device-static-ranges-group;
    uses coherent-device-host-interface-capability-group;
    description
      "Definition of the full set of Ciena WaveLogic device capabilities.";
  }
}
