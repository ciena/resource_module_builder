module ciena-pro-device-controller {
  yang-version 1.1;
  namespace "urn:ciena:params:xml:ns:yang:ciena-pro-device-controller";
  prefix ciena-pro-device-controller;

  import ciena-6500r-types {
    prefix ciena-types;
  }

  import ciena-pro-scaler-types {
    prefix ciena-pro-scaler-types;
  }

  import ciena-pro-optical-types {
    prefix ciena-pro-optical-types;
  }

  import ciena-common-version {
    prefix ciena-common-version;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's 6500r platform device controller ";

  revision 2021-07-15 {
    ciena-common-version:version "version" {
      ciena-common-version:string "2.0.1";
    }
    description
      "RLS Release 2.4 - Added instance-state.";
  }
  revision 2021-06-02 {
    ciena-common-version:version "version" {
      ciena-common-version:string "2.0.0";
    }
    description
      "RLS Release 2.4 - Renamed diag-string to additional-info,
       set max length to 256 characters.";
  }
  revision 2021-04-13 {
    ciena-common-version:version "version" {
      ciena-common-version:string "1.3.0";
    }
    description
      "RLS Release 2.4 - Added band leaf to directed action rpc,
       and take-transmission-profile, re-equalize-dgff actions.";
  }
  revision 2020-11-17 {
    ciena-common-version:version "version" {
      ciena-common-version:string "1.2.0";
    }
    description
      "RLS Release 2.3 - Added band-failed-state flag";
  }
  revision 2020-11-16 {
    ciena-common-version:version "version" {
      ciena-common-version:string "1.1.1";
    }
    description
      "RLS Release 2.2 - Added osc_controller_state";
  }
  revision 2020-10-08 {
    ciena-common-version:version "version" {
      ciena-common-version:string "1.1.0";
    }
    description
      "RLS Release 2.2 - Added max_osc_reach_without_raman, increased composite-name length";
  }
  revision 2020-09-08 {
    ciena-common-version:version "version" {
      ciena-common-version:string "1.0.0";
    }
    description
      "RLS Release 2.1 - Switch to ciena-pro-optical-types
                         First numbered version";
  }
  revision 2019-12-20 {
    description
      "RLS Release 2.0";
  }
  revision 2019-06-18 {
    description
      "6500r-series Release 1.1";
  }
  revision 2018-10-25 {
    description
      "6500r-series Release 1.0";
  }

  identity device-controller {
    base ciena-pro-scaler-types:owner;
    description
      "Extension of the owner type for Device Controller";
  }

  typedef control-type {
    type enumeration {
      enum "preamp" {
        description
          "Preamp Controller";
      }
      enum "booster" {
        description
          "Booster Controller";
      }
      enum "preamp-booster" {
        description
          "Preamp and Booster Controller";
      }
      enum "line-out-voa" {
        description
          "Lineout VOA Controller";
      }
      enum "ase" {
        description
          "ASE controller";
      }
      enum "osc" {
        description
          "OSC controller";
      }
      enum "raman" {
        description
          "Raman amplifier controller";
      }
      enum "dgff" {
        description
          "Dynamic Gain Flattening Filter controller";
      }
    }
  }

  typedef controller-mode {
    type enumeration {
      enum "directed" {
        description
          "Controller is being directed by higher level controller or user";
      }
      enum "operational" {
        description
          "Controller is actively controlling";
      }
    }
    description
      "Device controller mode";
  }

  typedef controller-state {
    type enumeration {
      enum "initializing" {
        description
          "Init mode of the controller upon creation";
      }
      enum "directed" {
        description
          "Controller is being directed by higher level controller or user";
      }
      enum "operational" {
        description
          "Controller is actively controlling";
      }
      enum "operational-frozen" {
        description
          "Controller is currently frozen while in operational mode";
      }
      enum "license-missing" {
        description
          "Controller is unable to retrieve the license";
      }
    }
    description
      "Device controller state";
  }

  typedef action-type {
    type enumeration {
      enum "null-action" {
        description
          "Null action";
      }
      enum "set-edfa-gain-tilt" {
        description
          "Set AMP gain and/or tilt target";
      }
      enum "set-voa-loss" {
        description
          "Set VOA target loss";
      }
      enum "set-osc-tx-power" {
        description
          "Set OSC target power in PWRMON";
      }
      enum "set-dgff-attenuation" {
        description
          "Set the attenuations on the DGFF";
      }
      enum "run-raman-calibration" {
        description
          "Start Raman calibration";
      }
      enum "raman-calibration-response" {
        description
          "Result of the Raman calibration";
      }
      enum "launch-ase" {
        description
          "Launch channel holders with minimum attenuation";
      }
      enum "dial-down-ase" {
        description
          "Set ASE VOA attenuation";
      }
      enum "reset-to-init" {
        description
          "Reset to init state";
      }
      enum "set-baseline-values" {
        description
          "Refreshes baseline values applicable to the controller";
      }
      enum "take-transmission-profile" {
        description
          "Takes transmission profile";
      }
      enum "re-equalize-dgff" {
        description
          "Initializes attenuations to 0dB and re-runs control loop steps";
      }
    }
    description
      "Action that should be performed by controller instance";
  }

  typedef ase-controller-state {
    type enumeration {
      enum "off" {
        description
          "ASE were not launched";
      }
      enum "launched" {
        description
          "ASE were launched at max power";
      }
      enum "dialed-down" {
        description
          "ASE VOA attenuation set";
      }
    }
    description
      "State of ASE controller";
  }

  typedef osc-controller-state {
    type enumeration {
      enum "not-calibrated" {
        description
          "Osc calibration has not been performed";
      }
      enum "idle" {
        description
          "Osc calibration has been performed";
      }
      enum "optical-line-fail-detected" {
        description
          "An optical line fail was detected, calibration will be performed once cleared.";
      }
    }
    description
      "State of Osc controller";
  }

  typedef raman-controller-state {
    type enumeration {
      enum "not-calibrated" {
        description
          "Raman calibration has not been performed";
      }
      enum "calibration-started" {
        description
          "Raman calibration started, waiting for card response";
      }
      enum "calibration-complete" {
        description
          "Raman calibration completed successfully";
      }
      enum "calibration-failed" {
        description
          "Raman calibration failed";
      }
      enum "pump-on" {
        description
          "Raman pump turned on";
      }
    }
    description
      "State of Raman controller";
  }

  grouping diagnostic-info {
    leaf live-state {
      type controller-state;
      description
        "State of the instance";
    }

    leaf additional-info {
      type string {
        length "1..256";
      }
      description
        "Additional info reported by the controller instance";
    }
  }

  grouping instance-state-info {
    leaf state {
      type controller-state;
      description
        "State of the instance";
    }
  }

  grouping shortfall-info {
    leaf band {
      type ciena-pro-optical-types:band-occupancy;
      description
        "Band info";
    }

    leaf value {
      type ciena-types:loss-dB-1-precision;
      description
        "Current controller shortfall";
    }

    leaf upstream-value {
      type ciena-types:loss-dB-1-precision;
      description
        "Upstream controller shortfall";
    }
  }

  grouping bandfail-info {
    leaf band {
      type ciena-pro-optical-types:band-occupancy;
      description
        "Band info";
    }

    leaf band-fail {
      type boolean;
      description
        "Indicates if this band is in a fail state";
    }
  }

  grouping ciena-pro-device-controller-mount {
    list device-controller {
      key "name1 name2";
      leaf name1 {
        type ciena-types:object-name;
        description
          "Name1 of the controller";
      }

      leaf name2 {
        type ciena-types:object-name;
        description
          "Name2 of the controller";
      }

      leaf type {
        type control-type;
        config false;
        description
          "Type of the controller will dictate the control algorithm used";
      }

      leaf mode {
        type controller-mode;
        description
          "Controller mode";
      }

      leaf state {
        type controller-state;
        description
          "Controller state";
      }

      leaf gain-mode-set {
        type boolean;
        description
          "Indicates whether the device controller has set gain mode. Could be used to force device controller to set gain-mode subsequently if set to false.";
      }

      leaf max-target-pwr-set {
        type boolean;
        description
          "Indicates whether the device controller has set maximum target power. Could be used to force device controller to set max-target-pwr subsequently if set to false. ";
      }

      leaf ase-state {
        type ase-controller-state;
        description
          "State of ASE controller";
      }

      leaf raman-state {
        type raman-controller-state;
        description
          "State of Raman controller";
      }

      leaf osc-state {
        type osc-controller-state;
        description
          "State of Osc controller";
      }

      leaf max-osc-reach-without-raman {
        type ciena-types:loss-dB-1-precision;
        description
          "Max osc reach without raman";
      }

      uses ciena-types:admin-state;

      list band-failed-state {
        key "band";
        uses bandfail-info;
      }

      list shortfall {
        key "band";
        uses shortfall-info;
      }

      list instance-state {
        key "composite-name";
        leaf composite-name {
          type string {
            length "1..600";
          }
          description
            "Name of the instance within composite controller";
        }

        uses instance-state-info;
      }

      list diagnostic {
        key "composite-name";
        config false;
        leaf composite-name {
          type string {
            length "1..600";
          }
          description
            "Name of the instance within composite controller";
        }

        uses diagnostic-info;
      }
    }
  }

  grouping ciena-pro-device-controller-mount-actions {
    action dump-ctrl-inst {
      input {
        leaf type {
          type control-type;
          description
            "Controller type to dump";
        }

        leaf instance {
          type uint8;
          description
            "Instance";
        }
      }

      output {
        leaf data {
          type string {
            length "1..5000";
          }
          description
            "Dump data";
        }
      }
    }

    action directed-action {
      description
        "Direct device controller to perform an action";
      input {
        leaf name1 {
          type ciena-types:object-name;
          description
            "Name1 of the controller";
        }

        leaf name2 {
          type ciena-types:object-name;
          description
            "Name2 of the controller";
        }

        leaf action {
          type action-type;
          description
            "Action that should be performed by controller instance";
        }

        leaf band {
          type ciena-pro-optical-types:band-occupancy;
          description
            "Band info";
        }
      }

      output {
        leaf success {
          type boolean;
          description
            "Action completed successfully";
        }
      }
    }
  }

  uses ciena-pro-device-controller-mount;

  rpc dump-ctrl-inst {
    input {
      leaf type {
        type control-type;
        description
          "Controller type to dump";
      }

      leaf instance {
        type uint8;
        description
          "Instance";
      }
    }

    output {
      leaf data {
        type string {
          length "1..5000";
        }
        description
          "Dump data";
      }
    }
  }

  rpc directed-action {
    description
      "Direct device controller to perform an action";
    input {
      leaf name1 {
        type ciena-types:object-name;
        description
          "Name1 of the controller";
      }

      leaf name2 {
        type ciena-types:object-name;
        description
          "Name2 of the controller";
      }

      leaf action {
        type action-type;
        description
          "Action that should be performed by controller instance";
      }

      leaf band {
        type ciena-pro-optical-types:band-occupancy;
        description
          "Band info";
      }
    }

    output {
      leaf success {
        type boolean;
        description
          "Action completed successfully";
      }
    }
  }
}
