module ciena-pro-command-log-internal {
  namespace "urn:ciena:params:xml:ns:yang:ciena-pro-command-log-internal";
  prefix log-internal;

  import ciena-pro-command-log {
    prefix cmd-log;
  }
  import ciena-common-version {
    prefix version;
  }
  import ciena-common-yang {
    prefix yang;
  }

  organization
    "Ciena Corporation";
  contact
    "Web URL: http://www.ciena.com/
     Postal:  7035 Ridge Road
             Hanover, Maryland 21076
             U.S.A.
     Phone:   +1 800-921-1144
     Fax:     +1 410-694-5750";
  description
    "This module defines RPC to set user/system command to command-log-mgr.";

  revision 2023-08-08 {
    description
      "Use ciena-common-yang's return code list for command-log-set RPC.";
    version:version "version" {
      version:string "1.1.0";
    }
  }
  revision 2022-03-14 {
    description
      "The initial definition of the command log data model.";
    version:version "version" {
      version:string "1.0.0";
    }
  }

  grouping command-log-status {
    container command-status {
      description
        "The internal error string by the system after executing the
         specified command.";
      uses yang:rpc-result-common;
    }
  }

  rpc command-log-set {
    description
      "This RPC used for set the user/system command to command-log-mgr
       on the various management interfaces, including CLI and NBI (RESTCONF,
       NETCONF, etc.).";
    input {
      uses cmd-log:command-log-info;
      uses command-log-status;
    }
  }
}
