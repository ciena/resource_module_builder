module ciena-6500r-osrp-rls-ra-osrp-config {
  namespace "urn:ciena:params:xml:ns:yang:ciena-6500r-osrp-rls-ra-osrp-config";
  prefix osrp-config;

  import ietf-inet-types {
    prefix ietf;
  }

  import ietf-yang-types {
    prefix ietf-yang;
  }

  import ciena-6500r-osrp-rls-ra-types {
    prefix ciena-6500r-osrp-rls-ra-types;
  }

  import ciena-common-version {
    prefix ciena-common-version;
  }

  organization
    "Ciena Corporation";
  contact
    "Web URL: http://www.ciena.com
     Postal: Ciena India Pvt. Ltd.
     Sector 32, Plot 14,
     Gurgaon 122001,
     Haryana, India";
  description
    "This module describes Ciena's OSRP shelf level attributes for the 6500r platform";

  revision 2021-02-07 {
    ciena-common-version:string "1.5.0";
    description
      "Audit timer field added.";
  }
  revision 2021-01-09 {
    ciena-common-version:string "1.4.0";
    description
      "Node-id length extended.";
  }
  revision 2021-01-05 {
    ciena-common-version:string "1.3.0";
    description
      "Added new field 'mac-address' and 'node-id' made configurable.";
  }
  revision 2020-11-20 {
    ciena-common-version:string "1.2.0";
    description
      "Removed 'enable-osrp-grouping' field.
       Added new fields 'inventory-version', 'instance-pool', 'system-name' and 'system-ip-address'.";
  }
  revision 2020-07-15 {
    ciena-common-version:string "1.1.0";
    description
      "Added new field 'enable-osrp-grouping' to support PFG grouping feature.";
  }
  revision 2019-11-26 {
    ciena-common-version:string "1.0.0";
    description
      "Renamed module name from osrp to osrp-config and added node list.";
  }
  revision 2019-10-28 {
    ciena-common-version:string "1.0.0";
    description
      "Renamed osrp-rls-ra to osrp in a few places and mounted osrp-node.";
  }
  revision 2019-09-25 {
    ciena-common-version:string "1.0.0";
    description
      "6500r-series Release 2.0
       YANG cleanup.";
  }
  revision 2019-08-16 {
    description
      "Initial revision.";
  }

  container osrp-config {
    description
      "OSRP shelf level data";
    leaf inventory-version {
      type string;
      config false;
      description
        "Version data for the service inventory required during the upgrades.";
    }

    leaf instance-pool {
      type string;
      config false;
      description
        "Represents the bit set for the OSRP instance-ids.";
    }

    leaf mac-address {
      type ietf-yang:mac-address;
      description
        "MAC address.";
    }

    leaf system-name {
      type string;
      description
        "Name of the system/shelf (updated internally not to be modifed directly).";
    }

    leaf system-ip-address {
      type ietf:ip-address;
      description
        "IP Address of the system/shelf (updated internally not to be modifed directly).";
    }

    leaf enable-osrp {
      type ciena-6500r-osrp-rls-ra-types:yes-no;
      default "no";
      config false;
      description
        "Enable OSRP";
    }

    leaf node-name {
      type string {
        length "0..255";
      }
      description
        "Shelf level node name";
    }

    leaf node-id {
      type ciena-6500r-osrp-rls-ra-types:node-id-hex-type;
      description
        "Shelf level node ID";
    }

    leaf conn-prov-mode {
      type ciena-6500r-osrp-rls-ra-types:conn-provisioning-types;
      default "normal";
      description
        "Indicates the mc/nmc prov modes. Default:normal";
    }

    leaf audit-timer {
      type ciena-6500r-osrp-rls-ra-types:timeperiod-sec;
      default "5";
      description
        "Indicates the interval of audit timer in secs. Default is 5secs.";
    }

    list node {
      key "node-name";
      config false;
      description
        "List of OSRP nodes";
      leaf node-name {
        type ciena-6500r-osrp-rls-ra-types:osrp-node-name;
        description
          "OSRP node name";
      }
    }
  }
}
