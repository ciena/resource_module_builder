module ciena-pro-cluster-mgmt {
  yang-version 1.1;
  namespace "urn:ciena:params:xml:ns:yang:ciena-pro-cluster-mgmt";
  prefix cluster-mgmt;

  import ciena-common-version {
    prefix ciena-common-version;
  }
  import ciena-pro-cluster-types {
    prefix cluster-types;
  }

  organization
    "Ciena Corporation";
  contact
    "Web URL: http://www.ciena.com/
     Postal:  7035 Ridge Road
             Hanover, Maryland 21076
             U.S.A.
     Phone:   +1 800-921-1144
     Fax:     +1 410-694-5750";
  description
    "This YANG module defines Ciena's internal cluster member list.";

  revision 2022-02-04 {
    description
      "Initial draft of pro-cluster-mgmt yang";
    ciena-common-version:string "1.0.0";
  }

  container cluster {
    list members {
      key "name";
      uses cluster-types:cluster-attribute-group;
      leaf domain {
        type string;
        mandatory true;
        description
          "The domain name of the remote member's service where CC is communicating with.";
      }
      leaf internal-domain {
        type string;
        description
          "A name to uniquely identify the local domain between Cluster-Controller and Driver.";
      }
      leaf is-local {
        type boolean;
        description
          "Indicates that if the this member node is the local node.";
      }
    }
  }
}
