module ciena-wavelogic-agent-key-mapping {
  namespace "urn:ciena:params:xml:ns:yang:ciena-wavelogic-agent-key-mapping";
  prefix wavelogic-agent-key-mapping;

  import ciena-common-version {
    prefix ciena-common-version;
  }
  import ciena-pro-coherent-device-types {
    prefix coherent-device-types;
  }

  organization
    "Ciena Corporation";
  contact
    "Web URL: http://www.ciena.com";
  description
    "Wavelogic Agent key mapping module";

  revision 2023-12-01 {
    description
      "Initial revision";
    ciena-common-version:string "1.0.0";
    reference
      "1.0.0";
  }

  container device-id-to-plug-id {
    list device {
      key "device-id";
      leaf device-id {
        type coherent-device-types:device-id-type;
        description
          "The top-level identifier for a coherent device represented in this list.";
      }
      leaf plug-id {
        type uint32 {
          range "0..99";
        }
        description
          "plug index";
      }
    }
  }
  container plug-id-to-device-id {
    list plug {
      key "plug-id";
      leaf plug-id {
        type uint32 {
          range "0..99";
        }
        description
          "plug index";
      }
      leaf device-id {
        type coherent-device-types:device-id-type;
        description
          "The top-level identifier for a coherent device.";
      }
    }
  }
  container service-group-to-plug-id {
    list service-group {
      key "supporting-resource";
      leaf supporting-resource {
        type instance-identifier;
        description
          "The top-level identifier for a coherent device represented in this list.";
      }
      leaf plug-id {
        type uint32 {
          range "0..99";
        }
        description
          "plug index";
      }
    }
  }
  container plug-id-to-service-group {
    list plug {
      key "plug-id";
      leaf plug-id {
        type uint32 {
          range "0..99";
        }
        description
          "plug index";
      }
      leaf supporting-resource {
        type instance-identifier;
        description
          "The top-level identifier for a service-group.";
      }
    }
  }
}
