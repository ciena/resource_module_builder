module ciena-osrp-dtl-set {
  yang-version 1.1;
  namespace "urn:ciena:params:xml:ns:yang:ciena-osrp-dtl-set";
  prefix dtl-set;

  import ciena-osrp-types {
    prefix ciena-osrp-types;
  }

  import ciena-common-version {
    prefix ciena-common-version;
  }

  organization
    "Ciena Corporation";
  contact
    "Web URL: http://www.ciena.com
     Postal: Ciena India Pvt. Ltd.
     Sector 32, Plot 14,
     Gurgaon 122001,
     Haryana, India";
  description
    "This module describes Ciena's OSRP DTLSET (Designated Transit List Set)
     object model for the 6500r platform";

  revision 2021-03-27 {
    ciena-common-version:string "1.1.0";
    description
      "6500r-series Release 2.0
       change max-elements of prot-dtls to 40.";
  }
  revision 2019-09-06 {
    ciena-common-version:string "1.0.0";
    description
      "6500r-series Release 2.0
       YANG cleanup.";
  }
  revision 2019-04-24 {
    description
      "Initial revision.";
  }

  grouping ciena-osrp-dtl-set-mount {
    list dtl-set {
      key "name";
      leaf name {
        type ciena-osrp-types:dtl-set-key;
        mandatory true;
        description
          "Name of Routing List (DTL SET). To retrieve all, use ALL/all.";
      }

      leaf label {
        type ciena-osrp-types:label;
      }

      leaf uuid {
        type ciena-osrp-types:uuid;
      }

      leaf-list protect-dtls {
        type ciena-osrp-types:dtl-key;
        max-elements 40;
        description
          "List of Protection routes.";
      }

      leaf work-dtl {
        type ciena-osrp-types:dtl-key;
        mandatory true;
        description
          "Working route for this DTLSET.";
      }
    }
  }

  grouping ciena-osrp-dtl-set-mount-actions;

  uses ciena-osrp-dtl-set-mount;
}
