module ciena-ddm-tcp {
  namespace "urn:ciena:params:xml:ns:yang:ciena-ddm-tcp";
  prefix ddm-tcp;

  import ciena-common-yang {
    prefix yang;
  }
  import ciena-ddy-msg {
    prefix ciena-ddy-msg;
  }

  organization
    "Ciena";
  contact
    "";
  description
    "Config parameters for TCP connection";

  revision 2018-10-24 {
    description
      "";
  }

  identity message-length-over-limit {
    base yang:error-code;
    description
      "Message length is over limit";
  }

  identity tcp {
    base ciena-ddy-msg:ddm-protocols;
    description
      "TCP Client/Server";
  }

  augment "/ciena-ddy-msg:domains/ciena-ddy-msg:protocols" {
    when "ciena-ddy-msg:type = 'ciena-ddy-msg:tcp'";
    container tcp-options {
      leaf ipport {
        type string;
        description
          "IP and Port in the URL of the destination.";
      }
      leaf pubipport {
        type string;
        description
          "IP and Port of the publisher to connect to";
      }
      leaf timeout {
        type uint32;
        units "msecs";
        default "5000";
        description
          "Response timeout in millisec";
      }
      leaf keepalive-enabled {
        type boolean;
        default "true";
        description
          "Keepalive option setting";
      }
      leaf keepalive-timeout {
        type uint16;
        units "seconds";
        default "15";
        description
          "Keepalive idle timeout in seconds";
      }
      leaf keepalive-count {
        type uint8;
        default "3";
        description
          "Keepalive count";
      }
      leaf keepalive-interval {
        type uint8;
        units "seconds";
        default "5";
        description
          "Keepalive interval in seconds";
      }
    }
    container yang-version {
      leaf version {
        type uint16;
        default "1";
        description
          "yang version";
      }
    }
  }
}
