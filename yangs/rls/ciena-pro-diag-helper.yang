module ciena-pro-diag-helper {
  namespace "urn:ciena:params:xml:ns:yang:ciena-pro-diag-helper";
  prefix ciena-pro-diag-helper;

  import ciena-common-version {
    prefix ciena-common-version;
  }

  organization
    "Ciena Corporation";
  contact
    "Web URL: http://www.ciena.com/";
  description
    "Ciena Pro Diag Helper. This model consists of diag point lists where key for each entry is name";

  revision 2021-02-22 {
    description
      "Initial version";
    ciena-common-version:string "1.0.0";
  }

  container diag-points {
    list diag-point {
      config true;
      key "name";
      description
        "List of Diag Point names. This list is keyed by the name.";
      leaf name {
        config true;
        type string;
        description
          "Unique Diag Point name";
      }
      leaf enabled {
        config true;
        type boolean;
        description
          "Enables Diag point";
      }
      leaf resource {
        config true;
        type instance-identifier;
        description
          "Path of resources";
      }
    }
  }
}
