module ciena-pro-cluster-types {
  yang-version 1.1;
  namespace "urn:ciena:params:xml:ns:yang:ciena-pro-cluster-types";
  prefix cluster-types;

  import ciena-common-version {
    prefix ciena-common-version;
  }

  organization
    "Ciena Corporation";
  contact
    "Web URL: http://www.ciena.com/
     Postal:  7035 Ridge Road
             Hanover, Maryland 21076
             U.S.A.
     Phone:   +1 800-921-1144
     Fax:     +1 410-694-5750";
  description
    "This YANG module defines common types used for Ciena's consolidated network representation.";

  revision 2022-02-04 {
    description
      "Initial draft of pro-cluster-types yang";
    ciena-common-version:string "1.0.0";
  }

  grouping cluster-attribute-group {
    description
      "Common attributes of cluster members.";
    leaf name {
      type string;
      description
        "Identifier name string of the cluster member, unique within a group.";
    }
  }
}
