module ciena-6500r-logical-protection-group-debug {
  namespace "urn:ciena:params:xml:ns:yang:ciena-6500r-logical-protection-group-debug";
  prefix ciena-6500r-logical-protection-group-debug;

  import ciena-common-version {
    prefix ciena-common-version;
  }

  organization
    "Ciena Corporation";
  contact
    "Web URL: http://www.ciena.com/
     Postal:  7035 Ridge Road
             Hanover, Maryland 21076
             U.S.A.
     Phone:   +1 800-921-1144
     Fax:     +1 410-694-5750";
  description
    "This module describes Ciena's 6500r protection group debug model";

  revision 2022-07-20 {
    description
      "Initial revision";
  }

  rpc evaluate_active_upstream_uncalibrated_path {
    output {
      leaf result {
        type enumeration {
          enum success;
          enum failed;
        }
      }
    }
  }
}
