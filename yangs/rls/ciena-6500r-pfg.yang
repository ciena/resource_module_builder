module ciena-6500r-pfg {
  namespace "urn:ciena:params:xml:ns:yang:ciena-6500r-pfg";
  prefix pfg;

  import ciena-6500r-fg {
    prefix fg-base-defs;
  }

  import ciena-common-version {
    prefix version;
  }

  organization
    "Ciena Corporation";
  contact
    "Web URL: http://www.ciena.com";
  description
    "This modules describes Ciena's Photonic Topology - Photonic Functional Group for the 6500R-Series platform";

  revision 2021-05-28 {
    version:version "version" {
      version:string "1.0.3";
    }
    description
      "Moved config-data to separate yang file";
  }
  revision 2020-11-27 {
    version:version "version" {
      version:string "1.0.2";
    }
    description
      "Adding COMMON-IN and COMMON-OUT roles";
  }
  revision 2020-10-02 {
    version:version "version" {
      version:string "1.0.1";
    }
    description
      "Adding OSCPFIB-MIN and OSCPFIB-MAX attributes";
  }
  revision 2020-04-15 {
    version:version "version" {
      version:string "1.0.0";
    }
    description
      "6500r-series Release 2.0
       Introduced CHANNEL-CONTROLLER ROLE";
  }
  revision 2018-08-22 {
    description
      "6500R-series Release 1.0";
  }

  identity DCI-MUX {
    base fg-base-defs:TYPE;
    description
      "This is a DCI MUX logical group";
  }

  identity DCI-DEMUX {
    base fg-base-defs:TYPE;
    description
      "This is a DCI DEMUX logical group";
  }

  identity DCIAMP {
    base fg-base-defs:TYPE;
    description
      "This is a DCI AMP logical group";
  }

  identity CHANNEL-MUX {
    base fg-base-defs:TYPE;
    description
      "This is a CHANNEL MUX logical group";
  }

  identity CHANNEL-DEMUX {
    base fg-base-defs:TYPE;
    description
      "This is a CHANNEL DEMUX logical group";
  }

  identity SECTION-MUX {
    base fg-base-defs:TYPE;
    description
      "This is a SECTION MUX logical group";
  }

  identity SECTION-DEMUX {
    base fg-base-defs:TYPE;
    description
      "This is a SECTION DEMUX logical group";
  }

  identity LINE-MUX {
    base fg-base-defs:TYPE;
    description
      "This is a LINE MUX logical group";
  }

  identity LINE-DEMUX {
    base fg-base-defs:TYPE;
    description
      "This is a LINE DEMUX logical group";
  }

  identity LINE-AMP {
    base fg-base-defs:TYPE;
    description
      "This is a LINE-AMP logical group";
  }

  identity WSS {
    base fg-base-defs:ROLE;
    description
      "WSS Facility";
  }

  identity OSC {
    base fg-base-defs:ROLE;
    description
      "OSC - depricated to be removed";
  }

  identity LINEIN {
    base fg-base-defs:ROLE;
    description
      "Line in port";
  }

  identity LINEOUT {
    base fg-base-defs:ROLE;
    description
      "Line out port";
  }

  identity LINEINOSC {
    base fg-base-defs:ROLE;
    description
      "Line in OSC";
  }

  identity LINEOUTOSC {
    base fg-base-defs:ROLE;
    description
      "Line out OSC";
  }

  identity PREAMP {
    base fg-base-defs:ROLE;
    description
      "pre AMP";
  }

  identity BOOSTER {
    base fg-base-defs:ROLE;
    description
      "booster AMP";
  }

  identity CHANNEL-AMP {
    base fg-base-defs:ROLE;
    description
      "Channel AMP";
  }

  identity COMMON-IN {
    base fg-base-defs:ROLE;
    description
      "Common In";
  }

  identity COMMON-OUT {
    base fg-base-defs:ROLE;
    description
      "Common Out";
  }

  identity BOUNDARY-IN {
    base fg-base-defs:ROLE;
    description
      "Boundary In Port";
  }

  identity BOUNDARY-OUT {
    base fg-base-defs:ROLE;
    description
      "Boundary Out Port";
  }

  identity ASE-VOA {
    base fg-base-defs:ROLE;
    description
      "ASE VOA";
  }

  identity ASE-AMP {
    base fg-base-defs:ROLE;
    description
      "ASE AMP";
  }

  identity ASE-PORT {
    base fg-base-defs:ROLE;
    description
      "ASE Port";
  }

  identity LINE-OUT-VOA {
    base fg-base-defs:ROLE;
    description
      "Line Out Voa";
  }

  identity RAMAN {
    base fg-base-defs:ROLE;
    description
      "Raman";
  }

  identity PARTNER-PFG {
    base fg-base-defs:ROLE;
    description
      "PARTNER PFG";
  }

  identity BAND-C {
    base fg-base-defs:ROLE;
    description
      "BAND C";
  }

  identity BAND-L {
    base fg-base-defs:ROLE;
    description
      "BAND L";
  }

  identity BAND-1 {
    base fg-base-defs:ROLE;
    description
      "BAND 1";
  }

  identity BAND-2 {
    base fg-base-defs:ROLE;
    description
      "BAND 2";
  }

  identity BAND-3 {
    base fg-base-defs:ROLE;
    description
      "BAND 3";
  }

  identity BAND-4 {
    base fg-base-defs:ROLE;
    description
      "BAND 4";
  }

  identity BAND-5 {
    base fg-base-defs:ROLE;
    description
      "BAND 5";
  }

  identity DGFF {
    base fg-base-defs:ROLE;
    description
      "DGFF Facility";
  }

  identity TELEMETRY {
    base fg-base-defs:ROLE;
    description
      "Telemetry Facility";
  }

  identity UPG-ASE-AMP {
    base fg-base-defs:ROLE;
    description
      "this identifies L-Band ASE source";
  }

  identity LINE-IN-TG {
    base fg-base-defs:ROLE;
    description
      "Line In TG";
  }

  identity CHANNEL-CONTROLLER {
    base fg-base-defs:ROLE;
    description
      "Channel controller";
  }

  identity PFG-ATTR {
    base fg-base-defs:ATTR;
    description
      "This identifies PFG management attributes";
  }

  identity UPSTR-PFG-NEIGHBOR {
    base fg-base-defs:ATTR;
    description
      "This identifies expected upstream PFG neighbor";
  }

  identity DOWNSTR-PFG-NEIGHBOR {
    base fg-base-defs:ATTR;
    description
      "This identifies expected downstream PFG neighbor ";
  }

  identity DISC-UPSTR-PFG-NEIGHBOR {
    base fg-base-defs:ATTR;
    description
      "This identifies discovered upstream PFG neighbor";
  }

  identity DISC-DOWNSTR-PFG-NEIGHBOR {
    base fg-base-defs:ATTR;
    description
      "This identifies discovered downstream PFG neighbor ";
  }

  identity OSCPFIB {
    base fg-base-defs:ATTR;
    description
      "This identifies OSC launch power";
  }

  identity OSCPFIB-MIN {
    base fg-base-defs:ATTR;
    description
      "This identifies minimum OSC launch power";
  }

  identity OSCPFIB-MAX {
    base fg-base-defs:ATTR;
    description
      "This identifies maximum OSC launch power";
  }

  identity DEGREE {
    base fg-base-defs:ATTR;
    description
      "This identifies degree";
  }

  identity BAND {
    base fg-base-defs:ATTR;
    description
      "This identifies band";
  }

  identity MIN-FREQ {
    base fg-base-defs:ATTR;
    description
      "This identifies minimum frequency in THz";
  }

  identity MAX-FREQ {
    base fg-base-defs:ATTR;
    description
      "This identifies maximum frequency in THz";
  }
}
