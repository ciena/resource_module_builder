module ciena-pro-spli-common-types {
  namespace "urn:ciena:params:xml:ns:yang:ciena-pro-spli-common-types";
  prefix spli-types;

  import ciena-common-version {
    prefix ciena-common-version;
  }

  organization
    "Ciena Corporation";
  contact
    "Web URL: http://www.ciena.com/
     Postal:  7035 Ridge Road
              Hanover, Maryland 21076
              U.S.A.
     Phone:   +1 800-921-1144
     Fax:     +1 410-694-5750";
  description
    "This module describes Ciena's SPLI object model";

  revision 2021-01-28 {
    ciena-common-version:string "1.1.2";
    description
      "Added NULL in shelf-name-format-enum ";
  }
  revision 2021-01-26 {
    ciena-common-version:string "1.1.1";
    description
      "Fixed dispersion-mode-enum ";
  }
  revision 2021-01-21 {
    ciena-common-version:string "1.1.0";
    description
      "Add dispersion-mode-enum ";
  }
  revision 2020-09-15 {
    description
      "Initial revision.";
  }

  typedef shelf-number {
    type uint16 {
      range "0..992";
    }
  }

  typedef shelf-name {
    type string {
      length "1..512";
    }
  }

  typedef port-number {
    type uint8 {
      range "0..255";
    }
  }

  typedef sub-port-number {
    type uint8 {
      range "0..255";
    }
  }

  typedef slot-number {
    type uint8 {
      range "0..255";
    }
  }

  typedef sub-slot-number {
    type uint8 {
      range "0..255";
    }
  }

  typedef shelf-name-format-enum {
    type enumeration {
      enum "null" {
        value 0;
      }
      enum "tid" {
        value 1;
      }
      enum "tid-bay" {
        value 2;
      }
      enum "ip" {
        value 3;
      }
    }
    description
      "Far end node name format enumeration identifies how node name is constructed";
  }

  typedef wavelength-spacing-enum {
    type enumeration {
      enum "fixed" {
        value 1;
      }
      enum "flex" {
        value 2;
      }
    }
    description
      "Wavelength spacing indicates whether it is fixed spacing (50/100/200GHz) or flex.";
  }

  typedef dispersion-mode-enum {
    type enumeration {
      enum "auto" {
        value 0;
      }
      enum "fixed" {
        value 1;
      }
      enum "expert" {
        value 2;
      }
      enum "search" {
        value 3;
      }
    }
    description
      "Transmitter Dispersion Compensation mode.";
  }

  typedef port-direction-enum {
    type enumeration {
      enum "tx" {
        description
          "transmit";
      }
      enum "rx" {
        description
          "receive";
      }
      enum "bidirectional" {
        description
          "bidirectional";
      }
    }
    description
      "Port direction enumeration identifies whether the port is uni (tx/rx) or bi-directional";
  }

  typedef line-system-type-enum {
    type enumeration {
      enum "colored" {
        value 0;
        description
          "Colored line system refers to photonic line with fixed wavelength assignments to specific ports ";
      }
      enum "colorless" {
        value 1;
        description
          "Colorless line system refers to photonic line where any wavelength (of any color) can be added/dropped on any port.";
      }
      enum "contentionless" {
        value 2;
        description
          "Contentionless line system refers to photonic line where the same wavelength can be added or dropped at the same add/drop structure.";
      }
      enum "mxcolored" {
        value 3;
        description
          "Coherent select colored line system type";
      }
      enum "cscolorless" {
        value 4;
        description
          "Coherent select colorless line system type";
      }
    }
    description
      "Type of photonic line";
  }

  typedef shelf-status-enum {
    type enumeration {
      enum "unreliable";
      enum "reliable";
      enum "not-verified";
    }
    description
      "Status of the neighbour shelf";
  }

  typedef shelf-type-enum {
    type enumeration {
      enum "null";
      enum "photonic";
      enum "transponder";
      enum "photonic-transponder";
    }
    description
      "Shelf type";
  }

  typedef far-end-address-format-enum {
    type enumeration {
      enum "format-null";
      enum "sl-prt";
      enum "sl-sbsl-prt";
      enum "shl-sl-prt";
      enum "sl-prt-sbprt";
      enum "sl-sbsl-prt-sbprt";
      enum "sl-prtlbl";
    }
    description
      "Far end address format";
  }

  typedef platform-type-enum {
    type enumeration {
      enum "null" {
        value 0;
      }
      enum "6500" {
        value 1;
      }
      enum "5400" {
        value 2;
      }
      enum "8700" {
        value 3;
      }
      enum "waveserver" {
        value 4;
      }
      enum "rls" {
        value 5;
      }
    }
    description
      "Platform type";
  }

  typedef comms-type-enum {
    type enumeration {
      enum "spli-nill";
      enum "spli-udp";
      enum "spli-tcp";
      enum "spli-tcpssh";
      enum "spli-udp-tcp";
      enum "spli-udp-tcpssh";
      enum "spli-local";
    }
    description
      "Supported shelf protocol combination";
  }

  typedef scm-conn-state-e {
    type enumeration {
      enum "scm-conn-state-init";
      enum "scm-conn-state-reqd";
      enum "scm-conn-state-1way";
      enum "scm-conn-state-2way";
      enum "scm-conn-state-estd";
      enum "scm-conn-state-inuse";
    }
    description
      "Supported shelf connection states";
  }
}
