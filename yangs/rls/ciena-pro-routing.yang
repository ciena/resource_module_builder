module ciena-pro-routing {
  namespace "urn:ciena:params:xml:ns:yang:ciena-pro-routing";
  prefix ciena-pro-routing;

  import ciena-common-version {
    prefix ciena-common-version;
  }

  organization
    "Ciena Corporation";
  contact
    "Web URL: http://www.ciena.com/";
  description
    "Provides RPC for routing-mgr service";

  revision 2021-11-19 {
    description
      "Add IP address to the RPC input for routing-protocols-delete and
       routing-protocols-add";
    ciena-common-version:string "1.0.1";
  }
  revision 2019-08-19 {
    description
      "Initial version";
    ciena-common-version:string "1.0.0";
  }

  rpc routing-protocols-delete {
    description
      "This RPC deletes the routing protocols on the specified
       interface";
    input {
      leaf if-name {
        type string {
          length "1..511";
        }
        description
          "Internal interface on which the routing protocols are reset";
      }
      leaf address-family {
        description
          "Address family type defines the IP address family that the
           protocol is running on";
        type enumeration {
          enum IPV4 {
            description
              "Routing protocol running on IPV4";
          }
          enum IPV6 {
            description
              "Routing protocol running on IPV6";
          }
        }
      }
      leaf address {
        type string {
          length "1..255";
        }
        description
          "The IP address associated with the interface.";
      }
    }
    output {
      leaf result {
        type boolean;
        description
          "The result shows TRUE if the routing protocols are reset; otherwise,
           the error happens";
      }
    }
  }

  rpc routing-protocols-add {
    description
      "This RPC adds the routing protocols on the specified
       interface";
    input {
      leaf if-name {
        type string {
          length "1..511";
        }
        description
          "Internal interface on which the routing protocols are reset";
      }
      leaf address-family {
        description
          "Address family type defines the IP address family that the
           protocol is running on";
        type enumeration {
          enum IPV4 {
            description
              "Routing protocol running on IPV4";
          }
          enum IPV6 {
            description
              "Routing protocol running on IPV6";
          }
        }
      }
      leaf address {
        type string {
          length "1..255";
        }
        description
          "The IP address associated with the interface.";
      }
    }
    output {
      leaf result {
        type boolean;
        description
          "The result shows TRUE if the routing protocols are reset; otherwise,
           the error happens";
      }
    }
  }

  rpc apply-routing-policy {
    description
      "This RPC applies the routing policy on all routing protocols referencing
       the routing policy name";
    input {
      leaf rpolicy-name {
        type string {
          length "1..511";
        }
        description
          "routing policy name to be applied.";
      }
    }
    output {
      leaf result {
        type enumeration {
          enum success;
          enum in-progress;
          enum failure;
        }
        description
          "The result shows progress while routing policy is being applied.";
      }
    }
  }

  rpc remove-routing-policy {
    description
      "This RPC removes the routing policy on all routing protocols referencing
       the routing policy name";
    input {
      leaf rpolicy-name {
        type string {
          length "1..511";
        }
        description
          "routing policy name to be removed.";
      }
    }
    output {
      leaf result {
        type enumeration {
          enum success;
          enum in-progress;
          enum failure;
        }
        description
          "The result shows progress while routing policy is being removed.";
      }
    }
  }
}
