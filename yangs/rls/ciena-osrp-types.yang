module ciena-osrp-types {
  namespace "urn:ciena:params:xml:ns:yang:ciena-osrp-types";
  prefix ciena-osrp-types;

  import ietf-yang-types {
    prefix ietf-yang;
  }

  import ietf-inet-types {
    prefix ietf-inet;
  }

  import ciena-common-version {
    prefix ciena-common-version;
  }

  organization
    "Ciena Corporation";
  contact
    "Web URL: http://www.ciena.com
     Postal: Ciena India Pvt. Ltd.
     Sector 32, Plot 14,
     Gurgaon 122001,
     Haryana, India";
  description
    "This module describes Ciena's OSRP data types for usage in Osrp objects model.";

  revision 2021-04-02 {
    ciena-common-version:string "1.6.1";
    description
      "Change transmission-mode to 32 characters max";
  }
  revision 2021-03-10 {
    ciena-common-version:string "1.6.0";
    description
      "Added enum unknown-comms in comms-prov-mode.";
  }
  revision 2021-02-05 {
    ciena-common-version:string "1.5.1";
    description
      "New secondary-state type added.";
  }
  revision 2021-01-28 {
    ciena-common-version:string "1.5.0";
    description
      "New node-id-hex-type type added.";
  }
  revision 2021-01-25 {
    ciena-common-version:string "1.4.0";
    description
      "Link optimization mode changed to enum.";
  }
  revision 2021-01-05 {
    ciena-common-version:string "1.3.3";
    description
      "Added no-fault field in rx-proxy enum type";
  }
  revision 2021-01-05 {
    ciena-common-version:string "1.3.2";
    description
      "node-address-type name corrected.";
  }
  revision 2020-12-23 {
    ciena-common-version:string "1.3.1";
    description
      "Added unknown field in controller state and rx-proxy enum type";
  }
  revision 2020-12-11 {
    ciena-common-version:string "1.3.0";
    description
      "Added new type spectrum";
  }
  revision 2020-12-11 {
    ciena-common-version:string "1.3.0";
    description
      "Added channel controller states and rx proxy status enum values to be used for end to end channel diagnostics.";
  }
  revision 2020-11-16 {
    ciena-common-version:string "1.2.3";
    description
      "Merge various degraded enum values into a single one in osrp-port-fault.";
  }
  revision 2020-10-27 {
    ciena-common-version:string "1.2.2";
    description
      "Removed range from timeperiod-sec and timeperiod-msec";
  }
  revision 2020-10-07 {
    ciena-common-version:string "1.2.1";
    description
      "Arranged faults enumeration.";
  }
  revision 2020-10-01 {
    ciena-common-version:string "1.2.0";
    description
      "Added enumeration comms-prov-mode.";
  }
  revision 2020-09-09 {
    ciena-common-version:string "1.1.1";
    description
      "Changed dtl-key name length.";
  }
  revision 2020-08-10 {
    ciena-common-version:string "1.1.0";
    description
      "Enums for batching-level added.";
  }
  revision 2020-05-11 {
    ciena-common-version:string "1.0.1";
    description
      "Removed duplicate typedefs.";
  }
  revision 2019-09-06 {
    ciena-common-version:string "1.0.0";
    description
      "6500r-series Release 2.0
       YANG cleanup.";
  }
  revision 2019-04-11 {
    description
      "Initial revision.";
  }

  typedef dtl-key {
    type string {
      length "1..1024";
    }
  }

  typedef dtl-set-key {
    type string {
      length "1..1024";
    }
  }

  typedef link-key {
    type string {
      length "1..1024";
    }
  }

  typedef node-key {
    type string {
      length "1..1024";
    }
  }

  typedef snc-key {
    type string {
      length "1..1024";
    }
  }

  typedef snc-group-key {
    type string {
      length "1..1024";
    }
  }

  typedef node-name {
    type string {
      length "3..512";
    }
  }

  typedef snc-group-ckt-name {
    type string {
      length "1..512";
    }
  }

  typedef snc-ckt-name {
    type string {
      length "1..512";
    }
  }

  typedef local-mc-ckt-name {
    type string {
      length "1..512";
    }
  }

  typedef local-mc-ckt-id {
    type string {
      length "1..512";
    }
  }

  typedef local-nmc-ckt-name {
    type string {
      length "1..512";
    }
  }

  typedef local-nmc-ckt-id {
    type string {
      length "1..512";
    }
  }

  typedef route-data {
    type string {
      length "1..1024";
    }
  }

  typedef port-name {
    type string {
      length "1..1024";
    }
  }

  typedef admin-state {
    type enumeration {
      enum "unlocked";
      enum "locked";
    }
  }

  typedef state {
    type enumeration {
      enum "unblocked" {
        description
          "State of entity is unblocked.";
      }
      enum "blocked" {
        description
          "State of entity is blocked. for Link, Alarm will be raised.";
      }
    }
  }

  typedef connection-standard {
    type enumeration {
      enum "MCTTP";
      enum "NMCCTP";
    }
  }

  typedef dp-fault-action {
    type enumeration {
      enum "alarm";
      enum "mesh-restore";
    }
  }

  typedef dtl-exclusive {
    type enumeration {
      enum "preferred";
      enum "working";
      enum "working-protect";
    }
  }

  typedef end-point-state {
    type enumeration {
      enum "orig-down";
      enum "orig-lock-pending";
      enum "orig-creating";
      enum "orig-starting";
      enum "orig-work-pending";
      enum "orig-working";
      enum "orig-preempting";
      enum "orig-protecting";
      enum "orig-recovering";
      enum "term-down";
      enum "term-working-connected";
      enum "orig-reverting";
      enum "orig-pending";
      enum "orig-validating";
      enum "orig-resizing";
    }
  }

  typedef flex-snc-type {
    type enumeration {
      enum "none";
      enum "non-grouped-snc";
      enum "grouped-snc";
      enum "snc-group";
      enum "non-grouped-fixed-snc";
    }
  }

  typedef freq-exclusive {
    type enumeration {
      enum "exclusive";
      enum "preferred";
    }
  }

  typedef operation {
    type enumeration {
      enum "manual-switch";
      enum "manual-switch-to-user-route";
      enum "regroom";
      enum "resize";
      enum "retune";
      enum "revert";
    }
  }

  typedef originating-or-terminating {
    type enumeration {
      enum "originating";
      enum "terminating";
    }
  }

  typedef primary-state {
    type enumeration {
      enum "in-service";
      enum "out-of-service-maintenance" {
        description
          "Out-of-service maintenance for provisioning memory administration";
      }
      enum "out-of-service-autonomous" {
        description
          "Out-of-service autonomous from a failure detected point of view.
           It is not out of service from a state point of view.";
      }
    }
  }

  typedef priority {
    type enumeration {
      enum "high";
      enum "low";
    }
  }

  typedef revert-type {
    type enumeration {
      enum "no-revert";
      enum "delay";
      enum "time-of-day";
    }
  }

  typedef secondary-state {
    type enumeration {
      enum "in-service" {
        description
          "SNC is fully operational.";
      }
      enum "supporting-group-entity-outage" {
        description
          "SNC is not fully operational because one or more supporting entities is not operational.";
      }
      enum "faulted" {
        description
          "SNC is faulted.";
      }
    }
  }

  typedef snc-event {
    type enumeration {
      enum "none";
      enum "start";
      enum "endpoint-active";
      enum "working-connection-active";
      enum "hard-failure";
      enum "soft-failure";
      enum "protection-active";
      enum "protection-released";
      enum "revert-ready";
      enum "revert-failed";
      enum "timer-expiry";
      enum "manual-revert";
      enum "manual-regroom";
      enum "manual-protect-switch";
      enum "shutdown";
      enum "path-defect-set";
      enum "path-defect-clear";
      enum "gige-response";
      enum "auto-regroom";
      enum "nmc-wait";
      enum "mc-validate";
      enum "bandwidth-resize";
    }
  }

  typedef snc-fsm-state {
    type enumeration {
      enum "down";
      enum "creating";
      enum "starting";
      enum "protecting";
      enum "working";
      enum "recovering";
      enum "reverting";
      enum "auto-revert-pending";
      enum "lock-pending";
      enum "regroom-pending";
      enum "pending";
      enum "validating";
      enum "resizing";
      enum "error";
    }
  }

  typedef snc-type {
    type enumeration {
      enum "dynamic";
      enum "permanent";
    }
  }

  typedef spvc-type {
    type enumeration {
      enum "orignating-spvc";
      enum "terminating-spvc";
    }
  }

  typedef link-primary-state {
    type enumeration {
      enum "in-service";
      enum "out-of-service-maintenance" {
        description
          "Out-of-service maintenance for provisioning memory administration";
      }
    }
  }

  typedef node-synchronization-state {
    type enumeration {
      enum "osrp-init";
      enum "osrp-init-port-sync";
      enum "osrp-init-conn-sync";
      enum "osrp-complete";
    }
  }

  typedef pce-ext-int {
    type enumeration {
      enum "internal";
      enum "external";
    }
  }

  typedef node-type {
    type enumeration {
      enum "not-supported";
      enum "6500-coherent-select";
      enum "6500-direct-attach";
      enum "6500-rls";
      enum "6500-s";
      enum "6500-t";
    }
  }

  typedef node-address-type {
    type string {
      length "44";
    }
  }

  typedef node-id-type {
    type uint64;
  }

  typedef node-id-hex-type {
    type string {
      length "16";
    }
  }

  typedef functional-group-type {
    type enumeration {
      enum "unknown";
      enum "channel-function";
      enum "section-function";
      enum "line-function";
    }
  }

  typedef batching-level {
    type enumeration {
      enum "none" {
        description
          "Batching is disabled.";
      }
      enum "level1" {
        description
          "Only Level-1(ConnectionBatchManager) batching is active.";
      }
      enum "level2" {
        description
          "Only Level-2 batching is active.";
      }
      enum "all" {
        description
          "Both Level-1 and Level-2 batching are active.";
      }
    }
  }

  typedef availability {
    type enumeration {
      enum "available";
      enum "not-available";
    }
  }

  typedef grid-type {
    type enumeration {
      enum "dwdm-12500mhz-classic-c-band";
      enum "dwdm-50000mhz-88ch-classic-c-band";
      enum "dwdm-100000mhz-classic-c-band";
      enum "dwdm-50000mhz-96ch-classic-c-band";
      enum "dwdm-flex-classic-c-band";
      enum "dwdm-flex-enhanced-c-band";
      enum "dwdm-12500mhz-enhanced-c-band";
      enum "dwdm-50000mhz-88ch-enhanced-c-band";
      enum "dwdm-100000mhz-enhanced-c-band";
      enum "dwdm-50000mhz-96ch-enhanced-c-band";
      enum "dwdm-fixed-flex-enhanced-c-band";
      enum "dwdm-flex-enhanced-l-band";
      enum "dwdm-flex-enhanced-cl-band";
    }
  }

  typedef comms-prov-mode {
    type enumeration {
      enum "unknown-comms";
      enum "intra-shelf";
      enum "inter-shelf";
      enum "inter-site";
      enum "out-of-band";
    }
  }

  typedef osrp-admin-state {
    type enumeration {
      enum "not-applicable";
      enum "enabled";
      enum "disabled";
    }
  }

  typedef osrp-operational-state {
    type enumeration {
      enum "disabled";
      enum "enabled";
    }
  }

  typedef osrp-port-direction {
    type enumeration {
      enum "unknown";
      enum "mux";
      enum "demux";
    }
  }

  typedef osrp-port-role {
    type enumeration {
      enum "unknown";
      enum "boundary-in";
      enum "boundary-out";
    }
  }

  typedef osrp-port-fault {
    type enumeration {
      enum "none";
      enum "down";
      enum "blocked";
      enum "degraded";
      enum "och-down";
      enum "och-degrade";
    }
  }

  typedef osrp-port-identifier {
    type string;
  }

  typedef band-type {
    type enumeration {
      enum "BAND-C";
      enum "BAND-L";
    }
  }

  typedef port-grid-type {
    type enumeration {
      enum "C-BAND-FLEX";
      enum "L-BAND-FLEX";
      enum "C-L-BAND";
    }
  }

  typedef osrp-port-type {
    type enumeration {
      enum "service";
      enum "routing";
      enum "internal";
    }
  }

  typedef port-type {
    type enumeration {
      enum "service";
      enum "routing";
      enum "internal";
    }
  }

  typedef timestamp {
    type ietf-yang:date-and-time;
  }

  typedef frequency {
    type decimal64 {
      fraction-digits 3;
      range "186075..190875 | 191325..196125";
    }
    units "GHz";
  }

  typedef frequency-mhz {
    type uint32;
    units "MHz";
  }

  typedef ip-address {
    type union {
      type ipv4-address;
      type ipv6-address;
    }
    description
      "The ip-address type represents an IP address and is IP
       version neutral.  The format of the textual representation
       implies the IP version.  This type supports scoped addresses
       by allowing zone identifiers in the address format.";
    reference
      "RFC 4007: IPv6 Scoped Address Architecture";
  }

  typedef ipv4-address {
    type string {
      pattern "(([0-9]|[1-9][0-9]|1[0-9][0-9]|2[0-4][0-9]|25[0-5])\\.){3}([0-9]|[1-9][0-9]|1[0-9][0-9]|2[0-4][0-9]|25[0-5])(%[\\p{N}\\p{L}]+)?";
    }
    description
      "The ipv4-address type represents an IPv4 address in
       dotted-quad notation.  The IPv4 address may include a zone
       index, separated by a % sign.

       The zone index is used to disambiguate identical address
       values.  For link-local addresses, the zone index will
       typically be the interface index number or the name of an
       interface.  If the zone index is not present, the default
       zone of the device will be used.

       The canonical format for the zone index is the numerical
       format";
  }

  typedef ipv6-address {
    type string {
      pattern "((:|[0-9a-fA-F]{0,4}):)([0-9a-fA-F]{0,4}:){0,5}((([0-9a-fA-F]{0,4}:)?(:|[0-9a-fA-F]{0,4}))|(((25[0-5]|2[0-4][0-9]|[01]?[0-9]?[0-9])\\.){3}(25[0-5]|2[0-4][0-9]|[01]?[0-9]?[0-9])))(%[\\p{N}\\p{L}]+)?";
      pattern "(([^:]+:){6}(([^:]+:[^:]+)|(.*\\..*)))|((([^:]+:)*[^:]+)?::(([^:]+:)*[^:]+)?)(%.+)?";
    }
    description
      "The ipv6-address type represents an IPv6 address in full,
       mixed, shortened, and shortened-mixed notation.  The IPv6
       address may include a zone index, separated by a % sign.

       The zone index is used to disambiguate identical address
       values.  For link-local addresses, the zone index will
       typically be the interface index number or the name of an
       interface.  If the zone index is not present, the default
       zone of the device will be used.

       The canonical format of IPv6 addresses uses the textual
       representation defined in Section 4 of RFC 5952.  The
       canonical format for the zone index is the numerical
       format as described in Section 11.2 of RFC 4007.";
    reference
      "RFC 4291: IP Version 6 Addressing Architecture
       RFC 4007: IPv6 Scoped Address Architecture
       RFC 5952: A Recommendation for IPv6 Address Text
       Representation";
  }

  typedef label {
    type string {
      length "0..255";
    }
    description
      "Label for the object.";
  }

  typedef comms-port-num {
    type ietf-inet:port-number {
      range "51001..52000";
    }
  }

  typedef port-num {
    type ietf-inet:port-number;
  }

  typedef spectrum {
    type decimal64 {
      fraction-digits 3;
      range "0..4800";
    }
    units "GHz";
  }

  typedef timeperiod-msec {
    type uint32;
    units "milliseconds";
  }

  typedef timeperiod-sec {
    type uint32;
    units "seconds";
  }

  typedef uuid {
    type string {
      length "0..36";
    }
    description
      "A string of 32 Hexadecimal Digits in five groups seperated
       by hypens in the form xxxxxxxx-xxxx-Mxxx-Nxxx-xxxxxxxxxxxx
       for a total of 36 charatcters, representing the Universally
       Unique Identifier (UUID) of the object.";
  }

  typedef yes-no {
    type enumeration {
      enum "no";
      enum "yes";
    }
  }

  typedef osrp-bitvec {
    type string;
  }

  typedef alarm-type {
    type enumeration {
      enum "low";
      enum "high";
    }
  }

  typedef alarm-severity {
    type enumeration {
      enum "unknown";
      enum "critical";
      enum "major";
      enum "minor";
      enum "warning";
      enum "trivial";
    }
  }

  typedef alarm-service-impact {
    type enumeration {
      enum "non-service-affecting";
      enum "service-affecting";
    }
  }

  typedef osrp-object-type {
    type enumeration {
      enum "osrp";
      enum "osrp-node";
      enum "osrp-link";
      enum "snc";
      enum "snc-group";
    }
  }

  typedef alarm-priority {
    type enumeration {
      enum "0";
      enum "1";
      enum "2";
      enum "3";
    }
    description
      "Default priority: 0. Highest priority: 1. Lowest priority: 3.";
  }

  typedef osrp-local-mc-ckt-name {
    type string;
  }

  typedef osrp-local-mc-ckt-id {
    type string;
  }

  typedef osrp-local-nmc-ckt-name {
    type string;
  }

  typedef osrp-local-nmc-ckt-id {
    type string;
  }

  typedef channel-type {
    type enumeration {
      enum "dynamic";
      enum "permanent";
    }
  }

  typedef conn-owner {
    type enumeration {
      enum "osrp";
      enum "user";
    }
  }

  typedef conn-channel-status {
    type enumeration {
      enum "adding";
      enum "managed";
      enum "deleting";
      enum "switching";
      enum "switched-to-ase";
    }
  }

  typedef transmission-mode {
    type string {
      length "0..32";
    }
  }

  typedef link-optimization-mode {
    type enumeration {
      enum "standard";
      enum "snr-performance";
      enum "fast-tracking";
      enum "spectral-efficiency";
      enum "low-latency";
      enum "narrow-bandwidth-channel";
      enum "non-linear-channel";
      enum "foreign-line";
      enum "reserved-mode-1";
      enum "reserved-mode-2";
      enum "reserved-mode-3";
      enum "custom";
      enum "unknown";
    }
  }

  typedef chromatic-dispersion {
    type decimal64 {
      fraction-digits 2;
    }
    units "ps/nm";
  }

  typedef modem-type {
    type string {
      length "0..100";
    }
    description
      "Types of Modem.";
  }

  typedef link-type {
    type enumeration {
      enum "dwdm-50ghz-classic";
      enum "dwdm-100ghz-classic";
      enum "dwdm-flexgrid-classic";
      enum "dwdm-flexgrid-enhanced";
      enum "dwdm-50ghz-enhanced";
      enum "dwdm-100ghz-enhanced";
      enum "dwdm-fixed-flexgrid-enhanced";
    }
  }

  typedef hex-triplet {
    type string {
      length "10";
    }
  }

  typedef channel-operational-state {
    type enumeration {
      enum "inactive" {
        description
          "Initial channel state";
      }
      enum "waiting-for-power" {
        description
          "Channel is waiting for sufficient power to be selected for addition.";
      }
      enum "pending-add" {
        description
          "Channel has been selected for addition.";
      }
      enum "adding" {
        description
          "Channel is in the process of being added.";
      }
      enum "in-service" {
        description
          "Channel has been added.";
      }
      enum "waiting-for-downstream" {
        description
          "Channel is waiting for the downstream section mux to finish deleting to be selected for deletion.";
      }
      enum "pending-delete" {
        description
          "Channel has been selected for deletion.";
      }
      enum "deleting" {
        description
          "Channel is in the process of being deleted.";
      }
      enum "faulted" {
        description
          "Fault has been declared against the channel.";
      }
      enum "pending-ase-replacement" {
        description
          "The faulted channel has been selected for ASE replacement.";
      }
      enum "replacing-with-ase" {
        description
          "Channel is in the process of being replaced by ASE.";
      }
      enum "ase" {
        description
          "Channel has been replaced by ASE.";
      }
      enum "unknown" {
        description
          "Channel controller state is not known.";
      }
    }
  }

  typedef rx-proxy-status {
    type enumeration {
      enum "rx-degrade";
      enum "rx-down";
      enum "no-fault";
    }
  }

  grouping hop-info {
    leaf nodeid {
      type node-address-type;
      config false;
      description
        "Node Identifier (Hex Formatted).";
    }

    leaf nodename {
      type node-name;
      description
        "Node name.";
    }

    leaf link {
      type link-key;
      description
        "Link name.";
    }
  }
}
