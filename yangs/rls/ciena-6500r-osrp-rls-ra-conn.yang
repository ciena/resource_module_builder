module ciena-6500r-osrp-rls-ra-conn {
  namespace "urn:ciena:params:xml:ns:yang:ciena-6500r-osrp-rls-ra-conn";
  prefix conn;

  import ciena-6500r-osrp-rls-ra-types {
    prefix osrp-rls-ra-types;
  }

  import ciena-common-version {
    prefix ciena-common-version;
  }

  organization
    "Ciena Corporation";
  contact
    "Web URL: http://www.ciena.com/
     Postal:  7035 Ridge Road
             Hanover, Maryland 21076
             U.S.A.
     Phone:   +1 800-921-1144
     Fax:     +1 410-694-5750";
  description
    "This module describes Ciena's osrp-rls-ra - mc/nmc conn object for the 6500r platform";

  revision 2021-01-19 {
    ciena-common-version:string "1.7.0";
    description
      "added ase-hold-off timer.";
  }
  revision 2021-01-05 {
    ciena-common-version:string "1.6.1";
    description
      "removed fetch-controller-state from nmcconn and added no-fault as default for rx-proxy status.";
  }
  revision 2020-12-16 {
    ciena-common-version:string "1.6.0";
    description
      "'mcconn/id' renamed to 'mcconn/mc-key'.
       'mcconn/label' field added.
       'mcconn/nmcconn/id' renamed to 'mcconn/nmcconn/nmc-key'.";
  }
  revision 2020-12-14 {
    ciena-common-version:string "1.5.0";
    description
      "added rx-acquisition-hold-off timer.";
  }
  revision 2020-12-11 {
    ciena-common-version:string "1.4.0";
    description
      "added channel controller state field in nmc-connection.";
  }
  revision 2020-10-18 {
    ciena-common-version:string "1.3.1";
    description
      "leaf-list mc-element and nmc-element changed to list.";
  }
  revision 2020-10-15 {
    ciena-common-version:string "1.3.0";
    description
      "Added mcconn/mc-element and mcconn/nmcconn/nmc-element list.";
  }
  revision 2020-10-07 {
    ciena-common-version:string "1.2.0";
    description
      "Addition of conn type field.";
  }
  revision 2020-01-12 {
    ciena-common-version:string "1.1.0";
    description
      "6500r-series Release 2.0
       YANG cleanup.";
  }
  revision 2019-10-11 {
    description
      "6500r-series Release 2.0
       Added connection yang model";
  }

  grouping nmc-connection {
    description
      "Specifies rx proxy and mux/demux channel controller status.";
    leaf name {
      type osrp-rls-ra-types:osrp-local-nmc-ckt-name;
      mandatory true;
      description
        "Name of Network Media Channel Connection (NMCCONN).";
    }

    leaf nmc-key {
      type osrp-rls-ra-types:osrp-local-nmc-ckt-id;
      mandatory true;
      description
        "Identifier of Network Media Channel Connection.";
    }

    list nmc {
      key "element";
      leaf element {
        type instance-identifier;
        description
          "NMC identifier.";
      }
    }

    leaf center-freq {
      type osrp-rls-ra-types:frequency-mhz;
      mandatory true;
      description
        "Center frequency of Network Media Channel Connection.";
    }

    leaf spectral-width {
      type osrp-rls-ra-types:frequency-mhz;
      mandatory true;
      description
        "Spectral Width of NMC. It's minumum value is 12.5GHz.";
    }

    leaf owner {
      type osrp-rls-ra-types:osrp-conn-owner;
      mandatory true;
      description
        "Owner of Network Media Channel Connection.";
    }

    leaf label {
      type string {
        length "0..64";
      }
      description
        "Label of Network Media Channel Connection.";
    }

    leaf transmission-mode {
      type osrp-rls-ra-types:osrp-conn-trans-mode;
      description
        "transmission mode.";
    }

    leaf link-optimization-mode {
      type osrp-rls-ra-types:osrp-conn-lom;
      description
        "link optimization mode.";
    }

    leaf dispersion {
      type osrp-rls-ra-types:osrp-conn-dispersion;
      description
        "Path Chromatic Dispersion.";
    }

    leaf rx-acquisition-hold-off {
      type osrp-rls-ra-types:timeperiod-msec;
      default "200000";
      description
        "Rx acquisition hold-off time (expected-restoration time).";
    }

    leaf ase-hold-off {
      type osrp-rls-ra-types:timeperiod-msec;
      default "30000";
      description
        "ASE hold-off time.";
    }

    uses channel-controller-state;
  }

  grouping channel-controller-state {
    list channel-controller-status {
      key "instance-name";
      leaf instance-name {
        type string;
        description
          "Specifies instance name of the corresponding channel controller.";
      }

      leaf operational-state {
        type osrp-rls-ra-types:channel-operational-state;
        description
          "Specifies current operational state of channel controller.";
      }

      leaf additional-info {
        type string {
          length "0..1024";
        }
        description
          "Specifies additional info about channel controller status.";
      }
    }

    container rx-status {
      leaf status {
        type osrp-rls-ra-types:rx-proxy-status;
        default "no-fault";
        description
          "Specifies rx-proxy current status.";
      }
    }
  }

  list mcconn {
    key "name";
    leaf name {
      type osrp-rls-ra-types:osrp-local-mc-ckt-name;
      description
        "Name of Media Channel Connection (MCCONN).";
    }

    leaf mc-key {
      type osrp-rls-ra-types:osrp-local-mc-ckt-id;
      mandatory true;
      description
        "Identifier of Media Channel Connection.";
    }

    leaf from {
      type osrp-rls-ra-types:osrp-port-identifier;
      mandatory true;
      description
        "From Port Identifier.";
    }

    leaf to {
      type osrp-rls-ra-types:osrp-port-identifier;
      mandatory true;
      description
        "To Port Identifier.";
    }

    leaf min-freq {
      type osrp-rls-ra-types:frequency-mhz;
      mandatory true;
      description
        "Minimum Frequency of Media Channel Connection.";
    }

    leaf max-freq {
      type osrp-rls-ra-types:frequency-mhz;
      mandatory true;
      description
        "Maximum Frequency of Media Channel Connection.";
    }

    leaf low-freq-deadband {
      type osrp-rls-ra-types:frequency-mhz;
      description
        "Lower Edge Spacing.";
    }

    leaf high-freq-deadband {
      type osrp-rls-ra-types:frequency-mhz;
      description
        "Higher Edge Spacing.";
    }

    leaf label {
      type string {
        length "0..64";
      }
      description
        "Label of Media Channel Connection.";
    }

    leaf owner {
      type osrp-rls-ra-types:osrp-conn-owner;
      mandatory true;
      description
        "Owner of Media Channel Connection.";
    }

    list mc {
      key "element";
      leaf element {
        type instance-identifier;
        description
          "MC identifier.";
      }
    }

    leaf node-name {
      type osrp-rls-ra-types:osrp-node-name;
      description
        "Name of OSRP Node which created this conn.";
    }

    leaf type {
      type osrp-rls-ra-types:channel-type;
      description
        "Type of channel, dynamic or permanent.";
    }

    list nmcconn {
      key "name";
      uses nmc-connection;
    }
  }
}
