module CIENA-6500R-INVENTORY-AMPS-MIB {
  namespace "urn:ietf:params:xml:ns:yang:smiv2:CIENA-6500R-INVENTORY-AMPS-MIB";
  prefix ciena-6500r-inventory;

  import CIENA-6500R-INVENTORY-MIB {
    prefix ciena-6500r;
  }
  import CIENA-6500R-TYPES-MIB {
    prefix ciena-6500r-types;
  }
  import CIENA-PRO-TYPES-MIB {
    prefix ciena-pro;
  }
  import SNMPv2-TC {
    prefix smiv2;
  }

  organization
    "Ciena Corporation";
  contact
    "Web URL: http://www.ciena.com/
     Postal:  7035 Ridge Road
     Hanover, Maryland 21076
     U.S.A.
     Phone:   +1 800-921-1144
     Fax:    Inventory +1 410-694-5750";
  description
    "This modules describes Ciena's photonic amplifier object.";

  revision 2021-09-28 {
    description
      "Added new parameter rlsInventoryAmpsGainTilt.";
  }
  revision 2020-09-30 {
    description
      "Initial revision.";
  }

  container cienaRlsInventoryAmpsMIB {
    list rlsInventoryAmpsEntry {
      config false;
      key "rlsInventoryAmpsSlotName rlsInventoryAmpsName";
      description
        "";
      leaf rlsInventoryAmpsSlotName {
        type ciena-pro:DisplayString32;
        config false;
        description
          "The name of the slot.";
      }
      leaf rlsInventoryAmpsName {
        type ciena-pro:DisplayString128;
        config false;
        description
          "Amplifier name.";
      }
      leaf rlsInventoryAmpsAmpMode {
        type enumeration {
          enum power {
            value 1;
          }
          enum gain {
            value 2;
          }
          enum gainclamp {
            value 3;
          }
        }
        config false;
        description
          "Control Mode of the AMP.";
      }
      leaf rlsInventoryAmpsState {
        type enumeration {
          enum unkown {
            value 0;
          }
          enum shutoff {
            value 1;
          }
          enum apr {
            value 2;
          }
          enum normal {
            value 3;
          }
          enum clamped {
            value 4;
          }
        }
        config false;
        description
          "State the amp is in reported by the card.";
      }
      leaf rlsInventoryAmpsGainMode {
        type enumeration {
          enum low {
            value 1;
          }
          enum high {
            value 2;
          }
        }
        config false;
        description
          "Gain Mode of the AMP.";
      }
      leaf rlsInventoryAmpsForcedShutdown {
        type enumeration {
          enum disabled {
            value 1;
          }
          enum enabled {
            value 2;
          }
        }
        config false;
        description
          "Forced EDFA Shutoff State.";
      }
      leaf rlsInventoryAmpsTargetGain {
        type ciena-pro:DisplayString32;
        config false;
        description
          "Target Gain in dB.";
      }
      leaf rlsInventoryAmpsBaselineTargetGain {
        type ciena-pro:DisplayString32;
        config false;
        description
          "Target Gain baseline in dB.";
      }
      leaf rlsInventoryAmpsBaselineTimestamp {
        type ciena-pro:DisplayString32;
        config false;
        description
          "Time stamp for target gain baseline.";
      }
      leaf rlsInventoryAmpsTargetGainRangesLowMin {
        type ciena-pro:DisplayString32;
        config false;
        description
          "";
      }
      leaf rlsInventoryAmpsTargetGainRangesLowMax {
        type ciena-pro:DisplayString32;
        config false;
        description
          "";
      }
      leaf rlsInventoryAmpsTargetGainRangesHighMin {
        type ciena-pro:DisplayString32;
        config false;
        description
          "";
      }
      leaf rlsInventoryAmpsTargetGainRangesHighMax {
        type ciena-pro:DisplayString32;
        config false;
        description
          "";
      }
      leaf rlsInventoryAmpsTargetPower {
        type ciena-pro:DisplayString32;
        units "dBm";
        config false;
        description
          "Target Total Power in dBm.";
      }
      leaf rlsInventoryAmpsTargetPowerRangesMin {
        type ciena-pro:DisplayString32;
        config false;
        description
          "";
      }
      leaf rlsInventoryAmpsTargetPowerRangesMax {
        type ciena-pro:DisplayString32;
        config false;
        description
          "";
      }
      leaf rlsInventoryAmpsTargetGainTilt {
        type ciena-pro:DisplayString32;
        units "dB";
        config false;
        description
          "Gain tilt in dB.";
      }
      leaf rlsInventoryAmpsTargetGainTiltRangesMin {
        type ciena-pro:DisplayString32;
        config false;
        description
          "";
      }
      leaf rlsInventoryAmpsTargetGainTiltRangesMax {
        type ciena-pro:DisplayString32;
        config false;
        description
          "";
      }
      leaf rlsInventoryAmpsShutoffThreshold {
        type ciena-pro:DisplayString32;
        units "dBm";
        config false;
        description
          "Shutoff Threshold in dBm.";
      }
      leaf rlsInventoryAmpsShutoffThresholdRangesMin {
        type ciena-pro:DisplayString32;
        config false;
        description
          "";
      }
      leaf rlsInventoryAmpsShutoffThresholdRangesMax {
        type ciena-pro:DisplayString32;
        config false;
        description
          "";
      }
      leaf rlsInventoryAmpsShutoffHysteresis {
        type ciena-pro:DisplayString32;
        units "dB";
        config false;
        description
          "Shutoff Hysteresis in dBm.";
      }
      leaf rlsInventoryAmpsInputLosThreshold {
        type ciena-pro:DisplayString32;
        units "dBm";
        config false;
        description
          "Threshold at which to declare input loss of signal in dBm.";
      }
      leaf rlsInventoryAmpsInputLosThresholdRangesMin {
        type ciena-pro:DisplayString32;
        config false;
        description
          "";
      }
      leaf rlsInventoryAmpsInputLosThresholdRangesMax {
        type ciena-pro:DisplayString32;
        config false;
        description
          "";
      }
      leaf rlsInventoryAmpsInputLosHysteresis {
        type ciena-pro:DisplayString32;
        units "dB";
        config false;
        description
          "Hysteresis at which to declare of clear the input loss of signal of signal alarm in dB.";
      }
      leaf rlsInventoryAmpsOrlThreshold {
        type ciena-pro:DisplayString32;
        units "dB";
        config false;
        description
          "Threshold at which to declare the optical return loss alarm.";
      }
      leaf rlsInventoryAmpsOrlThresholdRangesMin {
        type ciena-pro:DisplayString32;
        config false;
        description
          "";
      }
      leaf rlsInventoryAmpsOrlThresholdRangesMax {
        type ciena-pro:DisplayString32;
        config false;
        description
          "";
      }
      leaf rlsInventoryAmpsLowOrlHysteresis {
        type ciena-pro:DisplayString32;
        units "dB";
        config false;
        description
          "Hysteresis at which to declare low optical return loss alarm in dB.";
      }
      leaf rlsInventoryAmpsOrlState {
        type ciena-6500r-types:OrlState;
        config false;
        description
          "The ORL State";
      }
      leaf rlsInventoryAmpsGainOffset {
        type ciena-pro:DisplayString32;
        units "dB";
        config false;
        description
          "Gain Offset of the AMP in dB.";
      }
      leaf rlsInventoryAmpsGainOffsetRangesMin {
        type ciena-pro:DisplayString32;
        config false;
        description
          "";
      }
      leaf rlsInventoryAmpsGainOffsetRangesMax {
        type ciena-pro:DisplayString32;
        config false;
        description
          "";
      }
      leaf rlsInventoryAmpsGain {
        type ciena-pro:DisplayString32;
        units "dB";
        config false;
        description
          "The current gain of the amplifier in dB.";
      }
      leaf rlsInventoryAmpsMaxTargetPower {
        type ciena-pro:DisplayString32;
        units "dBm";
        config false;
        description
          "Maximum Target Power in dBm.";
      }
      leaf rlsInventoryAmpsMaxTargetPowerRangesMin {
        type ciena-pro:DisplayString32;
        config false;
        description
          "";
      }
      leaf rlsInventoryAmpsMaxTargetPowerRangesMax {
        type ciena-pro:DisplayString32;
        config false;
        description
          "";
      }
      leaf rlsInventoryAmpsAprThreshold {
        type ciena-pro:DisplayString32;
        units "dBm";
        config false;
        description
          "Threshold at which the amplifier enters reduced power mode in dBm.";
      }
      leaf rlsInventoryAmpsAprHysteresis {
        type ciena-pro:DisplayString32;
        units "dB";
        config false;
        description
          "Hysteresis at which the amplifier enters reduced power mode in dB.";
      }
      leaf rlsInventoryAmpsForceApr {
        type smiv2:TruthValue;
        config false;
        description
          "Forced APR.";
      }
      leaf rlsInventoryAmpsAprPowerLevel {
        type ciena-pro:DisplayString32;
        units "dBm";
        config false;
        description
          "Power level of the amplifier when the EDFA is in Automatic Power Reduction mode in dBm.";
      }
      leaf rlsInventoryAmpsOverloadThresholdsInputPsdLowGain {
        type ciena-pro:DisplayString32;
        config false;
        description
          "";
      }
      leaf rlsInventoryAmpsOverloadThresholdsInputPsdHighGain {
        type ciena-pro:DisplayString32;
        config false;
        description
          "";
      }
      leaf rlsInventoryAmpsAdminState {
        type ciena-6500r-types:AdminState;
        config false;
        description
          "Resource administrative state.";
      }
      leaf rlsInventoryAmpsServiceState {
        type enumeration {
          enum active {
            value 1;
          }
          enum idle {
            value 2;
          }
        }
        config false;
        description
          "Service state of the amp.";
      }
      leaf rlsInventoryAmpsInCurrPower {
        type ciena-pro:DisplayString32;
        units "dBm";
        config false;
        description
          "Input power to the AMP in dBm.";
      }
      leaf rlsInventoryAmpsInMinPower {
        type ciena-pro:DisplayString32;
        units "dBm";
        config false;
        description
          "Minimum tidemarked input power to the AMP in dBm. This should be the min power measured since the last measuremnt request in dBm.";
      }
      leaf rlsInventoryAmpsInMaxPower {
        type ciena-pro:DisplayString32;
        units "dBm";
        config false;
        description
          "Maximum tidemarked input power to the AMP in dBm. This should be the max power measured since the last measuremnt request.";
      }
      leaf rlsInventoryAmpsOutCurrPower {
        type ciena-pro:DisplayString32;
        units "dBm";
        config false;
        description
          "Output power from the AMP in dBm.";
      }
      leaf rlsInventoryAmpsOutMinPower {
        type ciena-pro:DisplayString32;
        units "dBm";
        config false;
        description
          "Minimum tidemarked output power from the AMP in dBm. This should be the min power measured since the last measuremnt request.";
      }
      leaf rlsInventoryAmpsOutMaxPower {
        type ciena-pro:DisplayString32;
        units "dBm";
        config false;
        description
          "Maximum tidemarked output power from the AMP in dBm. This should be the max power measured since the last measuremnt request in dBm.";
      }
      leaf rlsInventoryAmpsOpticalReturnLoss {
        type ciena-pro:DisplayString32;
        units "dB";
        config false;
        description
          "Optical return loss (ORL) is the amount of light that is reflected back up the fiber toward the source by
           light reflections off the interface of the polished end surface of the mated connectors and air, you should
           probably check you connection in dB";
      }
      leaf rlsInventoryAmpsDiagnosticInputLossSignal {
        type smiv2:TruthValue;
        config false;
        description
          "Input Loss of Signal.";
      }
      leaf rlsInventoryAmpsDiagnosticShutoffThresholdCrossed {
        type smiv2:TruthValue;
        config false;
        description
          "Shutoff Threshold Crossed.";
      }
      leaf rlsInventoryAmpsDignosticAutomaticShutoff {
        type smiv2:TruthValue;
        config false;
        description
          "Automatic Shutoff.";
      }
      leaf rlsInventoryAmpsDiagnosticAutomaticPowerReductionActive {
        type smiv2:TruthValue;
        config false;
        description
          "Automatic Power Reduction Active.";
      }
      leaf rlsInventoryAmpsDignosticParentFailed {
        type smiv2:TruthValue;
        config false;
        description
          "Parent Object Failed.";
      }
      leaf rlsInventoryAmpsDignosticOpticalLineFailed {
        type smiv2:TruthValue;
        config false;
        description
          "Optical Line Failed.";
      }
      leaf rlsInventoryAmpsDignosticLowOpticalReturnLoss {
        type smiv2:TruthValue;
        config false;
        description
          "Low Optical Return Loss.";
      }
      leaf rlsInventoryAmpsDignosticLossOfSignal {
        type smiv2:TruthValue;
        config false;
        description
          "Loss of Signal.";
      }
      leaf rlsInventoryAmpsDignosticInputOpticalOverload {
        type smiv2:TruthValue;
        config false;
        description
          "Input Optical Overload.";
      }
      leaf rlsInventoryAmpsGainTilt {
        type ciena-pro:DisplayString32;
        units "dB";
        config false;
        description
          "Gain tilt in dB.";
      }
    }
  }
}
