module ciena-6500r-pfg-internal {
  namespace "urn:ciena:params:xml:ns:yang:ciena-6500r-pfg-internal";
  prefix pfg-internal;

  import ciena-6500r-fg {
    prefix fg-base-defs;
  }
  import ciena-common-version {
    prefix version;
  }

  organization
    "Ciena Corporation";
  contact
    "Web URL: http://www.ciena.com";
  description
    "This module describes PFG internal data";

  revision 2021-05-28 {
    description
      "Initial Version";
  }

  grouping config-data {
    list config {
      key "type";
      description
        "This defines a photonic-functional group";
      leaf type {
        type identityref {
          base fg-base-defs:TYPE;
        }
      }
      list supported-attrs {
        key "attr";
        description
          "This defines the supported attributes for a PFG";
        uses attr;
      }
      list supported-roles {
        key "role";
        description
          "This defines the supported roles for a PFG";
        uses role;
      }
    }
  }

  grouping role {
    description
      "role attributes";
    leaf role {
      type identityref {
        base fg-base-defs:ROLE;
      }
    }
    leaf description {
      type string;
    }
    leaf mandatory {
      type boolean;
      default "false";
    }
  }

  grouping attr {
    description
      "PFG attributes";
    leaf attr {
      type identityref {
        base fg-base-defs:ATTR;
      }
    }
    leaf editable {
      type boolean;
      default "false";
    }
    leaf default-value {
      type string;
    }
  }

  uses config-data;

  rpc display-config-data {
    description
      "Display the pre-defined configuration data";
    output {
      uses config-data;
    }
  }
}
