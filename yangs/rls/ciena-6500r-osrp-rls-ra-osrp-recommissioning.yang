module ciena-6500r-osrp-rls-ra-osrp-recommissioning {
  namespace "urn:ciena:params:xml:ns:yang:ciena-6500r-osrp-rls-ra-osrp-recommissioning";
  prefix osrp-rls-ra-osrp-recommissioning;

  import ciena-common-version {
    prefix ciena-common-version;
  }

  organization
    "Ciena Corporation";
  contact
    "Web URL: http://www.ciena.com
     Postal: Ciena India Pvt. Ltd.
     Sector 32, Plot 14,
     Gurgaon 122001,
     Haryana, India";
  description
    "This module provides osrp-recommissioning interface for osrp-rls-ra.";

  revision 2023-04-18 {
    description
      "Initial revision.";
    ciena-common-version:string "1.0.0";
  }

  rpc osrp-recommissioning-procedure {
    description
      "Osrp-recommissioning utility.";
    input {
      leaf operation {
        type enumeration {
          enum delete-osrp {
            description
              "Terminates OSRP instance.";
          }
          enum delete-functional-group {
            description
              "Performs internal inventory cleanup for provided functional-group and terminates any associated OSRP instance.";
          }
          enum reset-osrp {
            description
              "Performs complete OSRP cleanup.";
          }
        }
        description
          "Recommissioning operation to perform.";
        mandatory true;
      }
      leaf data {
        type string;
        description
          "Functional-group name for operation delete-functional-group.
            Osrp-node name for operation delete-osrp.
            \"all\" to delete all.
            Not required for operation reset-osrp.";
      }
    }
    output {
      leaf response {
        type string;
        description
          "Status response of executed operation.";
      }
    }
  }
}
