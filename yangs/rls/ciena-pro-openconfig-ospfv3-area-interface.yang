module ciena-pro-openconfig-ospfv3-area-interface {
  yang-version 1;
  namespace "http://openconfig.net/yang/ciena-pro-openconfig-ospfv3-area-interface";
  prefix cn-ospfv3;

  import ciena-pro-openconfig-ospf {
    prefix oc-ospf;
  }

  import openconfig-extensions {
    prefix oc-ext;
  }

  import openconfig-network-instance {
    prefix oc-ni;
  }

  import ciena-common-version {
    prefix ciena-common-version;
  }

  organization
    "OpenConfig working group";
  contact
    "OpenConfig working group
     www.openconfig.net";
  description
    "This submodule provides OSPFv2 configuration and operational
     state parameters that are specific to the area context";

  revision 2019-08-16 {
    ciena-common-version:string "1.0.0";
    description
      "Initial revision";
  }

  oc-ext:openconfig-version "1.0.0";

  grouping ospfv3-area-interface-config {
    description
      "Structural grouping for configuration and operational state
       parameters that relate to an interface";
    leaf instance-id {
      type uint8;
      default "0";
      description
        "The OSPF protocol instance associated with this OSPF interface.";
    }

    leaf interface-id {
      type uint32;
      description
        "32-bit number uniquely identifying this interface among the
         collection of this router's interface. If it is not specified, the
         interface index can be used.";
    }
  }

  augment "/oc-ni:network-instances/oc-ni:network-instance/oc-ni:protocols/oc-ni:protocol/oc-ospf:ospfv3/oc-ospf:areas/oc-ospf:area/oc-ospf:interfaces/oc-ospf:interface/oc-ospf:config" {
    description
      "OSPFv3 interface paramaters";
    uses ospfv3-area-interface-config;
  }

  augment "/oc-ni:network-instances/oc-ni:network-instance/oc-ni:protocols/oc-ni:protocol/oc-ospf:ospfv3/oc-ospf:areas/oc-ospf:area/oc-ospf:interfaces/oc-ospf:interface/oc-ospf:state" {
    description
      "OSPFv3 interface paramaters";
    uses ospfv3-area-interface-config;
  }
}
