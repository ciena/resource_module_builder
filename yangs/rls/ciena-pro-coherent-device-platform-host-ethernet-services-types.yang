module ciena-pro-coherent-device-platform-host-ethernet-services-types {
  namespace "urn:ciena:ns:yang:ciena-pro-coherent-device-platform-host-ethernet-services-types";
  prefix coherent-device-platform-host-ethernet-services-types;

  import ciena-common-version {
    prefix version;
  }

  organization
    "Ciena Corporation";
  contact
    "Web URL: http://www.ciena.com/
     Postal:  7035 Ridge Road
            Hanover, Maryland 21076
            U.S.A.
     Phone:   +1 800-921-1144
     Fax:     +1 410-694-5750";
  description
    "Coherent-device platform host ethernet services types model.";

  revision 2023-11-01 {
    description
      "Initial version";
    version:version "version" {
      version:string "1.0.0";
    }
    reference
      "1.0.0";
  }

  typedef host-service-ethernet-lsh-timeout-enum {
    type enumeration {
      enum 0 {
        description
          "";
      }
      enum 10 {
        description
          "";
      }
      enum 50 {
        description
          "";
      }
      enum 100 {
        description
          "";
      }
      enum 200 {
        description
          "";
      }
      enum 300 {
        description
          "";
      }
      enum 500 {
        description
          "";
      }
      enum 1000 {
        description
          "";
      }
      enum idle {
        description
          "";
      }
    }
    description
      "";
  }

  typedef host-service-ethernet-fault-inject-type-enum {
    type enumeration {
      enum none {
        description
          "";
      }
      enum lf {
        description
          "";
      }
      enum rf {
        description
          "";
      }
      enum idle-test-pattern {
        description
          "";
      }
    }
    description
      "";
  }

  typedef host-service-ethernet-client-network-odu-conditioning-enum {
    type enumeration {
      enum csf-lf {
        description
          "";
      }
      enum idle {
        description
          "";
      }
      enum ais {
        description
          "";
      }
    }
    description
      "";
  }

  grouping host-ethernet-service-prov-common-group {
    leaf rx-conditioning-type {
      type host-service-ethernet-fault-inject-type-enum;
      description
        "Default is dependent on the interface/host-config/mode";
    }
    leaf rx-conditioning-holdoff {
      type host-service-ethernet-lsh-timeout-enum;
      description
        "";
    }
    leaf tx-conditioning-type {
      type host-service-ethernet-fault-inject-type-enum;
      description
        "";
    }
    leaf auto-condition-client-on-link-degrade {
      type boolean;
      default "true";
      description
        "";
    }
    leaf rmon-enable {
      type boolean;
      description
        "";
    }
    leaf eth-service-odu-conditioning-type {
      type host-service-ethernet-client-network-odu-conditioning-enum;
      description
        "";
    }
    leaf eth-400GE-interop-mode {
      type boolean;
      default "false";
      description
        "Internal host control to determine whether 400GE client mapping should be compatible
         with ASIC AA version mapping (custom_400GE). This is only applicable to -O transmission-modes.";
    }
    description
      "";
  }

  grouping host-ethernet-service-diagnostic-group {
    container diagnostics {
      leaf provisioning-mismatch {
        type boolean;
        default "false";
        description
          "";
      }
      leaf bandwidth-not-available {
        type boolean;
        default "false";
        description
          "There is not enough bandwidth available for the configured host-service
           based on the configured media-interface transmission-mode bit-rate. ";
      }
      leaf rx-local-fault {
        type boolean;
        default "false";
        description
          "";
      }
      leaf rx-remote-fault {
        type boolean;
        default "false";
        description
          "";
      }
      leaf rx-pcs-loss-of-block-lock {
        type boolean;
        default "false";
        description
          "";
      }
      leaf rx-pcs-loss-of-alignment-marker {
        type boolean;
        default "false";
        description
          "";
      }
      leaf rx-hi-bit-error-rate {
        type boolean;
        default "false";
        description
          "";
      }
      leaf rx-loss-of-char-sync {
        type boolean;
        default "false";
        description
          "";
      }
      leaf tx-local-fault {
        type boolean;
        default "false";
        description
          "";
      }
      leaf tx-remote-fault {
        type boolean;
        default "false";
        description
          "";
      }
      leaf tx-pcs-loss-of-block-lock {
        type boolean;
        default "false";
        description
          "";
      }
      leaf tx-pcs-loss-of-alignment-marker {
        type boolean;
        default "false";
        description
          "";
      }
      leaf tx-hi-bit-error-rate {
        type boolean;
        default "false";
        description
          "";
      }
      description
        "Diagnostic point (alarms) definition for an Ethernet service that are only relevant intenally
         to the host platform. Device host-interface services are internal to the host product. Therefore
         most diags/alarms are not exposed externally. ";
    }
    description
      "";
  }

  grouping host-ethernet-service-prov-config-group {
    container ethernet {
      uses host-ethernet-service-prov-common-group;
      description
        "";
    }
    description
      "";
  }

  grouping host-ethernet-service-prov-state-group {
    container ethernet {
      uses host-ethernet-service-prov-common-group;
      uses host-ethernet-service-diagnostic-group;
      description
        "";
    }
    description
      "";
  }
}
