module ciena-pro-fan {
  namespace "urn:ciena:params:xml:ns:yang:ciena-pro-fan";
  prefix fan;

  import ciena-common-version {
    prefix version;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's fan object";

  revision 2021-03-25 {
    version:version "version" {
      version:string "1.0.0";
    }
    description
      "Initial version";
  }

  grouping fan {
    leaf name {
      type string;
      description
        "A fan facility name";
    }

    container speed {
      config false;
      leaf value {
        type uint32;
        units "rpm";
        description
          "Current fan speed value";
      }

      leaf measurement-type {
        type enumeration {
          enum "measured";
          enum "estimated";
        }
        description
          "Flag to indicate if fan speed is measured, estimated.";
      }
    }
  }
}
