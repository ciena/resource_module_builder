module ciena-6500r-openconfig-ra {
  namespace "urn:ciena:params:xml:ns:yang:ciena-6500r-openconfig-ra";
  prefix oc-ra;

  import ciena-common-version {
    prefix version;
  }

  organization
    "Ciena Corporation";
  contact
    "Web URL: http://www.ciena.com/
     Postal:  7035 Ridge Road
             Hanover, Maryland 21076
             U.S.A.
     Phone:   +1 800-921-1144
     Fax:     +1 410-694-5750";
  description
    "This module is used to control and monitor the RLS OpenConfig
     Resource Adaptor.";

  revision 2019-08-09 {
    version:version "version" {
      version:string "1.0.0";
    }
    description
      "Initial revision added for RLS 1.1";
  }

  container openconfig-ra {
    description
      "Element used for control and monitoring of the Resource
       Adaptor";
    leaf enabled {
      type boolean;
      default "false";
      description
        "Indicates if the OpenConfig resource adaptor is enabled or not.";
    }

    leaf persistent-inventory {
      type boolean;
      default "false";
      description
        "Indicates if the CHASSIS, SLOT, and CARD components should be persistent
         and automatically created.  Even if these elements are deleted
         or omitted by a provisisioning request, they would not be removed";
    }

    leaf auto-create {
      type boolean;
      default "false";
      description
        "Indicates if the OpenConfig elements should be automatically created
         when they are created by the RLS side.  This should be false if
         declarative config is being used since anything automatically
         created by the system will be removed if omitted by the next
         config declaration.";
    }

    container caches {
      anyxml fallback;

      anyxml rls;

      anyxml oc;
    }
  }
}
