module ciena-6500r-network-fault {
  yang-version 1.1;
  namespace "urn:ciena:params:xml:ns:yang:ciena-6500r-network-fault";
  prefix network-fault;

  import ciena-6500r-types {
    prefix ciena-6500r-types;
  }

  import ciena-common-version {
    prefix version;
  }

  import ciena-pro-optical-types {
    prefix ciena-pro-optical-types;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's network fault service";

  revision 2020-09-08 {
    version:version "version" {
      version:string "1.2.0";
    }
    description
      "RLS Release 02.01.00 - use ciena-pro-optical-types";
  }
  revision 2020-06-12 {
    version:version "version" {
      version:string "1.1.0";
    }
    description
      "RLS Release 02.00.60 - introduce band specific network fault";
  }
  revision 2019-07-16 {
    version:version "version" {
      version:string "1.0.0";
    }
    description
      "RLS Release 1.1";
  }

  grouping ciena-6500r-network-fault-mount {
    list oms-ingress {
      key "name";
      description
        " An oms-ingress represent the entry point of an Optical Multiplex Section.";
      leaf name {
        type ciena-6500r-types:object-name;
        description
          " The name of the oms-ingress. This must be the name of the line-out PFG ";
      }

      leaf rdi {
        type boolean;
        description
          " Reverse Defect Indicator. It is set when a downstream node detected a problem(fault) on the common path or faults on both c and l bands on the section.";
      }

      list band-specific {
        key "band";
        description
          "band specific fault indication";
        leaf band {
          type ciena-pro-optical-types:band-occupancy;
          description
            "type of band";
        }

        leaf rdi {
          type boolean;
          description
            " Reverse Defect Indicator. It is set when a downstream node detected a problem (fault) per band on the section.";
        }
      }
    }

    list oms-egress {
      key "name";
      description
        " An oms-egress represent the exit point of an Optical Multiplex Section.";
      leaf name {
        type ciena-6500r-types:object-name;
        description
          " The name of the oms-egress. This must be the name of the line-in PFG ";
      }

      leaf fdi {
        type boolean;
        description
          " Forward Defect Indicator. It is set when a problem (fault) on the common path or faults on both c and l bands on the section.";
      }

      list band-specific {
        key "band";
        description
          "band specific fault indication";
        leaf band {
          type ciena-pro-optical-types:band-occupancy;
          description
            "type of band";
        }

        leaf fdi {
          type boolean;
          description
            " Forward Defect Indicator. It is set when a problem (fault) per band has been detected on the section.";
        }
      }
    }

    list ots-ingress {
      key "name";
      description
        " An ots-ingress represent the entry point of an Optical Transport Section.";
      leaf name {
        type ciena-6500r-types:object-name;
        description
          " The name of the ots-ingress. This must be the name of the line-out PFG or amp PFG ";
      }

      leaf rdi {
        type boolean;
        description
          " Reverse Defect Indicator. It is set when a downstream node detected a problem (fault) on the common path or faults on both c and l bands on the transport section (span).";
      }

      leaf fdi {
        type boolean;
        description
          " Forward Defect Indicator. It is set when a problem (fault) on the common path or faults on both c and l bands on the transport section (span).";
      }

      list band-specific {
        key "band";
        description
          "band specific fault indication";
        leaf band {
          type ciena-pro-optical-types:band-occupancy;
          description
            "type of band";
        }

        leaf rdi {
          type boolean;
          description
            " Reverse Defect Indicator. It is set when a downstream node detected a problem (fault) per band on the transport section (span).";
        }

        leaf fdi {
          type boolean;
          description
            " Forward Defect Indicator. It is set when a problem (fault) per band has been detected on the transport section (span).";
        }
      }
    }

    list ots-egress {
      key "name";
      description
        " An ots-egress represent the exit point of an Optical Transport Section.";
      leaf name {
        type ciena-6500r-types:object-name;
        description
          " The name of the ots-egress. This must be the name of the line-in PFG or amp PFG ";
      }

      leaf fdi {
        type boolean;
        description
          " Forward Defect Indicator. It is set when a problem (fault) on the common path or faults on both c and l bands on the transport section (span).";
      }

      list band-specific {
        key "band";
        description
          "band specific fault indication";
        leaf band {
          type ciena-pro-optical-types:band-occupancy;
          description
            "type of band";
        }

        leaf fdi {
          type boolean;
          description
            " Forward Defect Indicator. It is set when a problem (fault) per band has been detected on the transport section (span).";
        }
      }
    }
  }

  grouping ciena-6500r-network-fault-mount-actions;

  uses ciena-6500r-network-fault-mount;
}
