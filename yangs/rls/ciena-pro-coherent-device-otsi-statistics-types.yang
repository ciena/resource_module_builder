module ciena-pro-coherent-device-otsi-statistics-types {
  namespace "urn:ciena:ns:yang:coherent-device-otsi-statistics-types";
  prefix coherent-device-otsi-statistics-types;

  import ciena-common-version {
    prefix version;
  }
  import ciena-pro-coherent-device-statistics-types {
    prefix coherent-device-statistics-types;
  }
  import ciena-pro-wavelogic-device-extension-types {
    prefix wavelogic-device-extension-types;
  }

  organization
    "Ciena Corporation";
  contact
    "Web URL: http://www.ciena.com/
     Postal:  7035 Ridge Road
              Hanover, Maryland 21076
              U.S.A.
     Phone:   +1 800-921-1144
     Fax:     +1 410-694-5750";
  description
    "OTSI statistics definitions for coherent devices.";

  revision 2024-01-01 {
    description
      "Initial version.";
    version:version "version" {
      version:string "1.0.0";
    }
    reference
      "1.0.0";
  }

  grouping coherent-device-otsi-statistics-optical-power-group {
    container input-power-total {
      uses coherent-device-statistics-types:instant-interval-stats-precision2-dBm-group;
      description
        "";
    }
    container output-power-total {
      uses coherent-device-statistics-types:instant-interval-stats-precision2-dBm-group;
      description
        "";
    }
    container input-power-channel {
      uses coherent-device-statistics-types:instant-interval-stats-precision2-dBm-group;
      description
        "";
    }
    description
      "Grouping for OTSI statistics related to optical-power";
  }

  grouping coherent-device-otsi-statistics-coherent-group {
    container pre-fec-ber {
      uses coherent-device-statistics-types:instant-interval-stats-sci-notation-ber-group;
      description
        "";
    }
    container q-factor {
      uses coherent-device-statistics-types:instant-interval-stats-precision3-dB-group;
      description
        "";
    }
    container differential-group-delay {
      uses coherent-device-statistics-types:instant-interval-stats-precision3-ps-group;
      description
        "";
    }
    container polarization-dependent-loss {
      uses coherent-device-statistics-types:instant-interval-stats-precision3-dB-group;
      description
        "";
    }
    container esnr {
      uses coherent-device-statistics-types:instant-interval-stats-precision3-dB-group;
      description
        "";
    }
    container esnr-delta-db {
      uses coherent-device-statistics-types:instant-interval-stats-precision3-dB-group;
      description
        "";
    }
    container osnr {
      uses coherent-device-statistics-types:instant-interval-stats-precision3-dB-group;
      description
        "";
      reference
        "IA OIF-C-CMIS-01.1 Table 7";
    }
    container chromatic-dispersion {
      uses coherent-device-statistics-types:instant-interval-stats-precision3-ps-nm-group;
      description
        "";
    }
    container carrier-frequency-offset {
      uses coherent-device-statistics-types:instant-interval-stats-precision1-mhz-group;
      description
        "";
      reference
        "IA OIF-C-CMIS-01.1 Table 7";
    }
    container error-vector-magnitude {
      uses coherent-device-statistics-types:instant-interval-stats-precision2-percent-group;
      description
        "";
    }
    container modulation-error-ratio {
      uses coherent-device-statistics-types:instant-interval-stats-precision3-dB-group;
      description
        "";
      reference
        "IA OIF-C-CMIS-01.1 Table 7";
    }
    container second-order-polarization-mode-dispersion {
      uses coherent-device-statistics-types:instant-interval-stats-precision3-ps2-group;
      description
        "";
    }
    container state-of-polarization-rate-of-change {
      uses coherent-device-statistics-types:instant-interval-stats-precision1-krads-group;
      description
        "";
      reference
        "IA OIF-C-CMIS-01.1 Table 7";
    }
    description
      "OTSI coherent statistics grouping.";
  }

  grouping coherent-device-otsi-stat-q-factor-std-dev-group {
    uses coherent-device-statistics-types:interval-stat-std-dev-precision3-dB-group;
    description
      "Definition of an interval statistic for Q standard deviation.";
  }

  grouping coherent-device-otsi-statistics-fec-group {
    container uncorrected-frame-count {
      uses coherent-device-statistics-types:instant-interval-total-stats-counter64-group;
      description
        "The number of uncorrectable FEC frames.";
    }
    container uncorrected-second {
      uses coherent-device-statistics-types:instant-total-stats-seconds-count-group;
      description
        "The number of seconds with an uncorrectable FEC frame.";
    }
    container high-correction-count-second {
      uses coherent-device-statistics-types:instant-total-stats-seconds-count-group;
      description
        "The number of seconds where the number of FEC corrections
         exceeded the configurable high-correction-count-second threshold.";
    }
    description
      "OTSI FEC statistics grouping.";
  }

  grouping coherent-device-otsi-reach-latency-group {
    container estimated-reach {
      uses coherent-device-statistics-types:instant-interval-stats-kilometer-group;
      description
        "The estimated reach of an interface reported in kilometers.";
    }
    container estimated-unidirectional-latency {
      uses coherent-device-statistics-types:instant-interval-stats-microseconds-group;
      description
        "The estimated unidirectional latency reported in microseconds.";
    }
    container estimated-round-trip-delay {
      uses coherent-device-statistics-types:instant-interval-stats-microseconds-group;
      description
        "The estimated round-trip-delay reported in microseconds.";
    }
    description
      "";
  }

  grouping coherent-device-otsi-statistics-group {
    container statistics {
      uses coherent-device-statistics-types:stat-bin-details-group;
      list lane {
        key "lane-index";
        leaf lane-index {
          type uint8 {
            range "1..max";
          }
          description
            "The lane number for which the statistic applies.
             Coherent devices typically have a single-lane.";
        }
        uses coherent-device-otsi-statistics-optical-power-group;
        description
          "Per lane OTSI statistics.";
      }
      uses coherent-device-otsi-statistics-coherent-group;
      container fec {
        uses coherent-device-otsi-statistics-fec-group;
        uses wavelogic-device-extension-types:wavelogic-device-otsi-statistics-fec-group;
        description
          "OTSI FEC frame statistics.";
      }
      uses coherent-device-otsi-reach-latency-group;
      description
        "";
    }
    description
      "";
  }
}
