module ciena-pro-neighbours-config {
  namespace "urn:ciena:params:xml:ns:yang:ciena-pro-neighbours-config";
  prefix neighbours-config;

  import ietf-inet-types {
    prefix ietf;
  }

  import ietf-yang-types {
    prefix ietf-yang;
  }

  import ciena-common-version {
    prefix ciena-common-version;
  }

  import ciena-pro-types {
    prefix ciena-pro-types;
  }

  import ciena-pro-spli-common-types {
    prefix ciena-pro-spli-common-types;
  }

  organization
    "Ciena Corporation";
  contact
    "Web URL: http://www.ciena.com/
     Postal:  7035 Ridge Road
              Hanover, Maryland 21076
              U.S.A.
     Phone:   +1 800-921-1144
     Fax:     +1 410-694-5750";
  description
    "This model captures information about neighbours which can be manually configured without specifying local/remote interfaces.";

  revision 2021-03-04 {
    ciena-common-version:version "version" {
      ciena-common-version:string "1.4.0";
    }
    description
      "Change connection-state from scm status to shelf status enum.";
  }
  revision 2021-01-28 {
    ciena-common-version:version "version" {
      ciena-common-version:string "1.3.0";
    }
    description
      "Add IPv6 to config neighbour.";
  }
  revision 2021-01-26 {
    ciena-common-version:version "version" {
      ciena-common-version:string "1.2.0";
    }
    description
      "Added diagnostic/connection-state";
  }
  revision 2020-12-14 {
    ciena-common-version:version "version" {
      ciena-common-version:string "1.1.0";
    }
    description
      "Add platform type to neighbour info.";
  }
  revision 2019-09-04 {
    description
      "Initial Revision";
  }

  list config-neighbours {
    key "name";
    leaf name {
      type string;
      description
        "The name of the neighbour";
    }

    leaf ip-address {
      type ietf:ip-address;
      description
        "The IP address of the neighbour";
    }

    leaf ipv6-address {
      type ietf:ipv6-address-no-zone;
      description
        "The IPv6 address of neighbour.";
    }

    leaf platform-type {
      type identityref {
        base ciena-pro-types:platform-type;
      }
      description
        "Platform type of the neighbour. Examples: 6500, RLS, 5400, Waveserver.";
    }

    leaf mac-address {
      type ietf-yang:mac-address;
      description
        "The MAC address of the neighbour";
    }

    container diagnostic {
      config false;
      leaf connection-state {
        type ciena-pro-spli-common-types:shelf-status-enum;
        description
          "Connection state";
      }
    }
  }
}
