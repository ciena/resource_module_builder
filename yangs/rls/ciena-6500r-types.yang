module ciena-6500r-types {
  namespace "urn:ciena:params:xml:ns:yang:ciena-6500r-types";
  prefix ciena-6500r-types;

  import ciena-common-version {
    prefix ciena-common-version;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's release object for the 6500r platform";

  revision 2021-05-20 {
    ciena-common-version:version "version" {
      ciena-common-version:string "1.0.7";
    }
    description
      "Add power-mW-3-precision type.";
  }
  revision 2020-02-26 {
    ciena-common-version:string "1.0.6";
    description
      "Added typedef orl-state.";
  }
  revision 2020-02-11 {
    ciena-common-version:string "1.0.5";
    description
      "Added typedef sha512.";
  }
  revision 2020-01-21 {
    ciena-common-version:string "1.0.4";
    description
      "Added psd typedef.";
  }
  revision 2019-12-12 {
    ciena-common-version:string "1.0.3";
    description
      "Added restart-type";
  }
  revision 2019-12-03 {
    ciena-common-version:string "1.0.2";
    description
      "Added band-type based on RLS Release 2.0 requirements";
  }
  revision 2019-11-06 {
    ciena-common-version:string "1.0.1";
    description
      "Added 1 precison typedef based on RLS Release 2.0 requirements";
  }
  revision 2017-10-01 {
    ciena-common-version:string "1.0.0";
    description
      "6500r Release 1";
  }

  typedef BOOLEAN {
    type boolean;
  }

  typedef aid {
    type string {
      length "1..32";
    }
  }

  typedef STRING {
    type string {
      length "0..79";
    }
  }

  typedef IDENT {
    type string {
      length "1..32";
    }
  }

  typedef IPADDR {
    type string {
      length "1..16";
    }
  }

  typedef DATE {
    type string {
      length "1..9";
    }
  }

  typedef TIME {
    type string {
      length "1..9";
    }
  }

  typedef INT {
    type int64;
  }

  typedef DECIMAL {
    type decimal64 {
      fraction-digits 2;
    }
  }

  typedef pec-code {
    type string {
      length "8..16";
    }
  }

  typedef site {
    type uint16 {
      range "0..65535";
    }
  }

  typedef frequency {
    type decimal64 {
      fraction-digits 3;
    }
    units "GHz";
  }

  typedef power {
    type decimal64 {
      fraction-digits 2;
    }
    units "dBm";
  }

  typedef power-dBm-1-precision {
    type decimal64 {
      fraction-digits 1;
    }
    units "dBm";
  }

  typedef power-mW-3-precision {
    type decimal64 {
      fraction-digits 3;
    }
    units "mW";
  }

  typedef gain-loss {
    type decimal64 {
      fraction-digits 2;
    }
    units "dB";
    description
      "Positive for gain, negative for loss";
  }

  typedef gain {
    type decimal64 {
      fraction-digits 2;
    }
    units "dB";
    description
      "Positive for gain";
  }

  typedef gain-dB-1-precision {
    type decimal64 {
      fraction-digits 1;
    }
    units "dB";
    description
      "Positive for gain";
  }

  typedef loss {
    type decimal64 {
      fraction-digits 2;
    }
    units "dB";
    description
      "Positive for loss";
  }

  typedef loss-dB-1-precision {
    type decimal64 {
      fraction-digits 1;
    }
    units "dB";
    description
      "Positive for loss";
  }

  typedef object-name {
    type string {
      length "1..32";
    }
  }

  typedef psd {
    type decimal64 {
      fraction-digits 2;
    }
    units "dBm/12.5GHz";
    description
      "Power Spectral Density";
  }

  typedef sha512 {
    type string {
      length "0..128";
    }
    description
      "To store a sha512 value encoded with base64 (86 char + room for salt";
  }

  typedef product {
    type enumeration {
      enum "6500 Reconfigurable Line System";
    }
    description
      "Product that supports the shelf";
  }

  typedef shelf-type {
    type enumeration {
      enum "6500-R4 8-Slot";
      enum "6500-R2 4-Slot";
      enum "6500-R8-300 8-Slot";
    }
    description
      "Shelf type";
  }

  typedef restart-type {
    type enumeration {
      enum "warm" {
        value 1;
      }
      enum "cold" {
        value 2;
      }
    }
    description
      "Restart type";
  }

  typedef band-occupancy {
    type bits {
      bit BAND-C {
        position 0;
      }
      bit BAND-L {
        position 1;
      }
      bit OSC {
        position 2;
      }
      bit TELEMETRY {
        position 3;
      }
      bit TOTAL {
        position 4;
      }
    }
    description
      "Band Type";
  }

  typedef fiber-type {
    type enumeration {
      enum "unknown";
      enum "other";
      enum "AllWave";
      enum "DSF" {
        description
          "Dispersion Shifted single mode Fiber";
      }
      enum "FreeLight";
      enum "LEAF" {
        description
          "Large Effective Area Fiber";
      }
      enum "Enhanced LEAF";
      enum "Lambda Shifted";
      enum "NDSF" {
        description
          "Non-Dispersion Shifted Fiber";
      }
      enum "NDSF LWP" {
        description
          "NDSF Low Water Peak";
      }
      enum "PSC" {
        description
          "Pure Silica Fiber";
      }
      enum "TeraLight";
      enum "TeraWave ULL" {
        description
          "TeraWave Ultra Low Loss";
      }
      enum "TrueWave Classic";
      enum "TrueWave Plus";
      enum "TrueWave Reach";
      enum "TrueWave RS" {
        description
          "TrueWave Reduced Slope";
      }
      enum "EX2000";
      enum "EX3000";
      enum "MetroCor";
      enum "patchCord";
      enum "SMF28ULL";
    }
    description
      "Fiber type";
  }

  typedef orl-state {
    type enumeration {
      enum "valid" {
        value 1;
        description
          "ORL in valid state.";
      }
      enum "outputOORL" {
        value 2;
        description
          "Output is dark, OOR is low.";
      }
      enum "reflectOORL" {
        value 3;
        description
          "Reflection is dark, OOR is low.";
      }
      enum "reflectOORH" {
        value 4;
        description
          "Reflection is dark, OOR is high.";
      }
      enum "hssf" {
        value 5;
        description
          "Possible hardware subsystem failure.";
      }
      enum "shutoff" {
        value 6;
        description
          "Shutoff mode is enabled.";
      }
      enum "unknown" {
        value 7;
        description
          "If the state from the device is not known.";
      }
      enum "notApplicable" {
        value 8;
        description
          "ORL state not applicable (ie. Pre-Amp on RLA).";
      }
    }
    description
      "The ORL State";
  }

  grouping admin-state {
    leaf admin-state {
      type enumeration {
        enum "Enabled" {
          value 1;
          description
            "Service is Enabled.";
        }
        enum "Disabled" {
          value 2;
          description
            "Service is Disabled.";
        }
        enum "Unassigned" {
          value 3;
          description
            "Service is Unassigned.";
        }
      }
      description
        "Identify the administrative state";
    }
  }

  grouping slot-inventory-common {
    leaf pec {
      type pec-code;
      description
        "Actual PEC Code";
    }

    leaf hardware-release {
      type string {
        length "1..32";
      }
      description
        "Release Level";
    }

    leaf common-language-equipment-identifier {
      type string {
        length "1..32";
      }
      description
        "Common language equipment identifier";
    }

    leaf serial-number {
      type string {
        length "1..32";
      }
      description
        "Serial Number";
    }

    leaf manufacturing-date {
      type string;
      description
        "Date of Manufacture, in the format: year-week of year (YYYY-MM-DD).";
    }

    leaf age {
      type string;
      description
        "Age, cumulative in-service time elapsed since manufacture, in the format: years-days-hours-minutes (YY-DDD-HH-MM).";
    }

    leaf on-since {
      type string;
      description
        "On since, cumulative time since the unit was last inserted, in the format: years-days-hours-minutes (YY-DDD-HH-MM).";
    }

    leaf current-temperature {
      type string;
      description
        "Current card temperature";
    }

    leaf average-temperature {
      type string;
      description
        "Average card temperature";
    }
  }
}
