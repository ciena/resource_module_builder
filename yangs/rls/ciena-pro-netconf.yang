module ciena-pro-netconf {
  namespace "urn:ciena:params:xml:ns:yang:ciena-pro-netconf";
  prefix ciena-pro-netconf;

  import ciena-common-version {
    prefix version;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's Netconf model";

  revision 2020-09-11 {
    version:version "version" {
      version:string "1.2.0";
    }
    description
      "Restructured netconf container and added
       enable-disable enum for holding state";
  }
  revision 2020-08-18 {
    version:version "version" {
      version:string "1.1.0";
    }
    description
      "Added server-enable and server-validation leaf";
  }
  revision 2019-08-26 {
    version:version "version" {
      version:string "1.0.0";
    }
    description
      "Initial revision.";
  }

  typedef status-type {
    type enumeration {
      enum "disable" {
        description
          "Disable state.";
      }
      enum "enable" {
        description
          "Enable state.";
      }
    }
    description
      "Status type - enable or disable";
  }

  container netconf {
    container server {
      leaf state {
        type status-type;
        mandatory true;
        description
          "Flag to enable or disable Netconf interface";
      }

      leaf validation {
        type status-type;
        description
          "Flag to enable or disable northbound validation on the server";
      }
    }
  }

  rpc delete-subscription {
    description
      "This RPC allows a subscriber to delete a subscription that
       was previously created from by that same subscriber using the
       'create-subscription' RPC.

       If an error occurs, the server replies with an 'rpc-error'.";
  }
}
