module ciena-pro-coherent-device-types {
  namespace "urn:ciena:ns:yang:coherent-device-types";
  prefix coherent-device-types;

  import ciena-common-version {
    prefix version;
  }

  organization
    "Ciena Corporation";
  contact
    "Web URL: http://www.ciena.com/
     Postal:  7035 Ridge Road
              Hanover, Maryland 21076
              U.S.A.
     Phone:   +1 800-921-1144
     Fax:     +1 410-694-5750";
  description
    "Device definitions for coherent devices.";

  revision 2024-01-01 {
    description
      "Initial version.";
    version:version "version" {
      version:string "1.0.0";
    }
    reference
      "1.0.0";
  }

  typedef device-id-type {
    type string {
      length "1..32";
    }
    description
      "Type to represent a unique and product specific identification string for
       a coherent device. Typically this will be a product specific identifier
       that captures slot and port information.";
  }

  typedef media-interface-group-id-type {
    type string {
      length "1..32";
    }
    description
      "Type to represent a unique and product specific identification string for
       a media interface group. Typically this will be a product specific identifier
       that captures slot and port information.";
  }

  typedef admin-state-enum {
    type enumeration {
      enum enabled {
        description
          "Enabled represents that the entity is configured to be fully operational.";
      }
      enum disabled {
        description
          "Disabled represents that the entity is configured to be out-of-service.";
      }
    }
    description
      "Type for the administrative state of an entity.";
  }

  typedef device-class-type {
    type enumeration {
      enum coherent-pluggable-400g {
        description
          "Coherent pluggable optics device supporting up to 400G modulations and service,
           including Ciena WaveLogic 5n devices and Coherent-CMIS compliant QSFP-DD.";
      }
      enum wavelogic-6e {
        description
          "WaveLogic 6 Extreme as a network interface card.";
      }
    }
    description
      "A YANG type to identify the type of coherent-device being managed.";
  }

  typedef device-type-actual-type {
    type enumeration {
      enum wavelogic-5n {
        description
          "The device is a Ciena WaveLogic 5 Nano pluggable optics module.";
      }
      enum coherent-pluggable-400g-uncertified {
        description
          "The device is a Coherent-CMIS compliant pluggable optics module from
           a vendor other than Ciena.";
      }
      enum wavelogic-6e {
        description
          "The device is a Ciena WaveLogic 6 Extreme network interface card.";
      }
    }
    description
      "A YANG type to identify the actual type of coherent-device present in inventory.";
  }

  typedef coherent-device-media-modes-enum {
    type enumeration {
      enum 60-400-E-ZR {
        description
          "OIF 400ZR compliant 400G transmission-mode with CFEC for use with Ciena
           WaveLogic pluggable optics modules supporting 100GE and 400GE services.";
      }
      enum 60-400-100GE-ZR {
        description
          "OIF 400ZR compliant 400G transmission-mode with CFEC for use with non-Ciena
           branded C-CMIS compliant coherent QSFP-DD modules supporting up to four 100GE
           services. When used with Ciena WaveLogic pluggable optics modules, operation
           is limited to standard defined capabilities and behaviour.";
      }
      enum 60-400-400GE-ZR {
        description
          "OIF 400ZR compliant 400G transmission-mode with CFEC for use with non-Ciena
           branded C-CMIS compliant coherent QSFP-DD modules supporting a 400GE service.
           When used with Ciena WaveLogic pluggable optics modules, operation is limited
           to standard defined capabilities and behaviour.";
      }
      enum 60-400-E-ZR+ {
        description
          "OpenZR+ MSA compliant 400G transmission-mode with OFEC for use with Ciena
           WaveLogic pluggable optics modules supporting 100GE and 400GE services.";
      }
      enum 60-400-100GE-ZR+ {
        description
          "OpenZR+ MSA compliant 400G transmission-mode with OFEC for use with non-Ciena
           branded C-CMIS compliant coherent QSFP-DD modules supporting up to four 100GE
           services. When used with Ciena WaveLogic pluggable optics modules, operation
           is limited to standard defined capabilities and behaviour.";
      }
      enum 60-400-400GE-ZR+ {
        description
          "OpenZR+ MSA compliant 400G transmission-mode with OFEC for use with non-Ciena
           branded C-CMIS compliant coherent QSFP-DD modules supporting a 400GE service.
           When used with Ciena WaveLogic pluggable optics modules, operation is limited
           to standard defined capabilities and behaviour.";
      }
      enum 65-400-E {
        description
          "65 Gbaud, 400 Gbps, proprietary Ethernet-transcoded transmission-mode";
      }
      enum 65-300-E {
        description
          "65 Gbaud, 300 Gbps, proprietary Ethernet-transcoded transmission-mode";
      }
      enum 60-200-E {
        description
          "60 Gbaud, 200 Gbps, proprietary Ethernet-transcoded transmission-mode";
      }
      enum 70-400-E {
        description
          "70 Gbaud, 400 Gbps, proprietary Ethernet-transcoded transmission-mode";
      }
      enum 31.5-200-O {
        description
          "31.5 Gbaud, 200 Gbps, ITU-T/OpenROADM/CableLabs OTN-mapped with OFEC transmission-mode";
      }
      enum 31.5-100-O {
        description
          "31.5 Gbaud, 100 Gbps, ITU-T/OpenROADM/CableLabs OTN-mapped with OFEC transmission-mode";
      }
      enum 63-400-O {
        description
          "63 Gbaud, 400 Gbps, ITU-T/OpenROADM/CableLabs OTN-mapped with OFEC transmission-mode";
      }
      enum 63-200-O {
        description
          "63 Gbaud, 200 Gbps, ITU-T/OpenROADM/CableLabs OTN-mapped with OFEC transmission-mode";
      }
      enum 70-400-O {
        description
          "70 Gbaud, 400 Gbps, proprietary OTN-mapped transmission-mode";
      }
      enum 70-300-O {
        description
          "";
      }
      enum 35-200-O {
        description
          "35 Gbaud, 200 Gbps, proprietary OTN-mapped transmission-mode";
      }
      enum 58-200-O {
        description
          "58 Gbaud, 200 Gbps, proprietary OTN-mapped transmission-mode";
      }
      enum none {
        description
          "The media-side transmission-mode has not been assigned. This value may not be seen
           as a product may omit the attribute when it is not configured.";
      }
      enum unknown {
        description
          "The media-side transmission-mode is not known.";
      }
    }
    description
      "The defined set of coherent device media-interface transmission-modes supported.
       Transmission-modes are defined for Ciena WaveLogic specific capabilities as well as
       for standard-compliant mode of operation when using CMIS and C-CMIS compliant coherent
       QSFP-DD pluggable optical modules. Transmission-modes are named by a combination of
       baud, bit-rate, and type of media signal encapsulation used (e.g., 400ZR vs. OTN) and
       defines whether the mode is limited to standard-compliant behaviour. Transmission-mode
       support is dependent on the variant of device deployed.";
  }

  typedef coherent-device-tm-baud-enum {
    type enumeration {
      enum 31.5_GBAUD {
        description
          "31.5 GBAUD";
      }
      enum 35_GBAUD {
        description
          "35 GBAUD";
      }
      enum 58_GBAUD {
        description
          "58 GBAUD";
      }
      enum 60_GBAUD {
        description
          "60 GBAUD";
      }
      enum 63_GBAUD {
        description
          "63 GBAUD";
      }
      enum 65_GBAUD {
        description
          "65 GBAUD";
      }
      enum 70_GBAUD {
        description
          "70 GBAUD";
      }
    }
    description
      "Type to represent supported baud of a WaveLogic device transmission-mode modulation format.";
  }

  typedef coherent-device-tm-bitrate-enum {
    type enumeration {
      enum 100G {
        description
          "100G";
      }
      enum 200G {
        description
          "200G";
      }
      enum 300G {
        description
          "300G";
      }
      enum 400G {
        description
          "400G";
      }
      enum 500G {
        description
          "500G";
      }
      enum 600G {
        description
          "600G";
      }
      enum 700G {
        description
          "700G";
      }
      enum 800G {
        description
          "800G";
      }
    }
    description
      "Type to represent supported bit-rate of a WaveLogic device transmission-mode modulation format.";
  }

  typedef coherent-device-tm-mapping-type-enum {
    type enumeration {
      enum Ethernet {
        description
          "The transmission-mode uses a proprietary Flex-E like mapping.";
      }
      enum OTN {
        description
          "The transmission-mode uses a standard G.709 mapping.";
      }
    }
    description
      "Type to represent supported logical signal format of a WaveLogic device transmission-mode modulation format.";
  }

  typedef coherent-device-tm-operating-mode-enum {
    type enumeration {
      enum wavelogic {
        description
          "The operating-mode for Wavelogic-native transmission mode.";
      }
      enum coherent-cmis {
        description
          "The operating-mode for Coherent CMIS transmission mode.";
      }
    }
    description
      "";
  }

  typedef coherent-device-link-opt-mode-enum {
    type enumeration {
      enum standard {
        description
          "Standard Mode - Default setting which provides best SNR performance.";
      }
      enum snr-tolerant {
        description
          "SNR Tolerant Mode - Recommended for applications that want to achieve
           maximum SNR tolerance while still providing reasonable polarization tracking speed
           and PDL tolerance.";
      }
      enum fast-tracking {
        description
          "Fast Tracking Mode - Recommended for applications that want to maximize SOP tracking.";
      }
      enum narrow-bandwidth {
        description
          "Spectral Efficiency Mode - Recommended for applications that want to maximize
           spectral efficiency by minimizing spectral signal width.";
      }
      enum non-linear-channel {
        description
          "Non-Linear Channel Mode - Recommended for applications that want to achieve
           maximum SNR tolerance on a non-linear fiber link.";
      }
      enum spectral-efficiency {
        description
          "Spectral Efficiency Mode - Recommended for applications that want to maximize
           spectral efficiency by minimizing spectral signal width.";
      }
      enum foreign {
        description
          "Foreign Line Mode - Recommended for applications that require the transmitted signal
           to be be recognized/controlled by a non-Ciena photonics system.";
      }
      enum none {
        description
          "The link optimization mode is not configured.";
      }
      enum unknown {
        description
          "The link optimization mode is not known.";
      }
    }
    description
      "Ciena WaveLogic device link optimization modes";
  }

  typedef coherent-device-tuning-mode-enum {
    type enumeration {
      enum normal {
        description
          "Normal, performance-optimized, transmitter tuning mode.";
      }
      enum accelerated {
        description
          "Accelerated transmitter tuning mode.";
      }
      enum fast {
        description
          "Fast transmitter tuning mode.";
      }
    }
    description
      "Ciena WaveLogic device tuning modes.";
  }

  typedef coherent-device-laser-centering-mode-enum {
    type enumeration {
      enum disabled {
        description
          "WaveLogic laser centering is disabled.
           This is the default.";
      }
      enum enabled {
        description
          "WaveLogic laser centering is enabled.";
      }
      enum holdover {
        description
          "WaveLogic laser centering is set to holdover state.";
      }
    }
    description
      "A type for WaveLogic laser centering mode capability.";
  }

  typedef device-modem-class-enum {
    type enumeration {
      enum terrestrial {
        description
          "The modem on the device is terrestrial class. This applies to WaveLogic Nano
           and some variants of WaveLogic Extreme devices. Non-Ciena pluggable coherent
           optics may also be considered terrestrial given current standard reach limits.";
      }
      enum submarine {
        description
          "The modem is submarine class. This applies to some variants of WaveLogic Extreme.";
      }
      enum unknown {
        description
          "The class of modem is unknown. This value be used when the system cannot determine
           the modem class or for 3rd party coherent optics.";
      }
    }
    description
      "The class of modem associated with this coherent device.";
  }

  typedef coherent-device-loopback-mode-enum {
    type enumeration {
      enum disabled {
        description
          "Loopback is not configured and not active.";
      }
      enum rx-to-tx {
        description
          "The received signal is being looped back to the transmitter.
           Also known as a facility loopback.";
      }
      enum tx-to-rx {
        description
          "The signal to be transmitted is being looped back to the internal source.
           Also known as a terminal loopback.";
      }
    }
    description
      "Ciena WaveLogic device loopback types.";
  }

  typedef coherent-device-capacity {
    type uint8;
    units "100G";
    description
      "Capacity as expressed in increments of 100 Gigabits per second.";
  }

  identity operational-state-identity {
    description
      "An identity to represent entity operational state.";
  }

  identity oper-state-up {
    base operational-state-identity;
    description
      "The entity is operating normally.";
  }

  identity oper-state-down {
    base operational-state-identity;
    description
      "The entity is administratively disabled. This is an abnormal state.";
  }

  identity oper-state-fault {
    base operational-state-identity;
    description
      "The entity is administratively enabled and has 1 or more alarmable conditions associated with it.
       This is an abnormal state.";
  }

  identity oper-state-lower-layer-down {
    base operational-state-identity;
    description
      "The entity is administratively enabled and its supporting entity (parent) is in the faulted state.
       This is an abnormal state.";
  }

  identity oper-state-tx-provisioning-required {
    base operational-state-identity;
    description
      "The OTSI requires provisioning for Tx frequency or Tx power.";
  }

  identity oper-state-tuning-in-progress {
    base operational-state-identity;
    description
      "The OTSI is in the process of tuning to the provisioned tx-frequency.";
  }

  identity oper-state-device-unknown {
    base operational-state-identity;
    description
      "The device present is unrecognized by this version of software.";
  }

  identity oper-state-device-shutdown {
    base operational-state-identity;
    description
      "The device present powered down or in low-power-mode due to power-state configuration or another condition.";
  }

  identity oper-state-device-unequipped {
    base operational-state-identity;
    description
      "The device has provisioning but is not present in inventory.";
  }

  identity oper-state-device-not-provisioned {
    base operational-state-identity;
    description
      "The device is present in inventory but is currently unprovisioned and therefore is not operational.";
  }

  identity oper-state-device-uncertified {
    base operational-state-identity;
    description
      "The device present in invenvory is a not a Ciena-branded device.";
  }

  identity oper-state-device-media-interface-loopback-rx-to-tx {
    base operational-state-identity;
    description
      "The device has an Rx-to-Tx (facility) loopback provisioned on the media interface.";
  }

  identity oper-state-device-media-interface-loopback-tx-to-rx {
    base operational-state-identity;
    description
      "The device has an Tx-to-Rx (terminal) loopback provisioned on the media interface.";
  }

  identity oper-state-device-host-interface-loopback-rx-to-tx {
    base operational-state-identity;
    description
      "The device has a Rx-to-Tx (facility) loopback provisioned for a service carried on this device.";
  }

  identity oper-state-device-host-interface-loopback-tx-to-rx {
    base operational-state-identity;
    description
      "The device has a Tx-To-Rx (terminal) loopback provisioned for a service carried on this device.";
  }

  grouping coherent-device-config-media-interface-group {
    leaf mode {
      type coherent-device-media-modes-enum;
      mandatory true;
      description
        "";
    }
    leaf loopback {
      type coherent-device-loopback-mode-enum;
      default "disabled";
      description
        "On the device media-interface an rx-to-tx loopback is toward the media-interface (fiber)
         and tx-to-rx loopback is toward the system. ";
    }
    description
      "";
  }

  grouping coherent-device-state-media-interface-group {
    leaf mode {
      type coherent-device-media-modes-enum;
      description
        "";
    }
    leaf loopback {
      type coherent-device-loopback-mode-enum;
      default "disabled";
      description
        "On the device media-interface an rx-to-tx loopback is toward the media-interface (fiber)
         and tx-to-rx loopback is toward the system. ";
    }
    description
      "";
  }

  typedef media-channel-type-enum {
    type enumeration {
      enum ZR {
        description
          "The media channel is a ZR layer.";
      }
      enum FlexO {
        description
          "The media channel is a FlexO layer.";
      }
    }
    description
      "The type of the media channel.";
  }

  typedef media-channel-rate-enum {
    type enumeration {
      enum 400G {
        description
          "400G";
      }
    }
    description
      "The rate of the media channel.";
  }
}
