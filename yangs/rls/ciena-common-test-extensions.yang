module ciena-common-test-extensions {
  yang-version 1.1;
  namespace "urn:ciena:params:xml:ns:yang:ciena-common-test-extensions";
  prefix text;

  import ciena-common-yang {
    prefix yang;
  }

  organization
    "Ciena Corporation";
  contact
    "Web URL: http://www.ciena.com";
  description
    "A module to test extensions";

  revision 2021-02-05 {
    description
      "Initial revision";
  }

  extension min-value {
    argument value;
  }

  extension max-value {
    argument value;
  }

  extension ui-name {
    argument value;
  }

  extension s1 {
    argument value;
  }

  extension s2 {
    argument value;
  }

  extension s3 {
    argument value;
  }

  extension s4 {
    argument value;
  }

  extension s5 {
    argument value;
  }

  extension s6 {
    argument value;
  }

  yang:yang-data "test-extension-structure2" {
    container ext-struct {
      leaf ui-name {
        type string;
      }
      leaf min-value {
        type uint8;
      }
      leaf max-value {
        type uint8;
      }
    }
  }
  yang:yang-data "test-extension-structure" {
    container ext-struct {
      leaf ui-name {
        type string;
      }
      leaf min-value {
        type uint8;
      }
      leaf max-value {
        type uint8;
      }
    }
  }
  yang:yang-data "test-large-extension-structure" {
    container ext-struct {
      leaf ui-name {
        type string;
      }
      leaf min-value {
        type uint8;
      }
      leaf max-value {
        type uint8;
      }
      leaf s1 {
        type string;
      }
      leaf s2 {
        type string;
      }
      leaf s3 {
        type string;
      }
      leaf s4 {
        type string;
      }
      leaf s5 {
        type string;
      }
      leaf s6 {
        type string;
      }
    }
  }

  container container-with-metadata {
    description
      "Structure for testing that metadata extensions work.";
    yang:metadata-extension "test-extension-structure";
    leaf X {
      description
        "The simplest leaf type.";
      type string;
      yang:yang-data "metadata" {
        text:min-value "1";
        text:max-value "2";
        text:ui-name "a";
      }
    }
    leaf y {
      type uint8;
      yang:yang-data "metadata" {
        text:min-value "2";
        text:max-value "3";
        text:ui-name "c";
      }
    }
    list z {
      config false;
      leaf zz {
        type uint32;
      }
      yang:yang-data "metadata" {
        text:ui-name "xx";
        text:min-value "123";
      }
    }
    container container-a {
      yang:metadata-extension "test-extension-structure2";
      leaf xxx {
        type string;
        yang:yang-data "metadata" {
          text:ui-name "dsd";
          text:min-value "2";
        }
      }
      list a-z {
        config false;
        leaf zzz {
          type uint32;
        }
        yang:yang-data "metadata" {
          text:ui-name "xxdsd";
          text:max-value "12";
        }
      }
    }
    container container-b {
      yang:metadata-extension "test-large-extension-structure";
      description
        "Test extensions with more than 7 elements in their checklist";
      leaf xyz {
        type string;
        yang:yang-data "metadata" {
          text:ui-name "string name";
          text:min-value "1";
          text:s1 "string 1";
          text:s4 "string 4";
          text:s6 "string 6";
        }
      }
    }
  }
  list list-with-metadata {
    description
      "Structure for testing that metadata extensions work.";
    yang:metadata-extension "test-extension-structure";
    key "X";
    leaf X {
      description
        "The simplest leaf type.";
      type string;
      yang:yang-data "metadata" {
        text:min-value "1";
        text:max-value "2";
        text:ui-name "a";
      }
    }
    leaf y {
      type uint8;
      yang:yang-data "metadata" {
        text:min-value "2";
        text:max-value "3";
        text:ui-name "c";
      }
    }
    list z {
      config false;
      leaf zz {
        type uint32;
      }
      yang:yang-data "metadata" {
        text:ui-name "xx";
        text:min-value "123";
      }
    }
    container container-a {
      yang:metadata-extension "test-extension-structure2";
      leaf xxx {
        type string;
        yang:yang-data "metadata" {
          text:ui-name "dsd";
          text:min-value "2";
        }
      }
      list a-z {
        config false;
        leaf zzz {
          type uint32;
        }
        yang:yang-data "metadata" {
          text:ui-name "xxdsd";
          text:max-value "12";
        }
      }
    }
    container container-b {
      yang:metadata-extension "test-large-extension-structure";
      description
        "Test extensions with more than 7 elements in their checklist";
      leaf xyz {
        type string;
        yang:yang-data "metadata" {
          text:ui-name "string name";
          text:min-value "1";
          text:s1 "string 1";
          text:s4 "string 4";
          text:s6 "string 6";
        }
      }
    }
  }
}
