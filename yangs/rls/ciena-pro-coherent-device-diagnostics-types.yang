module ciena-pro-coherent-device-diagnostics-types {
  namespace "urn:ciena:ns:yang:coherent-device-diagnostics-types";
  prefix coherent-device-diagnostics-types;

  import ciena-common-version {
    prefix version;
  }

  organization
    "Ciena Corporation";
  contact
    "Web URL: http://www.ciena.com/
     Postal:  7035 Ridge Road
              Hanover, Maryland 21076
              U.S.A.
     Phone:   +1 800-921-1144
     Fax:     +1 410-694-5750";
  description
    "Diagnostic data definitions for coherent devices.";

  revision 2024-01-01 {
    description
      "Initial version.";
    version:version "version" {
      version:string "1.0.0";
    }
    reference
      "1.0.0";
  }

  grouping restart-diagnostics-group {
    leaf cold-restart-required {
      type boolean;
      default "false";
      config false;
      description
        "An indication that the WaveLogic device requires a cold restart.
         Normally this would be required when firmware installation requires
         a cold-restart to complete installation.";
    }
    leaf initialization-in-progress {
      type boolean;
      default "false";
      config false;
      description
        "An indication that the WaveLogic device is in the process of initializing.
         The restart may have been user or system initiated. For details of the type
         and cause of the refer to the restart details in the device inventory.";
    }
    description
      "";
  }

  grouping upgrade-diagnostics-group {
    leaf firmware-below-baseline {
      type boolean;
      default "false";
      description
        "An indication that firmware package active on a WaveLogic device is below the baseline
         for this release of product software and requires an upgrade as soon as possibel to ensure
         proper operation. While in this state, the device is remains configurable and monitored on
         a best-effort basis.";
    }
    leaf upgrade-in-progress {
      type boolean;
      default "false";
      description
        "An indication that a firmware package is in the process of being installed on a device
         as a single-step upgrade. This boolean is set to false when the installation
         completes. If the upgrade fails at any stage of the installation, a corresponding failure
         defect is set to true.";
    }
    leaf download-in-progress {
      type boolean;
      default "false";
      description
        "An indication that a firmware package is being downloaded to a device.
         This defect indicates process when a multi-step upgrade is being performed.";
    }
    leaf download-failed {
      type boolean;
      default "false";
      description
        "An indication that a firmware package failed to downloaded to a device and
         now requires a cancel or re-download to occur.";
    }
    leaf activate-in-progress {
      type boolean;
      default "false";
      description
        "An indication that a firmware package is being activated on a device.
         This defect indicates process when a multi-step upgrade is being performed.";
    }
    leaf activate-failed {
      type boolean;
      default "false";
      description
        "An indication that a firmware package failed to acctivate on a device and
         now requires a cancel to proceed.";
    }
    leaf commit-in-progress {
      type boolean;
      default "false";
      description
        "An indication that a firmware package is being committed on a device.
         This defect indicates process when a multi-step upgrade is being performed.";
    }
    leaf commit-failed {
      type boolean;
      default "false";
      description
        "An indication that a firmware package failed to commit on a device and
         now requires a cancel to proceed.";
    }
    leaf abort-in-progress {
      type boolean;
      default "false";
      description
        "An indication that a firmware package installation is being canceled for a device.";
    }
    leaf abort-failed {
      type boolean;
      default "false";
      description
        "An indication that a firmware package installation failed to cancel for a device
         and corrective action is required.";
    }
    description
      "";
  }

  grouping coherent-device-diags-cmis-modulator-bias-group {
    leaf modulator-bias-xi-high-alarm {
      type boolean;
      default "false";
      description
        "";
    }
    leaf modulator-bias-xi-high-warning {
      type boolean;
      default "false";
      description
        "";
    }
    leaf modulator-bias-xq-high-alarm {
      type boolean;
      default "false";
      description
        "";
    }
    leaf modulator-bias-xq-high-warning {
      type boolean;
      default "false";
      description
        "";
    }
    leaf modulator-bias-xi-low-alarm {
      type boolean;
      default "false";
      description
        "";
    }
    leaf modulator-bias-xi-low-warning {
      type boolean;
      default "false";
      description
        "";
    }
    leaf modulator-bias-xq-low-alarm {
      type boolean;
      default "false";
      description
        "";
    }
    leaf modulator-bias-xq-low-warning {
      type boolean;
      default "false";
      description
        "";
    }
    leaf modulator-bias-yi-high-alarm {
      type boolean;
      default "false";
      description
        "";
    }
    leaf modulator-bias-yi-high-warning {
      type boolean;
      default "false";
      description
        "";
    }
    leaf modulator-bias-yq-high-alarm {
      type boolean;
      default "false";
      description
        "";
    }
    leaf modulator-bias-yq-high-warning {
      type boolean;
      default "false";
      description
        "";
    }
    leaf modulator-bias-yi-low-alarm {
      type boolean;
      default "false";
      description
        "";
    }
    leaf modulator-bias-yi-low-warning {
      type boolean;
      default "false";
      description
        "";
    }
    leaf modulator-bias-yq-low-alarm {
      type boolean;
      default "false";
      description
        "";
    }
    leaf modulator-bias-yq-low-warning {
      type boolean;
      default "false";
      description
        "";
    }
    leaf modulator-bias-x-phase-high-alarm {
      type boolean;
      default "false";
      description
        "";
    }
    leaf modulator-bias-x-phase-high-warning {
      type boolean;
      default "false";
      description
        "";
    }
    leaf modulator-bias-x-phase-low-alarm {
      type boolean;
      default "false";
      description
        "";
    }
    leaf modulator-bias-x-phase-low-warning {
      type boolean;
      default "false";
      description
        "";
    }
    leaf modulator-bias-y-phase-high-alarm {
      type boolean;
      default "false";
      description
        "";
    }
    leaf modulator-bias-y-phase-high-warning {
      type boolean;
      default "false";
      description
        "";
    }
    leaf modulator-bias-y-phase-low-alarm {
      type boolean;
      default "false";
      description
        "";
    }
    leaf modulator-bias-y-phase-low-warning {
      type boolean;
      default "false";
      description
        "";
    }
    description
      "";
  }

  grouping device-diagnostics-group {
    leaf missing {
      type boolean;
      default "false";
      description
        "The device is provisioned but is absent from inventory.";
    }
    leaf not-provisioned {
      type boolean;
      default "false";
      description
        "The device is present in inventory but is not currently provisioned.
         In this state, the device is held in low-power-mode.";
    }
    leaf not-supported {
      type boolean;
      default "false";
      description
        "The device present in inventory as not supported in this location.";
    }
    leaf unknown {
      type boolean;
      default "false";
      description
        "The device present in inventory is unrecognized.";
    }
    leaf failed {
      type boolean;
      default "false";
      description
        "The device is failed due to detection of a hardware fault.";
    }
    leaf uncertified {
      type boolean;
      default "false";
      description
        "The device manufacturer is not Ciena. This an indication that the device
         may only support a subset of available functionality, such standard modes of operation.";
    }
    leaf over-temp-warning {
      type boolean;
      default "false";
      description
        "The device is over-temperature.";
    }
    leaf over-temp-critical {
      type boolean;
      default "false";
      description
        "The device is over-temperature.";
    }
    leaf under-temp-warning {
      type boolean;
      default "false";
      description
        "The device is under-temperature.";
    }
    leaf under-temp-critical {
      type boolean;
      default "false";
      description
        "The device is under-temperature.";
    }
    leaf comms-suspect {
      type boolean;
      default "false";
      description
        "The communications to device are failed or unreliable.";
    }
    leaf power-disabled {
      type boolean;
      default "false";
      description
        "The device is provisioned, present in inventory, not mismatched and
         is administratively powered-off or in low-power-mode by the power-state
         setting.";
    }
    leaf prov-mismatch {
      type boolean;
      default "false";
      description
        "The device-level provisioning for the device is not how the device is currently configured.
         This covers power-state and interface media-config and host-config.";
    }
    leaf far-end-modem-class-mismatch {
      type boolean;
      default "false";
      description
        "An indication that the configured modem-class value is different between
         this device and the far-end device.

         This defect only applies to WaveLogic Extreme devices.";
    }
    leaf voltage-high-alarm {
      type boolean;
      default "false";
      description
        "";
    }
    leaf voltage-high-warning {
      type boolean;
      default "false";
      description
        "";
    }
    leaf voltage-low-alarm {
      type boolean;
      default "false";
      description
        "";
    }
    leaf voltage-low-warning {
      type boolean;
      default "false";
      description
        "";
    }
    leaf device-class-mismatch {
      type boolean;
      default "false";
      description
        "The device class provisioning for the device does not match the device currently present.";
    }
    list lane {
      key "lane-index";
      config false;
      leaf lane-index {
        type uint8 {
          range "1..max";
        }
        description
          "";
      }
      leaf laser-bias-high-alarm {
        type boolean;
        default "false";
        description
          "";
      }
      leaf laser-bias-high-warning {
        type boolean;
        default "false";
        description
          "";
      }
      leaf laser-bias-low-alarm {
        type boolean;
        default "false";
        description
          "";
      }
      leaf laser-bias-low-warning {
        type boolean;
        default "false";
        description
          "";
      }
      leaf laser-temp-high-alarm {
        type boolean;
        default "false";
        description
          "";
      }
      leaf laser-temp-high-warning {
        type boolean;
        default "false";
        description
          "";
      }
      leaf laser-temp-low-alarm {
        type boolean;
        default "false";
        description
          "";
      }
      leaf laser-temp-low-warning {
        type boolean;
        default "false";
        description
          "";
      }
      uses coherent-device-diags-cmis-modulator-bias-group;
      description
        "Device-level lane diagnostic points.";
    }
    description
      "";
  }

  grouping coherent-device-diagnostics-group {
    container diagnostics {
      config false;
      container device {
        uses device-diagnostics-group;
        description
          "";
      }
      container upgrade {
        uses upgrade-diagnostics-group;
        description
          "";
      }
      container restart {
        uses restart-diagnostics-group;
        description
          "";
      }
      description
        "WaveLogic device level diagnostic points for alarm conditions
         related to the hardware, inventory status, top-level device
         provisioning, upgrades, and restarts.";
    }
    description
      "";
  }
}
