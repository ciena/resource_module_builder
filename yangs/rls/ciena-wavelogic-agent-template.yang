module ciena-wavelogic-agent-template {
  namespace "urn:ciena:params:xml:ns:yang:ciena-wavelogic-agent-template";
  prefix wavelogic-agent-template;

  import ciena-common-version {
    prefix ciena-common-version;
  }

  organization
    "Ciena Corporation";
  contact
    "Web URL: http://www.ciena.com";
  description
    "Wavelogic Agent template module";

  revision 2023-01-01 {
    description
      "Initial revision";
    ciena-common-version:string "1.0.0";
    reference
      "1.0.0";
  }

  list template {
    key "name";
    leaf name {
      type string;
    }
    list token {
      key "name";
      leaf name {
        type string;
      }
      leaf description {
        type string;
      }
    }
    anyxml data;
  }
}
