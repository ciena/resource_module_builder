module ciena-common-test-auth {
  yang-version 1.1;
  namespace "urn:ciena:params:xml:ns:yang:ciena-common-test-auth";
  prefix test-auth;

  organization
    "Ciena Corporation";
  contact
    "Web URL: http://www.ciena.com/
     Postal:  7035 Ridge Road
             Hanover, Maryland 21076
             U.S.A.
     Phone:   +1 800-921-1144
     Fax:     +1 410-694-5750";
  description
    "Test module - redefinitions of aaa types from the security-mgr service.";

  revision 2020-04-16 {
    description
      "Initial revision";
  }

  container authorization-level-1 {
    leaf data {
      type string;
    }
  }
  container authorization-level-2 {
    leaf data {
      type string;
    }
  }
  container authorization-level-3 {
    leaf data {
      type string;
    }
  }
  container authorization-level-4 {
    leaf data {
      type string;
    }
  }
  container hierarchical-authorization-level-1 {
    leaf data {
      type string;
    }
    container hierarchical-authorization-level-2 {
      leaf data {
        type string;
      }
      container hierarchical-authorization-level-3 {
        leaf data {
          type string;
        }
        container hierarchical-authorization-level-4 {
          leaf data {
            type string;
          }
        }
      }
    }
  }

  rpc rpc-authorization-level-1 {
    input {
      leaf input-data {
        type string;
      }
    }
    output {
      leaf output-data {
        type string;
      }
    }
  }

  rpc rpc-authorization-level-2 {
    input {
      leaf input-data {
        type string;
      }
    }
    output {
      leaf output-data {
        type string;
      }
    }
  }

  rpc rpc-authorization-level-3 {
    input {
      leaf input-data {
        type string;
      }
    }
    output {
      leaf output-data {
        type string;
      }
    }
  }

  rpc rpc-authorization-level-4 {
    input {
      leaf input-data {
        type string;
      }
    }
    output {
      leaf output-data {
        type string;
      }
    }
  }

  notification notification-authorization-level-1 {
    leaf data {
      type string;
    }
  }

  notification notification-authorization-level-2 {
    leaf data {
      type string;
    }
  }

  notification notification-authorization-level-3 {
    leaf data {
      type string;
    }
  }

  notification notification-authorization-level-4 {
    leaf data {
      type string;
    }
  }
}
