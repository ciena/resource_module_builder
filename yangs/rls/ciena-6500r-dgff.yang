module ciena-6500r-dgff {
  yang-version 1.1;
  namespace "urn:ciena:params:xml:ns:yang:ciena-6500r-dgff";
  prefix dgff;

  import ciena-6500r-amps {
    prefix ciena-6500r-amps;
  }

  import ciena-6500r-wss {
    prefix ciena-6500r-wss;
  }

  import ciena-common-yang {
    prefix yang;
  }

  import ciena-6500r-types {
    prefix types;
  }

  import ciena-common-version {
    prefix version;
  }

  organization
    "Ciena Corporation";
  contact
    "Web URL: http://www.ciena.com/
     Postal:  7035 Ridge Road
             Hanover, Maryland 21076
             U.S.A.
     Phone:   +1 800-921-1144
     Fax:     +1 410-694-5750";
  description
    "This module describes Ciena's 6500r platform dgff model";

  revision 2020-06-30 {
    version:version "version" {
      version:string "2.0.1";
    }
    description
      "Fix version formating";
  }
  revision 2019-10-29 {
    version:version "version" {
      version:string "2.0.0";
    }
    description
      "RLS Release 2.0";
  }

  grouping ciena-6500r-dgff-mount {
    list dgff {
      key "name";
      leaf name {
        type types:object-name;
        description
          "DGFF facility name";
      }

      leaf parent-link {
        type instance-identifier;
        description
          "parent-link identifier";
      }

      container fac {
        yang:mount-start "ciena-6500r-amps";
        yang:mount-end "ciena-6500r-amps";
        yang:mount-start "ciena-6500r-wss";
        yang:mount-end "ciena-6500r-wss";
        uses ciena-6500r-amps:ciena-6500r-amps-mount-actions;

        uses ciena-6500r-amps:ciena-6500r-amps-mount;

        uses ciena-6500r-wss:ciena-6500r-wss-mount-actions;

        uses ciena-6500r-wss:ciena-6500r-wss-mount;
      }
    }
  }

  grouping ciena-6500r-dgff-mount-actions;

  uses ciena-6500r-dgff-mount;
}
