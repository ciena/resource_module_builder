module ciena-6500r-ramans {
  yang-version 1.1;
  namespace "urn:ciena:params:xml:ns:yang:ciena-6500r-ramans";
  prefix ramans;

  import ciena-6500r-types {
    prefix types;
  }

  import ciena-6500r-ports {
    prefix ports;
  }

  import ciena-pro-fiber-types {
    prefix fiber-types;
  }

  import ciena-common-version {
    prefix version;
  }

  import ietf-yang-types {
    prefix yang;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's ramans object for the 6500 RLS platform";

  revision 2021-05-20 {
    version:version "version" {
      version:string "1.4.0";
    }
    description
      "Added power-mW leaf.";
  }
  revision 2021-03-31 {
    version:version "version" {
      version:string "1.3.0";
    }
    description
      "Added no-go-overridden-reason and no-go-overridden-date-time.";
  }
  revision 2020-12-10 {
    version:version "version" {
      version:string "1.2.2";
    }
    description
      "Aligned gain-mode enum values with the MIBs.";
  }
  revision 2020-11-13 {
    version:version "version" {
      version:string "1.2.1";
    }
    description
      "Added description to amp-calibration-override";
  }
  revision 2020-11-10 {
    version:version "version" {
      version:string "1.2.0";
    }
    description
      "Added activation-inhibited to diagnostics";
  }
  revision 2020-09-23 {
    version:version "version" {
      version:string "1.1.0";
    }
    description
      "Added back gain-mode";
  }
  revision 2020-08-10 {
    version:version "version" {
      version:string "1.1.0";
    }
    description
      "Added amp-calibration-override";
  }
  revision 2020-06-30 {
    version:version "version" {
      version:string "1.0.8";
    }
    description
      "Fix version formating";
  }
  revision 2020-02-11 {
    version:version "version" {
      version:string "1.0.7";
    }
    description
      "Added password";
  }
  revision 2020-02-05 {
    version:version "version" {
      version:string "1.0.6";
    }
    description
      "Added no-go-overridden";
  }
  revision 2020-01-10 {
    version:version "version" {
      version:string "1.0.5";
    }
    description
      "Remove gain-mode & recommended-gain";
  }
  revision 2019-12-10 {
    version:version "version" {
      version:string "1.0.4";
    }
    description
      "Added LORL alarm at input and output";
  }
  revision 2019-12-05 {
    version:version "version" {
      version:string "1.0.3";
    }
    description
      "Added Initializing to raman pump states";
  }
  revision 2019-11-11 {
    version:version "version" {
      version:string "1.0.2";
    }
    description
      "Modified based on RLS Release 2.0 requirements";
  }
  revision 2019-09-19 {
    version:version "version" {
      version:string "1.0.1";
    }
    description
      "Added Go/No-go support";
  }
  revision 2019-05-10 {
    version:version "version" {
      version:string "1.0.0";
    }
    description
      "Added additional info for alarms";
  }
  revision 2017-10-01 {
    description
      "RLS Release 1.0";
  }

  typedef amp-calibration-override {
    type bits {
      bit target-gain {
        position 0;
      }
    }
    description
      "Values to preserve during calibration.";
  }

  grouping ciena-6500r-ramans-mount {
    list ramans {
      key "name";
      leaf name {
        type types:object-name;
        description
          "RAMAN facility name";
      }

      leaf parent-port {
        type leafref {
          path "/ports:port/ports:name";
        }
        mandatory true;
        description
          "Amp facility parent.";
      }

      leaf max-power-limit {
        type types:power-dBm-1-precision;
        description
          "Maximum allowable power of all pumps together (dBm).";
      }

      container max-power-limit-ranges {
        leaf min {
          type types:power-dBm-1-precision;
        }

        leaf max {
          type types:power-dBm-1-precision;
        }
      }

      leaf output-orl-threshold {
        type types:loss-dB-1-precision;
        description
          "Express Out optical return loss Threshold (dB).";
      }

      container output-orl-threshold-ranges {
        leaf min {
          type types:loss-dB-1-precision;
        }

        leaf max {
          type types:loss-dB-1-precision;
        }
      }

      leaf input-orl-threshold {
        type types:loss-dB-1-precision;
        description
          "Line In optical return loss Threshold (dB).";
      }

      container input-orl-threshold-ranges {
        leaf min {
          type types:loss-dB-1-precision;
        }

        leaf max {
          type types:loss-dB-1-precision;
        }
      }

      leaf target-gain {
        type types:gain-dB-1-precision;
        description
          "Provisioned Gain for Raman pumps (dB).";
      }

      container target-gain-ranges {
        leaf min {
          type types:gain-dB-1-precision;
        }

        leaf max {
          type types:gain-dB-1-precision;
        }
      }

      leaf min-allowed-raman-gain {
        type types:gain-dB-1-precision;
        config false;
        description
          "Min allowed target gain for Raman pumps. This values are either reported by the card
           after a successful Raman gain calibration or from the look-up table when the gain cal has failed (dB).";
      }

      leaf max-allowed-raman-gain {
        type types:gain-dB-1-precision;
        config false;
        description
          "Max allowed target gain for Raman pumps. This values are either reported by the card
           after a successful Raman gain calibration or from the look-up table when the gain cal has failed (dB).";
      }

      leaf gain-mode {
        type enumeration {
          enum "provisioned" {
            value 1;
            description
              "Provisioned Mode";
          }
          enum "recommended" {
            value 2;
            description
              "Recommended Mode";
          }
          enum "bootstrap" {
            value 3;
            description
              "Bootstrap Mode";
          }
        }
        description
          "Provisioned gain mode for RAMAN Pumps.";
      }

      leaf pump-power-state {
        type enumeration {
          enum "initializing" {
            description
              "Default Pump power state, calibration required";
          }
          enum "not-optimized" {
            description
              "Pump power state not optimized";
          }
          enum "optimized" {
            description
              "Pump power state optimized";
          }
          enum "manual" {
            description
              "Pump power state manual optimization";
          }
        }
        description
          "State of Raman pump DOC optimization.";
      }

      leaf forced-shutoff {
        type enumeration {
          enum "Enabled" {
            value 2;
            description
              "Enabled";
          }
          enum "Disabled" {
            value 1;
            description
              "Disabled";
          }
        }
        description
          "Force Shutoff of Raman pumps. Should align with ramanfacProvForcedShutoff";
      }

      leaf operating-state {
        type enumeration {
          enum "shutoff" {
            value 1;
            description
              "Shutoff";
          }
          enum "normal" {
            value 2;
            description
              "Normal";
          }
          enum "bootstrap" {
            value 3;
            description
              "Bootstrap";
          }
        }
        config false;
        description
          "Provides the operating state of the RAMAN Pumps.";
      }

      leaf target-unachievable-threshold {
        type types:loss-dB-1-precision;
        description
          "Delta between the target gain and the calculated gain values (dB)";
      }

      container target-unachievable-threshold-ranges {
        leaf min {
          type types:loss-dB-1-precision;
        }

        leaf max {
          type types:loss-dB-1-precision;
        }
      }

      list pump-power {
        key "index";
        config false;
        description
          "Actual Pump Power (4 pumps)";
        leaf index {
          type types:object-name;
          description
            "Pump power index";
        }

        leaf power {
          type types:power-dBm-1-precision;
          description
            "Value of pump power (dBm).";
        }

        leaf power-mW {
          type types:power-mW-3-precision;
          description
            "Value of pump power (mW).";
        }
      }

      leaf measured-raman-gain {
        type types:gain-dB-1-precision;
        config false;
        description
          "Calculated Gain of Raman pumps (dB).";
      }

      leaf go-nogo-status {
        type enumeration {
          enum "nogo" {
            value 1;
            description
              "OTDR No go result or no OTDR measurements have yet been done.
               Raman pumps are disabled.";
          }
          enum "go" {
            value 2;
            description
              "OTDR measurements are a Go, Raman pumps are enabled.";
          }
        }
        config false;
        description
          "OTDR Go/No-Go measurement result to enable the raman pumps";
      }

      leaf no-go-overridden {
        type boolean;
        config false;
        description
          "OTDR go-nogo-status has been overridden to go as per user special request.";
      }

      leaf no-go-overridden-reason {
        type string;
        config false;
        description
          "Cause or reasoning for no-go-overridden state.";
      }

      leaf no-go-overridden-date-time {
        type yang:date-and-time;
        description
          "Timestamp of the last time the Raman was set to no-go-overriden state.";
      }

      leaf fiber-type {
        type leafref {
          path "/fiber-types:fiber-type/fiber-types:fiber-type";
        }
        description
          "The fiber type can either be copied from link (Line-In egress fiber) or entered by the external user for manual turn-up";
      }

      leaf input-optical-return-loss {
        type types:loss-dB-1-precision;
        config false;
        description
          "Measured optical return loss at line in (dB).";
      }

      leaf output-optical-return-loss {
        type types:loss-dB-1-precision;
        config false;
        description
          "Measured optical return loss at express out(dB).";
      }

      leaf amp-calibration-override {
        type amp-calibration-override;
        description
          "Values to preserve during calibration.";
      }

      uses types:admin-state;

      container diagnostic {
        config false;
        description
          "Facility Diagnostic state";
        leaf automatic-shutoff {
          type boolean;
          description
            "Automatic Shutoff";
        }

        leaf target-unachievable {
          type boolean;
          description
            "target unachievable";
        }

        leaf optical-line-failed {
          type boolean;
          description
            "Optical Line Failed";
        }

        leaf low-optical-return-loss-input {
          type boolean;
          description
            "Low Optical Return Loss at input.";
        }

        leaf low-optical-return-loss-output {
          type boolean;
          description
            "Low Optical Return Loss at output.";
        }

        leaf activation-inhibited {
          type boolean;
          description
            "RAMAN pumps are prevented from turing on because of a no-go status.";
        }
      }

      leaf alarm-additional-info {
        type string {
          length "1..80";
        }
        description
          "Additional info associated to a raised alarm.";
      }

      leaf password {
        type string {
          length "1..64";
        }
        description
          "Clear text password for nogo override(not for display).";
      }

      leaf encryptedPassword {
        type types:sha512;
        description
          "Encrypted password for nogo override.";
      }
    }
  }

  grouping ciena-6500r-ramans-mount-actions;

  uses ciena-6500r-ramans-mount;
}
