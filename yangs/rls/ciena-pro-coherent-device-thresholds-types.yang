module ciena-pro-coherent-device-thresholds-types {
  namespace "urn:ciena:ns:yang:coherent-device-thresholds-types";
  prefix coherent-device-thresholds-types;

  import ciena-common-version {
    prefix version;
  }
  import ciena-pro-coherent-device-common-types {
    prefix coherent-device-common-types;
  }

  organization
    "Ciena Corporation";
  contact
    "Web URL: http://www.ciena.com/
     Postal:  7035 Ridge Road
              Hanover, Maryland 21076
              U.S.A.
     Phone:   +1 800-921-1144
     Fax:     +1 410-694-5750";
  description
    "Device thresholds definitions for coherent devices.";

  revision 2024-01-01 {
    description
      "Initial version.";
    version:version "version" {
      version:string "1.0.0";
    }
    reference
      "1.0.0";
  }

  grouping coherent-device-thresholds-temperature-thresholds-group {
    leaf low-alarm {
      type coherent-device-common-types:stat-precision1-degree-c-type;
      description
        "Threshold value for low-alarm.";
    }
    leaf high-alarm {
      type coherent-device-common-types:stat-precision1-degree-c-type;
      description
        "Threshold value for high-alarm.";
    }
    leaf low-warning {
      type coherent-device-common-types:stat-precision1-degree-c-type;
      description
        "Threshold value for low-warning.";
    }
    leaf high-warning {
      type coherent-device-common-types:stat-precision1-degree-c-type;
      description
        "Threshold value for high-warning.";
    }
    description
      "Grouping for the low/high alarm/warning thresholds.";
  }

  grouping coherent-device-thresholds-voltage-thresholds-group {
    leaf low-alarm {
      type coherent-device-common-types:stat-precision2-volts-type;
      description
        "Threshold value for low-alarm.";
    }
    leaf high-alarm {
      type coherent-device-common-types:stat-precision2-volts-type;
      description
        "Threshold value for high-alarm.";
    }
    leaf low-warning {
      type coherent-device-common-types:stat-precision2-volts-type;
      description
        "Threshold value for low-warning.";
    }
    leaf high-warning {
      type coherent-device-common-types:stat-precision2-volts-type;
      description
        "Threshold value for high-warning.";
    }
    description
      "Grouping for the low/high alarm/warning thresholds.";
  }

  grouping coherent-device-thresholds-laser-bias-thresholds-group {
    leaf low-alarm {
      type coherent-device-common-types:stat-precision2-milliamps-type;
      description
        "Threshold value for low-alarm.";
    }
    leaf high-alarm {
      type coherent-device-common-types:stat-precision2-milliamps-type;
      description
        "Threshold value for high-alarm.";
    }
    leaf low-warning {
      type coherent-device-common-types:stat-precision2-milliamps-type;
      description
        "Threshold value for low-warning.";
    }
    leaf high-warning {
      type coherent-device-common-types:stat-precision2-milliamps-type;
      description
        "Threshold value for high-warning.";
    }
    description
      "Grouping for the low/high alarm/warning thresholds.";
  }

  grouping coherent-device-thresholds-modulator-bias-thresholds-group {
    leaf low-alarm {
      type coherent-device-common-types:stat-precision2-percent-type;
      description
        "Threshold value for low-alarm.";
    }
    leaf high-alarm {
      type coherent-device-common-types:stat-precision2-percent-type;
      description
        "Threshold value for high-alarm.";
    }
    leaf low-warning {
      type coherent-device-common-types:stat-precision2-percent-type;
      description
        "Threshold value for low-warning.";
    }
    leaf high-warning {
      type coherent-device-common-types:stat-precision2-percent-type;
      description
        "Threshold value for high-warning.";
    }
    description
      "Grouping for the low/high alarm/warning thresholds.";
  }

  grouping coherent-device-thresholds-temperature-group {
    container temperature {
      uses coherent-device-thresholds-types:coherent-device-thresholds-temperature-thresholds-group;
      description
        "Container for the device temperature thresholds.";
    }
    description
      "Grouping for the device temperature thresholds.";
  }

  grouping coherent-device-thresholds-voltage-group {
    container voltage {
      uses coherent-device-thresholds-types:coherent-device-thresholds-voltage-thresholds-group;
      description
        "Container for the device voltage thresholds.";
    }
    description
      "Grouping for the device voltage thresholds.";
  }

  grouping coherent-device-thresholds-laser-bias-group {
    container laser-bias {
      uses coherent-device-thresholds-types:coherent-device-thresholds-laser-bias-thresholds-group;
      description
        "Container for the device laser-bias thresholds.";
    }
    description
      "Grouping for the device laser-bias thresholds.";
  }

  grouping coherent-device-thresholds-laser-temperature-group {
    container laser-temperature {
      uses coherent-device-thresholds-types:coherent-device-thresholds-temperature-thresholds-group;
      description
        "Container for the device laser-temperature thresholds.";
    }
    description
      "Grouping for the device laser-temperature thresholds.";
  }

  grouping coherent-device-thresholds-modulator-bias-group {
    container modulator-bias-xi {
      uses coherent-device-thresholds-types:coherent-device-thresholds-modulator-bias-thresholds-group;
      description
        "Container for the device modulator-bias-xi thresholds.";
    }
    container modulator-bias-xq {
      uses coherent-device-thresholds-types:coherent-device-thresholds-modulator-bias-thresholds-group;
      description
        "Container for the device modulator-bias-xq thresholds.";
    }
    container modulator-bias-yi {
      uses coherent-device-thresholds-types:coherent-device-thresholds-modulator-bias-thresholds-group;
      description
        "Container for the device modulator-bias-yi thresholds.";
    }
    container modulator-bias-yq {
      uses coherent-device-thresholds-types:coherent-device-thresholds-modulator-bias-thresholds-group;
      description
        "Container for the device modulator-bias-yq thresholds.";
    }
    container modulator-bias-x-phase {
      uses coherent-device-thresholds-types:coherent-device-thresholds-modulator-bias-thresholds-group;
      description
        "Container for the device modulator-bias-x-phase thresholds.";
    }
    container modulator-bias-y-phase {
      uses coherent-device-thresholds-types:coherent-device-thresholds-modulator-bias-thresholds-group;
      description
        "Container for the device modulator-bias-y-phase thresholds.";
    }
    description
      "Groping for modulator-bias thresholds.";
  }

  grouping device-thresholds-group {
    container thresholds {
      uses coherent-device-thresholds-types:coherent-device-thresholds-temperature-group;
      uses coherent-device-thresholds-types:coherent-device-thresholds-voltage-group;
      list lane {
        key "lane-index";
        leaf lane-index {
          type uint8 {
            range "1..max";
          }
          description
            "Lane index.";
        }
        uses coherent-device-thresholds-types:coherent-device-thresholds-laser-bias-group;
        uses coherent-device-thresholds-types:coherent-device-thresholds-laser-temperature-group;
        uses coherent-device-thresholds-types:coherent-device-thresholds-modulator-bias-group;
        description
          "Device thresholds per lane.";
      }
      description
        "Device thresholds.";
    }
    description
      "Grouping for device thresholds.";
  }
}
