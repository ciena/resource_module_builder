module ciena-pro-file-service-options {
  namespace "urn:ciena:params:xml:ns:yang:ciena-pro-file-service-options";
  prefix file-service-options;

  import ciena-common-version {
    prefix ciena-common-version;
  }

  organization
    "Ciena Corporation";
  contact
    "Web URL: http://www.ciena.com/
     Postal:  7035 Ridge Road
              Hanover, Maryland 21076
              U.S.A.
     Phone:   +1 800-921-1144
     Fax:     +1 410-694-5750";
  description
    "This module defines the object model used to identify file system access for the file-service.";

  revision 2023-05-12 {
    description
      "Add certificate-validation container.";
    ciena-common-version:string "1.1.0";
  }
  revision 2020-09-30 {
    description
      "Initial revision of file service options";
    ciena-common-version:string "1.0.0";
  }

  container file-service-options {
    description
      "Container around the object model used to identify file system access for the file-service.";
    list data-directory {
      key "name";
      config true;
      description
        "List of directories accessible for file transfer operations";
      leaf name {
        type string;
        description
          "The name of the directory accessible for file transfer";
      }
      leaf mount {
        type string;
        description
          "The name of the directory to mount the data";
      }
    }
    leaf certificate-verification {
      type boolean;
      description
        "Option to enable or disable certificate verification.";
      default "false";
    }
  }
}
