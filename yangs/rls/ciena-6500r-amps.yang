module ciena-6500r-amps {
  yang-version 1.1;
  namespace "urn:ciena:params:xml:ns:yang:ciena-6500r-amps";
  prefix amps;

  import ciena-common-version {
    prefix version;
  }

  import ciena-pro-amp {
    prefix ciena-pro-amp;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's amps object for the 6500r platform";

  revision 2020-09-08 {
    version:version "version" {
      version:string "1.3.0";
    }
    description
      "Use ciena-pro-amp";
  }
  revision 2020-07-10 {
    version:version "version" {
      version:string "1.2.0";
    }
    description
      "Added service-state, debounce-time and debounce-cycle-number.";
  }
  revision 2020-06-30 {
    version:version "version" {
      version:string "1.1.1";
    }
    description
      "Fix version formating";
  }
  revision 2020-06-10 {
    version:version "version" {
      version:string "1.1.0";
    }
    description
      "Removed config false for parameters that should be saved in datastore.";
  }
  revision 2019-12-26 {
    version:version "version" {
      version:string "1.0.4";
    }
    description
      "Added ORL-state";
  }
  revision 2019-12-12 {
    version:version "version" {
      version:string "1.0.3";
    }
    description
      "Added overload-thresholds container
       Added input-optical-overload leaf in diagnostic container";
  }
  revision 2019-12-05 {
    version:version "version" {
      version:string "1.0.2";
    }
    description
      "Added baseine-target-gain
       Added baseine-time-stamp";
  }
  revision 2019-09-25 {
    version:version "version" {
      version:string "1.0.1";
    }
    description
      "Removed automatic-shutoff-compromised
       Removed high-fiber-loss
       Added loss-of-signal";
  }
  revision 2019-09-18 {
    version:version "version" {
      version:string "1.0.1";
    }
    description
      "Added missing diagnostic alarms:
       automatic-shutoff-compromised
       high-fiber-loss
       low-optical-return-loss";
  }
  revision 2019-09-03 {
    version:version "version" {
      version:string "1.0.1";
    }
    description
      "Added parameter ranges
       Removed config false for hysteresis parms and force-apr";
  }
  revision 2019-05-10 {
    version:version "version" {
      version:string "1.0.0";
    }
    description
      "Added additional info for alarms";
  }
  revision 2018-01-01 {
    description
      "6500r Release 1.0";
  }

  grouping ciena-6500r-amps-mount {
    list amps {
      key "name";
      uses ciena-pro-amp:amp;

      leaf parent-link {
        type instance-identifier;
        description
          "parent-link identifier";
      }
    }
  }

  grouping ciena-6500r-amps-mount-actions;

  uses ciena-6500r-amps-mount;
}
