submodule ciena-common-test-submodule {
  belongs-to ciena-common-test-ns {
    prefix top;
  }

  organization
    "osmCiena Corporation";
  contact
    "Web URL: http://www.ciena.com";
  description
    "Test module to test submodules.";

  revision 2018-01-01 {
    description
      "Initial revision";
  }

  grouping abc_group {
    leaf a {
      type uint8;
    }
    leaf b {
      type uint8;
    }
    leaf c {
      type uint8;
    }
  }
}
