submodule ciena-pro-openconfig-ospf-common {
  belongs-to ciena-pro-openconfig-ospf {
    prefix oc-ospf;
  }

  import openconfig-extensions {
    prefix oc-ext;
  }

  import ciena-common-version {
    prefix ciena-common-version;
  }

  organization
    "OpenConfig working group";
  contact
    "OpenConfig working group
     www.openconfig.net";
  description
    "This submodule provides OSPFv2 configuration and operational
     state parameters that are shared across multiple contexts";

  revision 2019-10-08 {
    ciena-common-version:string "1.0.0";
    description
      "Initial revision";
  }

  oc-ext:openconfig-version "1.0.0";

  grouping ospf-common-timers {
    description
      "Common definition of the type of timers that the OSPFv2 implementation
       uses";
    leaf timer-type {
      type enumeration {
        enum "LINEAR_BACKOFF" {
          description
            "The backoff used by the OSPFv2 implementation is linear, such that
             a common delay is added following each event.";
        }
        enum "EXPONENTIAL_BACKOFF" {
          description
            "The backoff used by the OSPFv2 implementation is exponential, such
             that the delay added following each event increases.";
        }
      }
      description
        "The timer mode that is utilised by the implementation.";
    }
  }
}
