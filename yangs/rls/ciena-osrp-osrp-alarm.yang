module ciena-osrp-osrp-alarm {
  namespace "urn:ciena:params:xml:ns:yang:ciena-osrp-osrp-alarm";
  prefix osrp-alarm;

  import ciena-osrp-types {
    prefix ciena-osrp-types;
  }
  import ciena-common-version {
    prefix ciena-common-version;
  }

  organization
    "Ciena Corporation";
  contact
    "Web URL: http://www.ciena.com
     Postal: Ciena India Pvt. Ltd.
     Sector 32, Plot 14,
     Gurgaon 122001,
     Haryana, India";
  description
    "This module describes Ciena's OSRP Alarm
     object model for the 6500r platform.";

  revision 2022-05-30 {
    description
      "Added alarm template state.";
    ciena-common-version:string "1.2.0";
  }
  revision 2021-07-12 {
    description
      "Added condition-type.";
    ciena-common-version:string "1.1.0";
  }
  revision 2020-05-11 {
    description
      "Added priority in templates to identify priority of alarms
       against other alarms within same object.";
    ciena-common-version:string "1.0.1";
  }
  revision 2020-01-21 {
    description
      "6500r-series Release 2.0
       YANG cleanup.";
    ciena-common-version:string "1.0.0";
  }

  list osrp-alarm {
    key "alarm-name object-name object-type node-name";
    leaf alarm-name {
      type string;
      description
        "Name of alarm.";
      mandatory true;
    }
    leaf node-name {
      type string;
      description
        "Name of osrp-node";
    }
    leaf object-name {
      type string;
      description
        "Name of Osrp object";
      mandatory true;
    }
    leaf object-type {
      type ciena-osrp-types:osrp-object-type;
      description
        "Type of Osrp object";
      mandatory true;
    }
    leaf additional-information {
      type string;
      description
        "Identifier of alarm.";
    }
  }
  list osrp-alarm-template {
    key "alarm-name";
    leaf alarm-name {
      type string;
      description
        "Name of alarm.";
    }
    leaf alarm-id {
      type uint32;
      description
        "Alarm id (for backward compatibility).";
    }
    leaf object-type {
      type ciena-osrp-types:osrp-object-type;
      description
        "Type of object.";
      mandatory true;
    }
    leaf condition-type {
      type string {
        length "1..31";
      }
      description
        "The type of the alarm; used to group or classify similar or related alarms
         within a resource.  Only one alarm of any given condition type can be active
         against a given resource at a time. This allows classification of alarms into
         conditions, and then the highest condition is the one that prevails. Since
         different alarms can (and do) share condition types, it provides a form of a
         classification system.";
    }
    leaf cause {
      type string;
      description
        "Alarm cause (alarm text).";
      mandatory true;
    }
    leaf type {
      type ciena-osrp-types:alarm-type;
      description
        "Alarm template type. For major/critical alarms, value is high else low.";
    }
    leaf severity {
      type ciena-osrp-types:alarm-severity;
      description
        "Severity of alarm.";
    }
    leaf priority {
      type ciena-osrp-types:alarm-priority;
      description
        "Priority of alarm against other alarms in same object-type.";
    }
    leaf service-impact {
      type ciena-osrp-types:alarm-service-impact;
      description
        "Impact of alarm on service.";
    }
    leaf template-state {
      type ciena-osrp-types:alarm-template-state;
      description
        "The state of the alarm template, which controls whether and how alarm records
         are generated when the alarm is raised. Default: enabled.";
    }
    leaf description {
      type string {
        length "0..1024";
      }
      description
        "Description of alarm condition.";
    }
  }
}
