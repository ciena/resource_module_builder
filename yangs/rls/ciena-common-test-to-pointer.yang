module ciena-common-test-to-pointer {
  yang-version 1.1;
  namespace "urn:ciena:params:xml:ns:yang:ciena-common-test-to-pointer";
  prefix tl;

  import ciena-common-yang {
    prefix yang;
  }

  organization
    "Ciena Corporation";
  contact
    "Web URL: http://www.ciena.com";
  description
    "A module to test ciena-common-options:to-pointer-paths option can convert all container
     and string from a module to containerptr and stringptr";

  revision 2023-10-26 {
    description
      "Add leaf/leaf-list to test unions to pointers.";
  }
  revision 2023-10-23 {
    description
      "Add root-level object to have conflict with 'ciena-common-test-ambiguous-object' module to
       test the preferred-modules option.";
  }
  revision 2023-03-13 {
    description
      "Initial revision";
  }

  typedef union-data-type {
    type union {
      type uint64;
      type int64;
      type decimal64 {
        fraction-digits 2;
      }
      type decimal64 {
        fraction-digits 17;
      }
      yang:unionptr "true";
    }
  }

  container common-test-leaf {
    leaf simple {
      type string;
    }
    leaf len-range {
      type uint8;
    }
    leaf union-leaf {
      type union-data-type;
    }
    leaf union-leaf-no-pointer {
      type union-data-type;
    }
    leaf-list union-leaf-list {
      type union-data-type;
    }
  }
  container ambiguous-object {
    description
      "This is only for a test case involving preferred-modules. Please do
       not use this container for any of your tests.";
    leaf number {
      type uint16;
    }
  }
}
