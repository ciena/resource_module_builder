module ciena-pro-optical-constraints {
  yang-version 1.1;
  namespace "urn:ciena:params:xml:ns:yang:ciena-pro-optical-constraints";
  prefix pro-optical-constraints;

  import ciena-common-yang {
    prefix ciena-common-yang;
  }
  import ciena-common-version {
    prefix ciena-common-version;
  }
  import ciena-pro-optical-types {
    prefix ciena-pro-optical-types;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena optical frequency constraints.";

  revision 2022-08-15 {
    description
      "Initial version";
    ciena-common-version:version "version" {
      ciena-common-version:string "1.0.0";
    }
  }

  grouping optical-constraints-grouping {
    list supported-freq-range {
      key "min-freq";
      leaf band-info {
        type ciena-pro-optical-types:band-occupancy;
        description
          "Supported band types";
      }
      leaf min-freq {
        type ciena-pro-optical-types:frequency;
        description
          "Minimum frequency";
      }
      leaf max-freq {
        type ciena-pro-optical-types:frequency;
        description
          "Maximum frequency";
      }
    }
  }

  grouping ciena-pro-optical-constraints-mount-data {
    container optical-constraints {
      uses optical-constraints-grouping;
    }
  }

  grouping ciena-pro-optical-constraints-mount-actions-notifs;

  grouping ciena-pro-optical-constraints-mount-actions-notifs-as-cont;

  grouping ciena-pro-optical-constraints-mount-data-actions-notifs-as-cont {
    container optical-constraints {
      uses optical-constraints-grouping;
    }
  }

  uses ciena-pro-optical-constraints-mount-data;
}
