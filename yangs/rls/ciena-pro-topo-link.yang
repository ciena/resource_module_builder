module ciena-pro-topo-link {
  namespace "urn:ciena:params:xml:ns:yang:ciena-pro-topo-link";
  prefix link;

  import ciena-6500r-types {
    prefix common-types;
  }
  import ciena-pro-topo-types {
    prefix topo-types;
  }
  import ciena-pro-link {
    prefix ciena-pro-link;
  }
  import ciena-pro-optical-types {
    prefix ciena-pro-optical-types;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's topological link object for the 6500r-Series platform";

  revision 2018-05-08 {
    description
      "6500r-series Release 1.0";
  }

  list topo-link {
    key "name";
    leaf name {
      type string {
        length "1..200";
      }
      description
        "Flattened link identifier";
    }
    leaf from {
      type string {
        length "1..200";
      }
      description
        "From (typically port) identifier";
    }
    leaf to {
      type string {
        length "1..200";
      }
      description
        "To (typically port) identifier";
    }
    leaf is-external {
      type boolean;
      default "false";
      description
        "false if link is within a slot, otherwise true";
    }
    leaf link-type {
      type ciena-pro-link:link-type;
      default "fiber";
      description
        "ciena_6500r_links_link_type";
    }
    leaf band {
      type ciena-pro-optical-types:band-occupancy;
      description
        "Supported band types";
    }
    list nmc-freq {
      key "freq";
      leaf freq {
        type uint32;
        description
          "NMC center frequency in unit of MHz";
      }
    }
  }
}
