module ciena-pro-pm-provisioning {
  namespace "urn:ciena:params:xml:ns:yang:ciena-pro-pm-provisioning";
  prefix pm-provisioning;

  import ciena-common-version {
    prefix ciena-common-version;
  }
  import ciena-pro-pm-types {
    prefix pm-types;
  }

  organization
    "Ciena Corporation";
  contact
    "Web URL: http://www.ciena.com";
  description
    "This module describes Ciena's pm provisioning notification data";

  revision 2023-02-01 {
    description
      "Include is line flag and slot number";
    ciena-common-version:string "1.0.1";
  }
  revision 2022-11-09 {
    description
      "Initial Yang File";
    ciena-common-version:string "1.0.0";
  }

  container otn-provisioning-data {
    description
      "Contains all OTN interface provisioning data used by PMs";
    leaf name {
      type string;
      config false;
      description
        "Name";
    }
    leaf interface-type {
      type pm-types:otn-signal-type;
      config false;
      description
        "Interface Type";
    }
    leaf slot {
      type uint32;
      config false;
      description
        "Slot number of the interface";
    }
    leaf data-rate {
      type pm-types:pm-data-rate;
      config false;
      description
        "Data Rate";
    }
    leaf fec-type {
      type pm-types:pm-fec-format;
      config false;
      description
        "Fec Type";
    }
    leaf odu-mode {
      type pm-types:pm-odu-mode;
      config false;
      description
        "Odu Mode";
    }
    leaf dm-enable {
      type boolean;
      config false;
      description
        "dm enable";
    }
    leaf is-gfp {
      type boolean;
      config false;
      description
        "Flag for checking gfp under odu";
    }
    leaf is-line {
      type boolean;
      config false;
      description
        "Flag for checking is this a line interface";
    }
  }
}
