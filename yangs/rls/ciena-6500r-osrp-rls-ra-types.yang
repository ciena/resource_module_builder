module ciena-6500r-osrp-rls-ra-types {
  namespace "urn:ciena:params:xml:ns:yang:ciena-6500r-osrp-rls-ra-types";
  prefix types;

  import ietf-inet-types {
    prefix ietf-inet;
  }

  import ciena-common-version {
    prefix ciena-common-version;
  }

  organization
    "Ciena Corporation";
  contact
    "Web URL: http://www.ciena.com
     Postal: Ciena India Pvt. Ltd.
     Sector 32, Plot 14,
     Gurgaon 122001,
     Haryana, India";
  description
    "This module describes Ciena's osrp-rls-ra-types object for the 6500r platform";

  revision 2021-04-06 {
    ciena-common-version:string "1.7.1";
    description
      "Change osrp-conn-trans-mode to 32 characters max";
  }
  revision 2021-01-28 {
    ciena-common-version:string "1.7.0";
    description
      "New node-id-hex-type type added.";
  }
  revision 2021-01-25 {
    ciena-common-version:string "1.6.0";
    description
      "Link optimization mode changed to enum.";
  }
  revision 2021-01-05 {
    ciena-common-version:string "1.5.2";
    description
      "Added no-fault field in rx-proxy enum type";
  }
  revision 2020-12-23 {
    ciena-common-version:string "1.5.1";
    description
      "Added unknown field in controller state and rx-proxy state enums.";
  }
  revision 2020-12-14 {
    ciena-common-version:string "1.5.0";
    description
      "Added typedef timeperiod-msec.";
  }
  revision 2020-12-11 {
    ciena-common-version:string "1.4.0";
    description
      "Added channel controller states and rx proxy status enum values to be used for end to end channel diagnostics.";
  }
  revision 2020-11-16 {
    ciena-common-version:string "1.3.1";
    description
      "Merge various degraded enum values into a single one in osrp-port-fault.";
  }
  revision 2020-10-07 {
    ciena-common-version:string "1.3.0";
    description
      "Rx-proxy faults addition.";
  }
  revision 2020-09-25 {
    ciena-common-version:string "1.2.0";
    description
      "discrete-link-identifier type defined.";
  }
  revision 2020-07-15 {
    ciena-common-version:string "1.1.0";
    description
      "grouping-ownership type defined.";
  }
  revision 2019-09-20 {
    ciena-common-version:string "1.0.0";
    description
      "oob-port-num and port-num added.";
  }
  revision 2019-04-11 {
    description
      "Initial revision.";
  }

  typedef osrp-node-name {
    type string {
      length "3..512";
    }
  }

  typedef node-id-hex-type {
    type string {
      length "16";
    }
  }

  typedef osrp-local-mc-ckt-name {
    type string;
  }

  typedef osrp-local-mc-ckt-id {
    type string;
  }

  typedef osrp-local-nmc-ckt-name {
    type string;
  }

  typedef osrp-local-nmc-ckt-id {
    type string;
  }

  typedef osrp-port-identifier {
    type string;
  }

  typedef band-type {
    type enumeration {
      enum "BAND-C";
      enum "BAND-L";
    }
  }

  typedef port-grid-type {
    type enumeration {
      enum "C-BAND-FLEX";
      enum "L-BAND-FLEX";
      enum "C-L-BAND";
    }
  }

  typedef osrp-port-type {
    type enumeration {
      enum "service";
      enum "routing";
      enum "internal";
    }
  }

  typedef osrp-pfg-type {
    type enumeration {
      enum "unknown";
      enum "channel";
      enum "section";
      enum "line";
    }
  }

  typedef channel-type {
    type enumeration {
      enum "dynamic";
      enum "permanent";
    }
  }

  typedef osrp-bitvec {
    type string;
  }

  typedef osrp-conn-owner {
    type enumeration {
      enum "osrp";
      enum "user";
    }
  }

  typedef frequency-mhz {
    type uint32;
    units "MHz";
  }

  typedef osrp-admin-state {
    type enumeration {
      enum "not-applicable";
      enum "enabled";
      enum "disabled";
    }
  }

  typedef osrp-operational-state {
    type enumeration {
      enum "disabled";
      enum "enabled";
    }
  }

  typedef osrp-port-direction {
    type enumeration {
      enum "unknown";
      enum "mux";
      enum "demux";
    }
  }

  typedef osrp-port-fault {
    type enumeration {
      enum "none";
      enum "down";
      enum "blocked";
      enum "degraded";
      enum "och-down";
      enum "och-degrade";
    }
  }

  typedef osrp-port-role {
    type enumeration {
      enum "unknown";
      enum "boundary-in";
      enum "boundary-out";
    }
  }

  typedef osrp-conn-channel-status {
    type enumeration {
      enum "adding";
      enum "managed";
      enum "deleting";
      enum "switching";
      enum "switched-to-ase";
    }
  }

  typedef osrp-conn-trans-mode {
    type string {
      length "0..32";
    }
  }

  typedef osrp-conn-lom {
    type enumeration {
      enum "standard";
      enum "snr-performance";
      enum "fast-tracking";
      enum "spectral-efficiency";
      enum "low-latency";
      enum "narrow-bandwidth-channel";
      enum "non-linear-channel";
      enum "foreign-line";
      enum "reserved-mode-1";
      enum "reserved-mode-2";
      enum "reserved-mode-3";
      enum "custom";
      enum "unknown";
    }
  }

  typedef osrp-conn-dispersion {
    type decimal64 {
      fraction-digits 2;
    }
    units "ps/nm";
  }

  typedef conn-provisioning-types {
    type enumeration {
      enum "normal";
      enum "minimal";
    }
  }

  typedef oob-port-num {
    type ietf-inet:port-number {
      range "51001..52000";
    }
  }

  typedef port-num {
    type ietf-inet:port-number;
  }

  typedef timeperiod-msec {
    type uint32;
    units "milliseconds";
  }

  typedef timeperiod-sec {
    type uint32;
    units "seconds";
  }

  typedef yes-no {
    type enumeration {
      enum "no";
      enum "yes";
    }
  }

  typedef grouping-ownership {
    type enumeration {
      enum "master";
      enum "slave";
    }
  }

  typedef discrete-link-identifier {
    type string;
  }

  typedef channel-operational-state {
    type enumeration {
      enum "inactive" {
        description
          "Initial channel state";
      }
      enum "waiting-for-power" {
        description
          "Channel is waiting for sufficient power to be selected for addition.";
      }
      enum "pending-add" {
        description
          "Channel has been selected for addition.";
      }
      enum "adding" {
        description
          "Channel is in the process of being added.";
      }
      enum "in-service" {
        description
          "Channel has been added.";
      }
      enum "waiting-for-downstream" {
        description
          "Channel is waiting for the downstream section mux to finish deleting to be selected for deletion.";
      }
      enum "pending-delete" {
        description
          "Channel has been selected for deletion.";
      }
      enum "deleting" {
        description
          "Channel is in the process of being deleted.";
      }
      enum "faulted" {
        description
          "Fault has been declared against the channel.";
      }
      enum "pending-ase-replacement" {
        description
          "The faulted channel has been selected for ASE replacement.";
      }
      enum "replacing-with-ase" {
        description
          "Channel is in the process of being replaced by ASE.";
      }
      enum "ase" {
        description
          "Channel has been replaced by ASE.";
      }
      enum "unknown" {
        description
          "Channel controller state is not known.";
      }
    }
  }

  typedef rx-proxy-status {
    type enumeration {
      enum "rx-degrade";
      enum "rx-down";
      enum "no-fault";
    }
  }
}
