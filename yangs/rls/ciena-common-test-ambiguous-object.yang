module ciena-common-test-ambiguous-object {
  yang-version 1.1;
  namespace "urn:ciena:params:xml:ns:yang:ciena-common-test-ambiguous-object";
  prefix tl;

  organization
    "Ciena Corporation";
  contact
    "Web URL: http://www.ciena.com";
  description
    "A module to test that the preferred-modules option works.";

  revision 2023-10-23 {
    description
      "Initial revision";
  }

  container ambiguous-object {
    description
      "This is only for a test case involving preferred-modules. Please do
       not use this container for any of your tests.";
    leaf not-number {
      type string;
    }
  }
}
