module ciena-pro-ztp {
  namespace "urn:ciena:params:xml:ns:yang:ciena-pro-ztp";
  prefix ciena-pro-ztp;

  import ciena-6500r-types {
    prefix ciena-6500r-types;
  }

  import ciena-common-version {
    prefix ciena-common-version;
  }

  organization
    "Ciena Corporation";
  contact
    "Web URL: http://www.ciena.com/";
  description
    "This module defines zero touch provisioning for Ciena's 6500r Platform.";

  revision 2019-10-25 {
    ciena-common-version:string "1.0.1";
    description
      "Add RPC call to ztp";
  }
  revision 2019-06-27 {
    ciena-common-version:string "1.0.0";
    description
      "Initial version";
  }

  container ztp {
    description
      "ZTP top structure";
    uses ciena-6500r-types:admin-state;

    leaf oper-state {
      type enumeration {
        enum "ztp-is-done" {
          description
            "ztp is done";
        }
        enum "ztp-in-progress" {
          description
            "ztp in progress";
        }
        enum "processing-client-options" {
          description
            "processing the dhcp client options";
        }
        enum "processing-ra-options" {
          description
            "processing the relay agent options";
        }
        enum "failed-due-to-internal-error" {
          description
            "ztp failed due to internal error";
        }
        enum "failed-to-process-ra-options" {
          description
            "failed while processing the relay agent options";
        }
        enum "failed-to-process-command-file" {
          description
            "failed while processing the command file";
        }
        enum "failed-to-process-config-file" {
          description
            "failed while processing the config file";
        }
        enum "failed-to-process-script-file" {
          description
            "failed while processing the script file";
        }
        enum "failed-to-download-bootfile" {
          description
            "bootfile xml download failed";
        }
        enum "failed-to-parse-bootfile" {
          description
            "bootfile xml parsing failed";
        }
        enum "failed-to-validate-bootfile" {
          description
            "bootfile xml validation failed";
        }
        enum "failed-to-process-bootfile" {
          description
            "bootfile xml processing failed";
        }
        enum "failed-to-install-software" {
          description
            "software installation failed";
        }
        enum "failed-to-upgrade-software" {
          description
            "software upgrade failed";
        }
        enum "option43-not-received" {
          description
            "option43 not received";
        }
        enum "option66-not-received" {
          description
            "option66 not received";
        }
        enum "product-name-missing-in-bootfile" {
          description
            "Product name not present in bootfile";
        }
        enum "product-name-not-compatible" {
          description
            "Product name is not compatible with current configuration";
        }
        enum "release-name-missing-in-bootfile" {
          description
            "Release name not present in bootfile";
        }
        enum "release-name-not-compatible" {
          description
            "Release name is not compatible with current configuration";
        }
        enum "config-rule-not-compatible" {
          description
            "Config rule is not compatible with current configuration";
        }
        enum "timeout-not-compatible" {
          description
            "timeout is not compatible with current configuration";
        }
        enum "missing-config-file-or-script-file-or-package-path" {
          description
            "Either config file, script file or package path should be present";
        }
        enum "invalid-url-received-for-bootfile" {
          description
            "option 66 and/or 67 doesn't constitute a proper url";
        }
        enum "invalid-url-received-for-package-file" {
          description
            "package file url found in bootfile is not valid";
        }
        enum "invalid-url-received-for-config-file" {
          description
            "config file url found in bootfile is not valid";
        }
        enum "invalid-url-received-for-script-file" {
          description
            "script file url found in bootfile is not valid";
        }
        enum "invalid-url-received-for-license-file" {
          description
            "license file url found in bootfile is not valid";
        }
        enum "file-access-issue-due-to-invalid-url" {
          description
            "file access issue due to invalid url";
        }
        enum "file-access-issue-due-to-permissions" {
          description
            "file access issue due to permissions";
        }
        enum "file-access-issue-due-to-network-failure" {
          description
            "file access issue due to network failure";
        }
        enum "file-access-issue-due-to-ssl-verification-failure" {
          description
            "file access issue due to ssl verification failure";
        }
        enum "file-access-issue-due-to-protocol-error" {
          description
            "file access issue due to protocol error";
        }
        enum "upgrade-in-progress" {
          description
            "software upgrade in progress";
        }
      }
      config false;
    }

    leaf oper-state-desc {
      type string;
      config false;
      description
        "operational state description";
    }
  }

  rpc set-shelf-state {
    input {
      leaf shelf-commissioned {
        type boolean;
        description
          "shelf is commissioned";
      }
    }
  }

  rpc get-shelf-state {

    output {
      leaf shelf-commissioned {
        type boolean;
        description
          "shelf is commissioned";
      }
    }
  }
}
