module CIENA-6500R-ENTITY-MIB {
  namespace "urn:ietf:params:xml:ns:yang:smiv2:CIENA-6500R-ENTITY-MIB";
  prefix ciena-6500r-entity;

  import CIENA-6500R-SLOTS-MIB {
    prefix ciena-6500r;
  }
  import CIENA-6500R-TYPES-MIB {
    prefix ciena-6500r-types;
  }
  import CIENA-PRO-TYPES-MIB {
    prefix ciena-pro;
  }

  organization
    "Ciena Corporation";
  contact
    "Web URL: http://www.ciena.com/
     Postal:  7035 Ridge Road
     Hanover, Maryland 21076
     U.S.A.
     Phone:   +1 800-921-1144
     Fax:     +1 410-694-5750";
  description
    "This modules describes Ciena's photonic ENTITY object.";

  revision 2022-01-10 {
    description
      "Initial revision.";
  }

  container cienaRlsEntityMIB {
    list rlsPhysicalEntityEntry {
      config false;
      key "rlsPhysicalEntityIndex";
      description
        "";
      leaf rlsPhysicalEntityIndex {
        type ciena-6500r-types:PhysicalIndex;
        config false;
        description
          "The index for this entry.";
      }
      leaf rlsPhysicalEntityCtype {
        type ciena-pro:DisplayString128;
        config false;
        description
          "The type of the physical entity.  ";
      }
      leaf rlsPhysicalEntityClass {
        type ciena-6500r-types:PhysicalClass;
        config false;
        description
          "An indication of the general hardware type of the physical
           entity.";
      }
      leaf rlsPhysicalEntityName {
        type ciena-pro:DisplayString32;
        config false;
        description
          "Name of the Physical Entry";
      }
      leaf rlsPhysicalEntityHardwareVersion {
        type ciena-pro:DisplayString32;
        config false;
        description
          "The vendor-specific hardware version for the
           physical entity.  ";
      }
      leaf rlsPhysicalEntityFirmwareVersion {
        type ciena-pro:DisplayString32;
        config false;
        description
          "The vendor-specific firmware version for the
           physical entity.";
      }
      leaf rlsPhysicalEntitySoftwareVersion {
        type ciena-pro:DisplayString32;
        config false;
        description
          "The vendor-specific software version for the
           physical entity.";
      }
      leaf rlsPhysicalEntitySerialNumber {
        type ciena-pro:DisplayString32;
        config false;
        description
          "The vendor-specific serial number string for the physical
           entity. ";
      }
      leaf rlsPhysicalEntityManufactureName {
        type ciena-pro:DisplayString32;
        config false;
        description
          "The name of the manufacturer of this physical component.";
      }
      leaf rlsPhysicalEntityModelName {
        type ciena-pro:DisplayString32;
        config false;
        description
          "The vendor-specific model name identifier string associated
           with this physical component.  ";
      }
      leaf rlsPhysicalEntityAssetID {
        type ciena-pro:DisplayString32;
        config false;
        description
          "Asset Id of the entity";
      }
      leaf rlsPhysicalEntityType {
        type ciena-pro:DisplayString32;
        config false;
        description
          "The Entity Type";
      }
    }
  }
}
