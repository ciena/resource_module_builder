module ciena-pro-babel-debug {
  yang-version 1.1;
  namespace "urn:ciena:params:xml:ns:yang:ciena-pro-babel-debug";
  prefix babel-debug;

  import ciena-common-yang {
    prefix ciena;
  }
  import ciena-common-test-harness {
    prefix test-harness;
  }

  organization
    "Ciena Corporation";
  contact
    "Web URL: http://www.ciena.com";
  description
    "Babel Service Debug Tools";

  revision 2021-11-11 {
    description
      "Add build-info container with a flag indicating whether Rust is
       enabled.";
    reference
      "See Documentation";
  }
  revision 2020-10-02 {
    description
      "Initial Commit";
    reference
      "See Documentation";
  }

  container build-info {
    config false;
    leaf rust-enabled {
      type boolean;
      description
        "Whether Babel-svc is running with Rust extensions enabled for
         performance.";
    }
  }

  rpc display-diagnostic {
    description
      "Dumps internal stuctures/outputs of functions that we want to debug";
    input {
      leaf in {
        type string;
        description
          "Function/global to be output with call to str(in)";
      }
    }
    output {
      uses ciena:rpc-result-common;
      leaf out {
        type string {
          length "1..50000";
        }
        description
          "This will be the internal model that we are interested in";
      }
    }
  }

  rpc test-babel-handler-performance {
    output {
      uses test-harness:test-rpc-output-common;
    }
  }
}
