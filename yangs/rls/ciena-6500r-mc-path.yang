module ciena-6500r-mc-path {
  namespace "urn:ciena:params:xml:ns:yang:ciena-6500r-mc-path";
  prefix mcpath;

  import ciena-6500r-types {
    prefix common-types;
  }

  import ciena-common-version {
    prefix version;
  }

  organization
    "Ciena Corporation";
  contact
    "Web URL: http://www.ciena.com/
     Postal:  7035 Ridge Road
             Hanover, Maryland 21076
             U.S.A.
     Phone:   +1 800-921-1144
     Fax:     +1 410-694-5750";
  description
    "This module implements a construct to represent a stitched path of mc elements. It only creates
     the media channel that is not auto-created during link creation.";

  revision 2019-06-11 {
    version:version "version" {
      version:string "1.1.0";
    }
    description
      "6500r-series Release 1.1
       Added mcpath yang model";
  }

  list mc-path {
    key "name";
    leaf name {
      type string;
      description
        "This is a path that is constituted by mc elements";
    }

    leaf owner {
      type string;
      description
        "This identifies the provisioning ownership";
    }

    leaf from {
      type instance-identifier;
      mandatory true;
      description
        "From port identifier";
    }

    leaf to {
      type instance-identifier;
      mandatory true;
      description
        "To port identifier";
    }

    leaf min-freq {
      type common-types:frequency;
      mandatory true;
      description
        "Minimum frequency edge of the media channel";
    }

    leaf low-freq-deadband {
      type common-types:frequency;
      default "6.25";
      description
        "Deadband associated with min-freq edge to account for filter roll off. ";
    }

    leaf max-freq {
      type common-types:frequency;
      mandatory true;
      description
        "Maximum frequency edge of the media channel";
    }

    leaf high-freq-deadband {
      type common-types:frequency;
      default "6.25";
      description
        "Deadband associated with max-freq edge to account for filter roll off. ";
    }

    leaf user-label {
      type string;
      description
        "a user provisioned label used by discrete MC path elements.";
    }

    list path {
      key "element";
      leaf element {
        type instance-identifier;
        description
          "The identifer of the path element";
      }
    }
  }
}
