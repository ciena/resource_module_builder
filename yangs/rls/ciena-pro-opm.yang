module ciena-pro-opm {
  namespace "urn:ciena:params:xml:ns:yang:ciena-pro-opm";
  prefix pro-opm;

  import ciena-common-version {
    prefix ciena-common-version;
  }

  import ciena-pro-optical-types {
    prefix ciena-pro-optical-types;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's Optical Power Monitor (OPM) object.";

  revision 2020-08-01 {
    ciena-common-version:version "version" {
      ciena-common-version:string "1.0.0";
    }
    description
      "Initial version";
  }

  grouping opm {
    leaf name {
      type string;
      description
        "OPM facility name";
    }

    leaf signal-type {
      type enumeration {
        enum "C-Band";
        enum "L-Band";
      }
      description
        "Signal Type";
    }

    leaf start-frequency-index {
      type uint16;
      config false;
      description
        "Center frequency index of the first slice measured by the OPM";
    }

    leaf integration-bandwidth {
      type ciena-pro-optical-types:frequency;
      units "GHz";
      config false;
      description
        "How wide each measurement slice is";
    }

    leaf slice-spacing {
      type ciena-pro-optical-types:frequency;
      units "GHz";
      config false;
      description
        "The offset between the center frequencies of neighboring measurement slices, the slices may overlap each other";
    }

    leaf min-freq {
      type ciena-pro-optical-types:frequency;
      config false;
      description
        "Minimum frequency limit of the OCM module (start frequency index converted to a frequency)";
    }

    leaf max-freq {
      type ciena-pro-optical-types:frequency;
      config false;
      description
        "Maximum frequency limit of the OCM module (calculated using start frequency index and the number of slices returned via SNMP)";
    }

    list slice {
      key "frequency";
      config false;
      leaf frequency {
        type ciena-pro-optical-types:frequency;
        config false;
        description
          "Center frequency";
      }

      leaf power {
        type ciena-pro-optical-types:power {
          range "-75..75.00";
        }
        units "dBm";
        config false;
        description
          "Power measured in an OPM slice in dBm.";
      }
    }
  }
}
