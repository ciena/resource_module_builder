module ciena-pro-fiber-types {
  namespace "urn:ciena:params:xml:ns:yang:ciena-pro-fiber-types";
  prefix fiber-types;

  import ciena-6500r-types {
    prefix types;
  }

  import ciena-common-version {
    prefix version;
  }

  organization
    "Ciena Corporation";
  contact
    "Web URL: http://www.ciena.com/
     Postal:  7035 Ridge Road
             Hanover, Maryland 21076
             U.S.A.
     Phone:   +1 800-921-1144
     Fax:     +1 410-694-5750";
  description
    "This effective area and launch coefficients for different fiber types";

  revision 2021-02-05 {
    version:version "version" {
      version:string "1.0.1";
    }
    description
      "6500r-series Release 2.3
       Updated the description of the launch cofficient to indicate that
       this attribute represents the dB loss per km of the fiber type";
  }
  revision 2019-11-06 {
    version:version "version" {
      version:string "1.0.0";
    }
    description
      "6500r-series Release 2.0
       Added effective area and launch coefficients and pfib coefficients";
  }

  typedef band {
    type enumeration {
      enum "C" {
        description
          "C-Band";
      }
      enum "CPlusL-C" {
        description
          "C+L-C-Band";
      }
      enum "CPlusL-L" {
        description
          "C+L-L-Band";
      }
    }
    description
      "the frequency band";
  }

  typedef raman {
    type enumeration {
      enum "with-raman" {
        description
          "with raman";
      }
      enum "without-raman" {
        description
          "without raman";
      }
    }
    description
      "this identifies if it's for RAMAN";
  }

  typedef profile-type {
    type enumeration {
      enum "predefined" {
        description
          "pre-defined";
      }
      enum "custom" {
        description
          "custom";
      }
    }
    description
      "this identifies if it's pre-defined or custom fiber-type";
  }

  list fiber-type {
    key "fiber-type";
    leaf fiber-type {
      type types:object-name;
      description
        "fiber type";
    }

    leaf launch-coefficient {
      type decimal64 {
        fraction-digits 2;
      }
      units "dB/Km";
      description
        "loss coefficient for this fiber type in dB/Km";
    }

    leaf dispersion {
      type decimal64 {
        fraction-digits 2;
      }
      units "dB/km";
      description
        "dispersion for this fiber type";
    }

    leaf effective-area {
      type decimal64 {
        fraction-digits 2;
      }
      units "um^2";
      description
        "effective area for this fiber type";
    }

    list pfib {
      key "band raman";
      leaf band {
        type band;
      }

      leaf raman {
        type raman;
      }

      leaf Pfib-a {
        type decimal64 {
          fraction-digits 2;
        }
        units "dB/Km";
        description
          "Pfib a for this fiber type, band and with/without raman";
      }

      leaf Pfib-b {
        type decimal64 {
          fraction-digits 2;
        }
        units "dB/Km";
        description
          "Pfib b for this fiber type, band and with/without raman";
      }
    }

    leaf profile-type {
      type profile-type;
      description
        "profile-type of the fiber type; pre-defined or custom";
    }
  }
}
