module ciena-osrp-pce-graph-publisher {
  namespace "urn:ciena:params:xml:ns:yang:ciena-osrp-pce-graph-publisher";
  prefix graph-publisher;

  import ciena-common-version {
    prefix ciena-common-version;
  }

  organization
    "Ciena Corporation";
  contact
    "Web URL: http://www.ciena.com
     Postal: Ciena India Pvt. Ltd.
     Sector 32, Plot 14,
     Gurgaon 122001,
     Haryana, India";
  description
    "This module describes Ciena's Graph publisher which will publish the inputs to build oce-graph of Pce.";

  revision 2020-05-20 {
    ciena-common-version:string "1.0.0";
    description
      "6500r-series Release 2.0
       Initial config.";
  }

  list oce-graph-publisher {
    key "publisher-domain";
    description
      "OCE Graph publisher details";
    leaf publisher-domain {
      type string;
      mandatory true;
      description
        "Publisher domain name";
    }

    leaf publisher-name {
      type string;
      mandatory true;
      description
        "Publisher name";
    }

    list graph-element {
      key "element-name";
      leaf element-name {
        type string {
          length "1..10";
        }
        mandatory true;
        description
          "Graph element name, node or link.";
      }

      leaf element-desc {
        type instance-identifier;
        mandatory true;
        description
          "Graph publisher object identifier";
      }
    }
  }
}
