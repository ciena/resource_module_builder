module ciena-pro-oms {
  namespace "urn:ciena:params:xml:ns:yang:ciena-pro-oms";
  prefix ciena-pro-oms;

  import ciena-common-version {
    prefix version;
  }

  organization
    "Ciena Corporation";
  contact
    "Web URL: http://www.ciena.com/
     Postal:  7035 Ridge Road
              Hanover, Maryland 21076
              U.S.A.
     Phone:   +1 800-921-1144
     Fax:     +1 410-694-5750";
  description
    "This modules describes Ciena's OMS model.";

  revision 2022-11-10 {
    description
      "Initial revision";
    version:version "version" {
      version:string "1.0.0";
    }
  }

  container oms {
    container options {
      leaf suppress-serdes-errors {
        type boolean;
        default "true";
        description
          "By default serdes errors are suppressed by oms and not reported to the caller,
           set this flag to false to receive all serdes errors";
      }
      description
        "Options when performing a remote set/get through oms";
    }
  }
}
