module ciena-pro-dependency {
  namespace "urn:ciena:params:xml:ns:yang:ciena-pro-dependency";
  prefix ciena-pro-dependency;

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's Pro platform dependency mgr ";

  revision 2019-04-11 {
    description
      "Initial revision";
  }

  rpc register-blocking {
    input {
      leaf service-name {
        type string;
        description
          "Serivce Name";
      }
      leaf priority {
        type uint32 {
          range "0..3";
        }
        description
          "Priority";
      }
      leaf trans-id {
        type string;
        description
          "Transaction ID";
      }
    }
    output {
      leaf result {
        type boolean;
        description
          "Did transaction register?";
      }
    }
  }

  rpc activate-blocking {
    input {
      leaf trans-id {
        type string;
        description
          "Transaction ID";
      }
      leaf service-name {
        type string;
        description
          "Service Name";
      }
    }
    output {
      leaf result {
        type boolean;
        description
          "Did transaction get activated?";
      }
    }
  }

  rpc cancel-blocking {
    input {
      leaf trans-id {
        type string;
        description
          "Transaction ID";
      }
      leaf service-name {
        type string;
        description
          "Service Name";
      }
      leaf priority {
        type uint32 {
          range "0..3";
        }
        description
          "Priority";
      }
    }
    output {
      leaf result {
        type boolean;
        description
          "Did transaction get de-activated?";
      }
    }
  }

  rpc check-blocking {
    input {
      leaf service-name {
        type string;
        description
          "Service Name";
      }
      leaf priority {
        type uint32 {
          range "0..3";
        }
        description
          "Priority";
      }
      leaf trans-id {
        type string;
        description
          "Transaction ID";
      }
    }
    output {
      leaf block {
        type boolean;
        description
          "Does the transaction block?";
      }
    }
  }
}
