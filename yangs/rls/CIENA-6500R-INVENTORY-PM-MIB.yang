module CIENA-6500R-INVENTORY-PM-MIB {
  namespace "urn:ietf:params:xml:ns:yang:smiv2:CIENA-6500R-INVENTORY-PM-MIB";
  prefix ciena-6500r-inventory;

  import CIENA-6500R-INVENTORY-MIB {
    prefix ciena-6500r;
  }
  import CIENA-6500R-TYPES-MIB {
    prefix ciena-6500r-types;
  }
  import CIENA-PRO-TYPES-MIB {
    prefix ciena-pro;
  }

  organization
    "Ciena Corporation";
  contact
    "Web URL: http://www.ciena.com/
     Postal:  7035 Ridge Road
     Hanover, Maryland 21076
     U.S.A.
     Phone:   +1 800-921-1144
     Fax:    Inventory +1 410-694-5750";
  description
    "This modules describes Ciena's photonic PM object.";

  revision 2021-11-22 {
    description
      "Initial revision.";
  }

  container cienaRlsInventoryPmMIB {
    list rlsOpticalPmCurrentEntry {
      config false;
      key "rlsOpticalPmCurrentResource";
      description
        "Rls Optical Recent PM Table Entry";
      leaf rlsOpticalPmCurrentResource {
        type ciena-pro:DisplayString128;
        config false;
        description
          "Pm Resource instance.";
      }
      leaf rlsOpticalPmCurrentStartDateTime {
        type ciena-pro:DateTime;
        config false;
        description
          "Pm Resource Start Date/Time.";
      }
      leaf rlsOpticalPmCurrentRetrievalDateTime {
        type ciena-pro:DateTime;
        config false;
        description
          "Pm Resource Retrieval Date/Time.";
      }
      leaf rlsOpticalPmCurrentParentPort {
        type ciena-pro:DisplayString128;
        config false;
        description
          "Pm Resource Parent Port.";
      }
      leaf rlsOpticalPmCurrentSignalType {
        type enumeration {
          enum nmcmon {
            value 0;
          }
          enum sdmon {
            value 1;
          }
        }
        config false;
        description
          "Pm Resource Signal Type.";
      }
    }
    config false;
    list rlsOpticalPmValEntry {
      config false;
      key "rlsOpticalPmValResource rlsOpticalPmValMonType";
      description
        "Rls Optical Recent PM Val Table Entry";
      leaf rlsOpticalPmValResource {
        type ciena-pro:DisplayString128;
        config false;
        description
          "Pm Val Resource instance.";
      }
      leaf rlsOpticalPmValMonType {
        type ciena-6500r-types:PmMonType;
        config false;
        description
          "PM Val Mon Type.";
      }
      leaf rlsOpticalPmVallocation {
        type enumeration {
          enum nearEnd {
            value 0;
          }
          enum farEnd {
            value 1;
          }
        }
        config false;
        description
          "PM Val location.";
      }
      leaf rlsOpticalPmValdirection {
        type enumeration {
          enum tx {
            value 0;
          }
          enum rx {
            value 1;
          }
          enum bidirectional {
            value 2;
          }
          enum notApplicable {
            value 3;
          }
        }
        config false;
        description
          "PM Val direction.";
      }
    }
    list rlsOpticalPmCurrentMeasurementEntry {
      config false;
      key "rlsOpticalPmCurrentMeasurementResource
           rlsOpticalPmCurrentMeasurementMonType
           rlsOpticalPmCurrentMeasurementInterval";
      description
        "Rls Optical Measurement Interval PM Table Entry";
      leaf rlsOpticalPmCurrentMeasurementResource {
        type ciena-pro:DisplayString128;
        config false;
        description
          "Rls Optical PM Resource";
      }
      leaf rlsOpticalPmCurrentMeasurementMonType {
        type ciena-6500r-types:PmMonType;
        config false;
        description
          "Rls Optical PM Monitoring Type";
      }
      leaf rlsOpticalPmCurrentMeasurementInterval {
        type enumeration {
          enum untimed {
            value 0;
          }
          enum fifteenmin {
            value 1;
          }
          enum oneday {
            value 2;
          }
        }
        config false;
        description
          "PM Measurement Interval";
      }
      leaf rlsOpticalPmCurrentMeasurementPower {
        type ciena-pro:DisplayString32;
        config false;
        description
          "Rls Optical PM MEasurement Power value (in dB)";
      }
      leaf rlsOpticalPmCurrentMeasurementValidity {
        type enumeration {
          enum notAvailable {
            value 0;
          }
          enum complete {
            value 1;
          }
          enum partial {
            value 2;
          }
          enum suspect {
            value 3;
          }
        }
        config false;
        description
          "Rls Optical PM validity of power data";
      }
      leaf rlsOpticalPmCurrentMeasurementDateAndTime {
        type ciena-pro:DateTime;
        config false;
        description
          "Rls Optical PM Data and Time of the Measurement";
      }
    }
    list rlsOpticalPmCurrentSdmonMeasurementEntry {
      config false;
      key "rlsOpticalPmCurrentSdmonMeasurementResource
           rlsOpticalPmCurrentSdmonMeasurementMonType
           rlsOpticalPmCurrentSdmonMeasurementInterval
           rlsOpticalPmCurrentSdmonMeasurementFrequency";
      description
        "Rls Optical Sdmon Measurement PM Table Entry";
      leaf rlsOpticalPmCurrentSdmonMeasurementResource {
        type ciena-pro:DisplayString128;
        config false;
        description
          "Rls Optical Sdmon PM Resource";
      }
      leaf rlsOpticalPmCurrentSdmonMeasurementMonType {
        type ciena-6500r-types:PmMonType;
        config false;
        description
          "Rls Optical PM Monitoring Type";
      }
      leaf rlsOpticalPmCurrentSdmonMeasurementInterval {
        type enumeration {
          enum untimed {
            value 0;
          }
          enum fifteenmin {
            value 1;
          }
          enum oneday {
            value 2;
          }
        }
        config false;
        description
          "PM Measurement Interval";
      }
      leaf rlsOpticalPmCurrentSdmonMeasurementPower {
        type ciena-pro:DisplayString32;
        config false;
        description
          "Rls Optical PM MEasurement Power value (in dB)";
      }
      leaf rlsOpticalPmCurrentSdmonMeasurementFrequency {
        type ciena-pro:DisplayString128;
        config false;
        description
          "Center frequency";
      }
    }
    list rlsOpticalPmCurrentNmcmonMeasurementEntry {
      config false;
      key "rlsOpticalPmCurrentNmcmonMeasurementResource
           rlsOpticalPmCurrentNmcmonMeasurementMonType
           rlsOpticalPmCurrentNmcmonMeasurementInterval
           rlsOpticalPmCurrentNmcmonMeasurementCenterFreq";
      description
        "Rls Optical Nmcmon Measurement PM Table Entry";
      leaf rlsOpticalPmCurrentNmcmonMeasurementResource {
        type ciena-pro:DisplayString128;
        config false;
        description
          "Rls Optical Nmcmon PM Resource";
      }
      leaf rlsOpticalPmCurrentNmcmonMeasurementMonType {
        type ciena-6500r-types:PmMonType;
        config false;
        description
          "Rls Optical PM Monitoring Type";
      }
      leaf rlsOpticalPmCurrentNmcmonMeasurementInterval {
        type enumeration {
          enum untimed {
            value 0;
          }
          enum fifteenmin {
            value 1;
          }
          enum oneday {
            value 2;
          }
        }
        config false;
        description
          "PM Measurement Interval";
      }
      leaf rlsOpticalPmCurrentNmcmonMeasurementPower {
        type ciena-pro:DisplayString32;
        config false;
        description
          "Rls Optical PM MEasurement Power value (in dB)";
      }
      leaf rlsOpticalPmCurrentNmcmonMeasurementCenterFreq {
        type ciena-pro:DisplayString128;
        config false;
        description
          "Center frequency";
      }
      leaf rlsOpticalPmCurrentNmcmonMeasurementSpectralWidth {
        type ciena-pro:DisplayString128;
        config false;
        description
          "Nmcmon Spectral Width";
      }
      leaf rlsOpticalPmCurrentNmcmonMeasurementExpectedPower {
        type ciena-pro:DisplayString32;
        config false;
        description
          "Measurement Expected Power";
      }
    }
    list rlsOpticalPmHistoricalMeasurementEntry {
      config false;
      key "rlsOpticalPmHistoricalMeasurementResource
           rlsOpticalPmHistoricalMeasurementMonType
           rlsOpticalPmHistoricalMeasurementInterval
           rlsOpticalPmHistoricalMeasurementIndex";
      description
        "Rls Optical Nmcmon Measurement PM Table Entry";
      leaf rlsOpticalPmHistoricalMeasurementResource {
        type ciena-pro:DisplayString128;
        config false;
        description
          "Rls Optical Nmcmon PM Resource";
      }
      leaf rlsOpticalPmHistoricalMeasurementMonType {
        type ciena-6500r-types:PmMonType;
        config false;
        description
          "Rls Optical PM Monitoring Type";
      }
      leaf rlsOpticalPmHistoricalMeasurementInterval {
        type enumeration {
          enum untimed {
            value 0;
          }
          enum fifteenmin {
            value 1;
          }
          enum oneday {
            value 2;
          }
        }
        config false;
        description
          "PM Measurement Interval";
      }
      leaf rlsOpticalPmHistoricalMeasurementPower {
        type ciena-pro:DisplayString32;
        config false;
        description
          "Rls Optical PM MEasurement Power value (in dB)";
      }
      leaf rlsOpticalPmHistoricalMeasurementIndex {
        type int32 {
          range "1..255";
        }
        config false;
        description
          "bin Index";
      }
      leaf rlsOpticalPmHistoricalMeasurementUpdateTime {
        type ciena-pro:DateTime;
        config false;
        description
          "Measurement Update Time";
      }
      leaf rlsOpticalPmHistoricalMeasurementCompletionTime {
        type ciena-pro:DateTime;
        config false;
        description
          "Measurement Completion Time";
      }
    }
  }
}
