module CIENA-PRO-SOFTWARE-MIB {
  namespace "urn:ietf:params:xml:ns:yang:smiv2:CIENA-PRO-SOFTWARE-MIB";
  prefix ciena-pro-software;

  import CIENA-PRO-TYPES-MIB {
    prefix ciena-pro;
  }
  import CIENA-SMI {
    prefix ciena-smi;
  }

  organization
    "Ciena Corporation";
  contact
    "Web: http://www.ciena.com
     Postal:   7035 Ridge Road
               Hanover, Maryland 21076
               U.S.A
     Phone:    +1 800-921-1144
     Fax:      +1 410-694-5750";
  description
    "This module defines software upgrade support for Ciena Platform's.";

  revision 2020-10-01 {
    description
      "Initial Revision.";
  }

  typedef UpgradeOpState {
    type enumeration {
      enum unknown {
        value 0;
      }
      enum idle {
        value 1;
      }
      enum loadInProgress {
        value 2;
      }
      enum loadComplete {
        value 3;
      }
      enum loadFailed {
        value 4;
      }
      enum invokeInProgress {
        value 5;
      }
      enum invokeComplete {
        value 6;
      }
      enum invokeFailed {
        value 7;
      }
      enum installationInProgress {
        value 8;
      }
      enum installationComplete {
        value 9;
      }
      enum installationFailed {
        value 10;
      }
      enum commitInProgress {
        value 11;
      }
      enum commitComplete {
        value 12;
      }
      enum commitFailed {
        value 13;
      }
      enum cancelInProgress {
        value 14;
      }
      enum cancelComplete {
        value 15;
      }
      enum cancelFailed {
        value 16;
      }
      enum deleteInProgress {
        value 17;
      }
      enum deleteComplete {
        value 18;
      }
      enum deleteFailed {
        value 19;
      }
      enum automaticUpgradeInProgress {
        value 20;
      }
      enum automaticUpgradeComplete {
        value 21;
      }
      enum automaticUpgradeFailed {
        value 22;
      }
      enum moduleColdRestartRequired {
        value 23;
      }
      enum componentUpgradeInProgress {
        value 24;
      }
      enum componentUpgradeComplete {
        value 25;
      }
      enum componentUpgradeFailed {
        value 26;
      }
      enum deliveryInProgress {
        value 27;
      }
      enum deliveryComplete {
        value 28;
      }
      enum deliveryFailed {
        value 29;
      }
    }
    description
      "Software upgrade operational state.";
  }

  typedef UpgradeOperation {
    type enumeration {
      enum unknown {
        value 0;
      }
      enum none {
        value 1;
      }
      enum softwareInstall {
        value 2;
      }
      enum softwareDeliver {
        value 3;
      }
      enum softwareLoad {
        value 4;
      }
      enum softwareActivate {
        value 5;
      }
      enum softwareCommit {
        value 6;
      }
      enum softwareCancel {
        value 7;
      }
      enum softwareDelete {
        value 8;
      }
      enum autoUpgrade {
        value 9;
      }
    }
    description
      "Software upgrade operation";
  }

  typedef OperationResultType {
    type enumeration {
      enum ok {
        value 0;
      }
      enum failed {
        value 1;
      }
      enum unknownError {
        value 2;
      }
      enum timeout {
        value 3;
      }
      enum packageDeliveryFailure {
        value 4;
      }
      enum packageValidationFailure {
        value 5;
      }
      enum insufficientDiskSpace {
        value 6;
      }
      enum packageExtractionFailure {
        value 7;
      }
      enum systemError {
        value 8;
      }
      enum dependentServiceError {
        value 9;
      }
      enum packageInformationUnavailable {
        value 10;
      }
      enum upgradeVersionUnknown {
        value 11;
      }
      enum authenticationFailure {
        value 12;
      }
      enum fileNotFound {
        value 13;
      }
      enum fileTransferFailure {
        value 14;
      }
      enum invalidUri {
        value 15;
      }
      enum invalidState {
        value 16;
      }
      enum dataConversionFailure {
        value 17;
      }
      enum licenseCheckFailure {
        value 18;
      }
    }
    description
      "Software upgrade result";
  }

  container cienaProSoftware {
    leaf cienaProSoftwareUpgradeOperationalState {
      type ciena-pro-software:UpgradeOpState;
      config false;
      description
        "Current software manager state.
         Examples: <op>-in-progress, <op>-complete, <op>-failed or Idle.";
    }
    leaf cienaProSoftwareEntityReportedState {
      type ciena-pro-software:UpgradeOpState;
      config false;
      description
        "Current state reported by the managed upgrade entity.
         Examples: <op>-in-progress, <op>-complete, <op>-failed or Idle.";
    }
    leaf cienaProSoftwareOperationInProgress {
      type ciena-pro-software:UpgradeOperation;
      config false;
      description
        "Current software manager operation in progress, if applicable.";
    }
    leaf cienaProSoftwareOperationStartTimestamp {
      type ciena-pro:DateTime;
      config false;
      description
        "Timestamp when the current software manager operation in progress started.
         (Not supported in this software release version).";
    }
    leaf cienaProSoftwareLastOperation {
      type ciena-pro-software:UpgradeOperation;
      config false;
      description
        "Timestamp when the current software manager operation in progress started.
         (Not supported in this software release version).";
    }
    leaf cienaProSoftwareLastOperationResult {
      type ciena-pro-software:OperationResultType;
      config false;
      description
        "Result of the last completed software manager operation.";
    }
    leaf cienaProSoftwareLastOperationResultStr {
      type binary;
      config false;
      description
        "Result description details of the last completed software manager operation.";
    }
    leaf cienaProSoftwareLastOperationStartTimestamp {
      type ciena-pro:DateTime;
      config false;
      description
        "Timestamp when the Timestamp when the last software manager operation had started.";
    }
    leaf cienaProSoftwareLastOperationEndTimestamp {
      type ciena-pro:DateTime;
      config false;
      description
        "Timestamp when the last software manager operation completed.";
    }
    leaf cienaProSoftwareCommittedVersion {
      type binary;
      config false;
      description
        "Last successfully upgraded software release version.
         Format: RLS-xx.yy.zz.bbbb.";
    }
    leaf cienaProSoftwareActiveVersion {
      type binary;
      config false;
      description
        "Target software release version which was activated by an upgrade.
         UNKNOWN implies an upgrade is required.
         Format: RLS-xx.yy.zz.bbbb.";
    }
    leaf cienaProSoftwareUpgradeToVersion {
      type binary;
      config false;
      description
        "Target software release version of an in-progress upgrade.
         Format: RLS-xx.yy.zz.bbbb.";
    }
    leaf cienaProSoftwareRunningVersion {
      type binary;
      config false;
      description
        "Actual software release version that is currently running
         and is expected to match active-version after an upgrade is completed.
         Format: RLS-xx.yy.zz.bbbb.";
    }
  }
}
