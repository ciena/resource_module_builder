module CIENA-6500R-TYPES-MIB {
  namespace "urn:ietf:params:xml:ns:yang:smiv2:CIENA-6500R-TYPES-MIB";
  prefix ciena-6500r;

  import CIENA-SMI {
    prefix ciena-smi;
  }
  import ietf-yang-types {
    prefix yang;
  }

  organization
    "Ciena Corporation";
  contact
    "Web: http://www.ciena.com
     Postal:   7035 Ridge Road
               Hanover, Maryland 21076
               U.S.A
     Phone:    +1 800-921-1144
     Fax:      +1 410-694-5750";
  description
    "This modules describes Ciena's release object for the 6500r platform.";

  revision 2023-03-09 {
    description
      "Fix PmMonType enum.";
  }
  revision 2022-01-10 {
    description
      "[Revision added by libsmi due to a LAST-UPDATED clause.]";
  }
  revision 2022-01-10 {
    description
      "Add definitions for PhysicalIndex and PhysicalClass.";
  }
  revision 2020-10-01 {
    description
      "Initial Revision.";
  }

  typedef PecCode {
    type string {
      length "1..16";
      pattern '.{1,16}';
    }
    description
      "A UTF-8 string with a max length of 16 characters";
  }

  typedef MeansurementType {
    type enumeration {
      enum measured {
        value 0;
      }
      enum estimated {
        value 1;
      }
      enum unknown {
        value 2;
      }
    }
    description
      "Flag to indicate if current power is measured, estimated or unknown.";
  }

  typedef BandOccupancy {
    type bits {
      bit bandC {
        position 0;
      }
      bit bandL {
        position 1;
      }
      bit osc {
        position 2;
      }
      bit telmetry {
        position 3;
      }
      bit total {
        position 4;
      }
    }
    description
      "Band Type";
  }

  typedef PowerEnum {
    type enumeration {
      enum ac {
        value 0;
      }
      enum dc {
        value 1;
      }
    }
    description
      "Power supply type";
  }

  typedef RamEnum {
    type enumeration {
      enum size16G {
        value 0;
      }
      enum size32G {
        value 1;
      }
    }
    description
      "";
  }

  typedef RestartType {
    type enumeration {
      enum warm {
        value 1;
      }
      enum cold {
        value 2;
      }
    }
    description
      "Restart type";
  }

  typedef OrlState {
    type enumeration {
      enum valid {
        value 1;
      }
      enum outputOORL {
        value 2;
      }
      enum reflectOORL {
        value 3;
      }
      enum reflectOORH {
        value 4;
      }
      enum hssf {
        value 5;
      }
      enum shutoff {
        value 6;
      }
      enum unknown {
        value 7;
      }
      enum notApplicable {
        value 8;
      }
    }
    description
      "The ORL State.";
  }

  typedef AdminState {
    type enumeration {
      enum enabled {
        value 1;
      }
      enum disabled {
        value 2;
      }
      enum unassigned {
        value 3;
      }
    }
    description
      "Identify the administrative state";
  }

  typedef FixedX1000 {
    type int32;
    description
      "This represents a fixed point number with a
       3 digits after the decimal point. However,
       because SNMP does not support floats, we multiply
       the number by 1000 before SNMP gets it. To obtain
       actual value, divide by 1000 and keep the remainder
       as the value after the decimal point. For example,
       the number 5.700 would be represented using this
       type as 5700";
  }

  typedef Frequency {
    type ciena-6500r:FixedX1000 {
      range "0..20000000";
    }
    description
      "Center frequency ";
  }

  typedef PmMonType {
    type enumeration {
      enum opticalPower {
        value 0;
      }
      enum opticalPowerMin {
        value 1;
      }
      enum opticalPowerMax {
        value 2;
      }
      enum opticalPowerAvg {
        value 3;
      }
      enum opticalPowerOutput {
        value 4;
      }
      enum opticalPowerOutputMin {
        value 5;
      }
      enum opticalPowerOutputMax {
        value 6;
      }
      enum opticalPowerOutputAvg {
        value 7;
      }
      enum opticalPowerInput {
        value 8;
      }
      enum opticalPowerInputMin {
        value 9;
      }
      enum opticalPowerInputMax {
        value 10;
      }
      enum opticalPowerInputAvg {
        value 11;
      }
      enum opticalPowerOutputOSC {
        value 12;
      }
      enum opticalPowerOutputOSCMin {
        value 13;
      }
      enum opticalPowerOutputOSCMax {
        value 14;
      }
      enum opticalPowerOutputOSCAvg {
        value 15;
      }
      enum opticalPowerInputOSC {
        value 16;
      }
      enum opticalPowerInputOSCMin {
        value 17;
      }
      enum opticalPowerInputOSCMax {
        value 18;
      }
      enum opticalPowerInputOSCAvg {
        value 19;
      }
      enum opticalReturnLoss {
        value 20;
      }
      enum opticalReturnLossMin {
        value 21;
      }
      enum opticalReturnLossMax {
        value 22;
      }
      enum opticalReturnLossAvg {
        value 23;
      }
      enum inputOpticalReturnLoss {
        value 24;
      }
      enum inputOpticalReturnLossMin {
        value 25;
      }
      enum inputOpticalReturnLossMax {
        value 26;
      }
      enum inputOpticalReturnLossAvg {
        value 27;
      }
      enum outputOpticalReturnLoss {
        value 28;
      }
      enum outputOpticalReturnLossMin {
        value 29;
      }
      enum outputOpticalReturnLossMax {
        value 30;
      }
      enum outputOpticalReturnLossAvg {
        value 31;
      }
      enum line-loss-measurement {
        value 32;
      }
      enum line-loss-measurement-min {
        value 33;
      }
      enum line-loss-measurement-max {
        value 34;
      }
      enum line-loss-measurement-avg {
        value 35;
      }
      enum line-loss-margin {
        value 36;
      }
      enum line-loss-margin-min {
        value 37;
      }
      enum line-loss-margin-max {
        value 38;
      }
      enum line-loss-margin-avg {
        value 39;
      }
      enum express-loss-measurement {
        value 40;
      }
      enum express-loss-measurement-min {
        value 41;
      }
      enum express-loss-measurement-max {
        value 42;
      }
      enum express-loss-measurement-avg {
        value 43;
      }
      enum express-loss-margin {
        value 44;
      }
      enum express-loss-margin-min {
        value 45;
      }
      enum express-loss-margin-max {
        value 46;
      }
      enum express-loss-margin-avg {
        value 47;
      }
      enum target-loss {
        value 48;
      }
      enum target-loss-min {
        value 49;
      }
      enum target-loss-max {
        value 50;
      }
      enum target-loss-avg {
        value 51;
      }
      enum gain {
        value 52;
      }
      enum gain-min {
        value 53;
      }
      enum gain-max {
        value 54;
      }
      enum gain-avg {
        value 55;
      }
      enum gainTilt {
        value 56;
      }
      enum gain-tilt {
        value 57;
      }
      enum gain-tilt-min {
        value 58;
      }
      enum gain-tilt-max {
        value 59;
      }
      enum gain-tilt-avg {
        value 60;
      }
      enum link {
        value 61;
      }
      enum opm {
        value 62;
      }
      enum min-allowed-gain {
        value 63;
      }
      enum max-allowed-gain {
        value 64;
      }
      enum calculatedOSCLoss {
        value 98;
      }
      enum calculatedOSCLossMin {
        value 99;
      }
      enum calculatedOSCLossMax {
        value 100;
      }
      enum calculatedOSCLossAvg {
        value 101;
      }
      enum measuredOSCLoss {
        value 102;
      }
      enum measuredOSCLossMin {
        value 103;
      }
      enum measuredOSCLossMax {
        value 104;
      }
      enum measuredOSCLossAvg {
        value 105;
      }
      enum calculatedTotalLoss {
        value 106;
      }
      enum calculatedTotalLossMin {
        value 107;
      }
      enum calculatedTotalLossMax {
        value 108;
      }
      enum calculatedTotalLossAvg {
        value 109;
      }
      enum measuredTotalLoss {
        value 110;
      }
      enum measuredTotalLossMin {
        value 111;
      }
      enum measuredTotalLossMax {
        value 112;
      }
      enum measuredTotalLossAvg {
        value 113;
      }
    }
    description
      "PM Monitoring Type";
  }

  typedef PhysicalIndex {
    type int32 {
      range "1..2147483647";
    }
    description
      "Physical Index of the Entity";
  }

  typedef PhysicalClass {
    type enumeration {
      enum backplane {
        value 1;
      }
      enum access-panel {
        value 2;
      }
      enum ctm {
        value 3;
      }
      enum fan {
        value 4;
      }
      enum power {
        value 5;
      }
      enum i2c {
        value 6;
      }
      enum passive {
        value 7;
      }
      enum sfp {
        value 8;
      }
      enum sfpplus {
        value 9;
      }
      enum cfp {
        value 10;
      }
      enum cfp2 {
        value 11;
      }
      enum xfp {
        value 12;
      }
      enum qsfp {
        value 13;
      }
      enum qsfp28 {
        value 14;
      }
      enum ctm-front-panel {
        value 15;
      }
      enum backplane-300mm {
        value 16;
      }
      enum chassis {
        value 17;
      }
    }
    description
      "Physical Class of the Entity.";
  }
}
