module ciena-ddm-netconf {
  namespace "urn:ciena:params:xml:ns:yang:ciena-ddm-netconf";
  prefix ddm-netconf;

  import ciena-ddy-msg {
    prefix ciena-ddy-msg;
  }

  organization
    "Ciena";
  contact
    "Web URL: http://www.ciena.com/
     Postal:  7035 Ridge Road
             Hanover, Maryland 21076
             U.S.A.
     Phone:   +1 800-921-1144
     Fax:     +1 410-694-5750";
  description
    "Options for Netconf messaging protocol.";

  revision 2019-10-23 {
    description
      "Added username and password to netconf-options for client.";
  }
  revision 2015-04-07 {
    description
      "Initial revision.";
  }

  identity netconf {
    base ciena-ddy-msg:ddm-protocols;
    description
      "Netconf Client/Server";
  }

  augment "/ciena-ddy-msg:domains/ciena-ddy-msg:protocols" {
    when "ciena-ddy-msg:type = 'ciena-ddy-msg:netconf'";
    container netconf-options {
      leaf ipport {
        type string;
        description
          "IP and Port in the URL of the destination.";
      }
      leaf timeout {
        type uint32;
        description
          "Timeout";
      }
      leaf username {
        type string;
        description
          "Username";
      }
      leaf password {
        type string;
        description
          "Password";
      }
    }
  }
}
