module ciena-pro-grpc {
  namespace "urn:ciena:params:xml:ns:yang:ciena-pro-grpc";
  prefix ciena-pro-grpc;

  import ciena-common-version {
    prefix version;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's gRPC model";

  revision 2021-05-04 {
    version:version "version" {
      version:string "1.1.0";
    }
    description
      "Add mutual-auth leaf.";
  }
  revision 2020-09-03 {
    version:version "version" {
      version:string "1.0.0";
    }
    description
      "Initial revision";
  }

  container grpc {
    container server {
      leaf state {
        type enumeration {
          enum "disable" {
            value 0;
          }
          enum "enable" {
            value 1;
          }
        }
        mandatory true;
        description
          "Flag to enable or disable gRPC interface";
      }

      leaf mutual-auth {
        type enumeration {
          enum "disable" {
            value 0;
          }
          enum "enable" {
            value 1;
          }
        }
        mandatory true;
        description
          "Flag to enable or disable mutual authentication for gRPC interface";
      }
    }
  }

  rpc kill-session {
    description
      "Force the termination of a gRPC session.";
    input {
      leaf session-id {
        type uint64;
        mandatory true;
        description
          "Particular session to kill.";
      }
    }
  }
}
