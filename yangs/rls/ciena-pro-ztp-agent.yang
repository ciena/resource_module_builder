module ciena-pro-ztp-agent {
  namespace "urn:ciena:params:xml:ns:yang:ciena-pro-ztp-agent";
  prefix ciena-pro-ztp-agent;

  import ciena-pro-ztp-bootfile {
    prefix ciena-pro-ztp-bootfile;
  }
  import ciena-common-version {
    prefix ciena-common-version;
  }
  import ciena-pro-ztp {
    prefix ciena-pro-ztp;
  }

  organization
    "Ciena Corporation";
  contact
    "Web URL: http://www.ciena.com/";
  description
    "This module defines provisioning interface for zero
     touch provisioning for Ciena's 6500r Platform.";

  revision 2022-02-17 {
    description
      "Add ztp-license output";
    ciena-common-version:string "1.0.3";
  }
  revision 2022-01-07 {
    description
      "Add ztp-license-compliant";
    ciena-common-version:string "1.0.2";
  }
  revision 2021-10-27 {
    description
      "Add ztp-license RPC";
    ciena-common-version:string "1.0.1";
  }
  revision 2019-10-08 {
    description
      "Initial version";
    ciena-common-version:string "1.0.0";
  }

  rpc config {
    input {
      uses ciena-pro-ztp-bootfile:CienaCommandFile;
    }
  }

  rpc script {
    input {
      uses ciena-pro-ztp-bootfile:CienaCommandFile;
    }
  }

  rpc upgrade {
    input {
      uses ciena-pro-ztp-bootfile:CienaCommandFile;
    }
  }

  rpc ztp-license-compliant {
    output {
      leaf return-code {
        type uint32;
      }
      leaf return-string {
        type string;
        description
          "License return code description";
      }
    }
  }

  rpc ztp-license {
    input {
      uses ciena-pro-ztp-bootfile:CienaCommandFile;
    }
    output {
      leaf return-code {
        type uint32;
      }
      leaf return-string {
        type string;
        description
          "License return code description";
      }
    }
  }

  rpc query {
    output {
      leaf upgrade-state {
        type enumeration {
          enum progress {
            description
              "upgrade in progress";
          }
          enum success {
            description
              "upgrade completed with success";
          }
          enum failed {
            description
              "upgrade completed with failure";
          }
        }
      }
    }
  }
}
