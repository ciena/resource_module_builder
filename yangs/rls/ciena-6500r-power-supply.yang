module ciena-6500r-power-supply {
  yang-version 1.1;
  namespace "urn:ciena:params:xml:ns:yang:ciena-6500r-power-supply";
  prefix power-supply;

  import ciena-6500r-types {
    prefix ciena-6500r-types;
  }

  import ciena-common-version {
    prefix version;
  }

  import ciena-pro-power-supply {
    prefix ciena-pro-power-supply;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's power object";

  revision 2021-05-11 {
    version:version "version" {
      version:string "1.0.0";
    }
    description
      "Initial version";
  }

  grouping ciena-6500r-power-supply-mount {
    container power-supplies {
      list power-supply {
        key "name";
        uses ciena-pro-power-supply:power-supply;

        uses ciena-6500r-types:admin-state;
      }
    }
  }

  grouping ciena-6500r-power-supply-mount-actions;

  uses ciena-6500r-power-supply-mount;
}
