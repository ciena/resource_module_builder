module ciena-common-service-broker-private {
  namespace "urn:ciena:params:xml:ns:yang:ciena-service-broker-private";
  prefix service-broker-private;

  import ciena-common-version {
    prefix version;
  }
  import ciena-common-recording-agent {
    prefix ciena-common-recording-agent;
  }

  organization
    "Ciena Corporation";
  contact
    "Web URL: http://www.ciena.com/
     Postal:  7035 Ridge Road
              Hanover, Maryland 21076
              U.S.A.
     Phone:   +1 800-921-1144
     Fax:     +1 410-694-5750";
  description
    "Service Level locking with Transactions.";

  revision 2024-01-08 {
    description
      "Initial Revision";
    version:version "version" {
      version:string "1.0.0";
    }
  }

  identity service-broker-stats {
    base ciena-common-recording-agent:recording-type;
    description
      "Recording type to record service-broker statistics when enabled
       by setting the return-stats attribute to true in broker-options";
  }
}
