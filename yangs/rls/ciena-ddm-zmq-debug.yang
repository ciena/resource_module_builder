module ciena-ddm-zmq-debug {
  namespace "urn:ciena:params:xml:ns:yang:ciena-ddm-zmq-debug";
  prefix ddm-zmq;

  import ciena-common-version {
    prefix ciena-common-version;
  }

  organization
    "Ciena Corporation";
  contact
    "Web URL: http://www.ciena.com/
     Postal:  7035 Ridge Road
             Hanover, Maryland 21076
             U.S.A.
     Phone:   +1 800-921-1144
     Fax:     +1 410-694-5750";
  description
    "Yang file for zmq debug related options";

  revision 2021-03-01 {
    description
      "Initial revision";
    ciena-common-version:string "0.1.0";
  }

  rpc reset-zmq-msg-stats {
    description
      "Reset ZMQ message statistics";
  }
}
