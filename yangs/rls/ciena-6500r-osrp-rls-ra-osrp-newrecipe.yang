module ciena-6500r-osrp-rls-ra-osrp-newrecipe {
  namespace "urn:ciena:params:xml:ns:yang:ciena-6500r-osrp-rls-ra-osrp-newrecipe";
  prefix osrp-newrecipe;

  import ietf-inet-types {
    prefix ietf;
  }
  import ciena-6500r-types {
    prefix ciena-6500r-types;
  }
  import ciena-6500r-osrp-rls-ra-types {
    prefix osrp-rls-ra-types;
  }
  import ciena-common-version {
    prefix ciena-common-version;
  }

  organization
    "Ciena Corporation";
  contact
    "Web URL: http://www.ciena.com
     Postal: Ciena India Pvt. Ltd.
     Sector 32, Plot 14,
     Gurgaon 122001,
     Haryana, India";
  description
    "This module describes Ciena's osrp-rls-ra - osrp-recipe data for the osrp";

  revision 2022-07-11 {
    description
      "added field 'controller-unsupported'.";
    ciena-common-version:string "1.3.0";
  }
  revision 2021-01-09 {
    description
      "Node-id field type changed.";
    ciena-common-version:string "1.2.1";
  }
  revision 2021-01-05 {
    description
      "Node-id length extended.";
    ciena-common-version:string "1.2.0";
  }
  revision 2020-07-15 {
    description
      "Added container 'osrp-grouping' for PFG grouping data.";
    ciena-common-version:string "1.1.0";
  }
  revision 2020-05-11 {
    description
      "Added shelf ip-address for inter-osrp comms.";
    ciena-common-version:string "1.0.1";
  }
  revision 2019-10-28 {
    description
      "Renamed module name from recipe to osrp-recipe and fixed indentation.";
    ciena-common-version:string "1.0.0";
  }
  revision 2019-09-20 {
    description
      "Initial revision.";
  }

  list osrp-newrecipe {
    key "pfg-name";
    leaf pfg-name {
      type string;
      description
        "Name of associated functional-group.";
      mandatory true;
    }
    leaf osrp-node-name {
      type string;
      description
        "OSRP node name that is unique across the OSRP network.";
      mandatory true;
    }
    leaf osrp-node-id {
      type osrp-rls-ra-types:node-id-hex-type;
      description
        "Unique node-id of osrp-node across network.";
      mandatory true;
    }
    leaf functional-type {
      type osrp-rls-ra-types:osrp-pfg-type;
      description
        "Type of Pfg i.e. channel, section or line.";
    }
    leaf controller-unsupported {
      type boolean;
      description
        "Specifies if controller is not supported.";
    }
    leaf lics-from-nameserver-port {
      type osrp-rls-ra-types:port-num;
      description
        "Lics From Nameserver Port";
      mandatory true;
    }
    leaf lics-msg-base-port {
      type osrp-rls-ra-types:port-num;
      description
        "OSRP Lics msg base port which can bind upto 20 subsequent ports";
      mandatory true;
    }
    leaf lics-to-nameserver-port {
      type osrp-rls-ra-types:port-num;
      description
        "Lics To Nameserver Port";
      mandatory true;
    }
    leaf oob-comm-port {
      type osrp-rls-ra-types:oob-port-num;
      description
        "OOB Comm Port";
      mandatory true;
    }
    leaf osrp-debug-port {
      type osrp-rls-ra-types:port-num;
      description
        "OSRP debug Port";
      mandatory true;
    }
    container osrp-grouping {
      description
        "OSRP Grouping related data.";
      leaf grouping-ownership {
        type osrp-rls-ra-types:grouping-ownership;
        description
          "Specifies the type of ownership in the PFG grouping.";
      }
      leaf grouping-owner-name {
        type string;
        description
          "Specifies the grouping owner name if the current instance is a grouping member.";
      }
      leaf-list grouping-member-name {
        type string;
        description
          "Specifies the grouping members name in the list if the current instance is a grouping owner.";
      }
      leaf-list associated-slot {
        type ciena-6500r-types:object-name;
        description
          "List of the slots to which this osrp-recipe's PFG is associated to.";
      }
    }
    leaf rest-port {
      type osrp-rls-ra-types:port-num;
      description
        "OSRP Rest Port";
      mandatory true;
    }
    leaf ip-address {
      type ietf:ip-address;
      description
        "Shelf IP address";
      mandatory true;
    }
    leaf zmq-port {
      type osrp-rls-ra-types:port-num;
      description
        "OSRP ZMQ port";
      mandatory true;
    }
    leaf zmq-pub-port {
      type osrp-rls-ra-types:port-num;
      description
        "OSRP ZMQ Public Port";
      mandatory true;
    }
  }
}
