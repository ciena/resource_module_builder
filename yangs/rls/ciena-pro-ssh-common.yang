module ciena-pro-ssh-common {
  namespace "urn:ciena:params:xml:ns:yang:ciena-pro-ssh-common";
  prefix ciena-pro-ssh-common;

  import ciena-pro-types {
    prefix ciena-pro-types;
  }

  import ciena-common-version {
    prefix ciena-common-version;
  }

  organization
    "Ciena Corporation";
  contact
    "Web URL: http://www.ciena.com/
     Postal:  7035 Ridge Road
             Hanover, Maryland 21076
             U.S.A.
     Phone:   +1 800-921-1144
     Fax:     +1 410-694-5750";
  description
    "This module contains a collection of YANG type definitions for
     SSH.";

  revision 2020-10-22 {
    ciena-common-version:string "0.1.0";
    description
      "Make model platform independent";
  }
  revision 2018-10-23 {
    description
      "Initial version, based on OneOS, Waveserver and IETF Experimental modules";
  }

  feature ssh-ecc {
    description
      "Elliptic Curve Cryptography is supported for SSH.";
  }

  feature ssh-dh-group-exchange {
    description
      "Diffie-Hellman Group Exchange is supported for SSH.";
  }

  feature ssh-ctr {
    description
      "SDCTR encryption mode is supported for SSH.";
  }

  feature ssh-sha2 {
    description
      "The SHA2 family of cryptographic hash functions is
       supported for SSH.";
  }

  typedef kex-algorithm {
    type enumeration {
      enum "curve25519-sha256" {
        description
          "The curve25519-sha256 algorithm.";
      }
      enum "curve25519-sha256-at-libssh-dot-org" {
        description
          "The curve25519-sha256@libssh.org algorithm.";
      }
      enum "ecdh-sha2-nistp256" {
        description
          "Elliptic Curve Diffie-Hellman (ECDH) key exchange using the
           nistp256 curve and the SHA2 family of hashing algorithms.";
      }
      enum "ecdh-sha2-nistp384" {
        description
          "Elliptic Curve Diffie-Hellman (ECDH) key exchange using the
           nistp384 curve and the SHA2 family of hashing algorithms.";
      }
      enum "ecdh-sha2-nistp521" {
        description
          "Elliptic Curve Diffie-Hellman (ECDH) key exchange using the
           nistp521 curve and the SHA2 family of hashing algorithms.";
      }
      enum "diffie-hellman-group-exchange-sha256" {
        description
          "Diffie-Hellman Group and Key Exchange with SHA-256 as HASH.";
      }
      enum "diffie-hellman-group-exchange-sha1" {
        description
          "Diffie-Hellman Group and Key Exchange with SHA-1 as HASH.";
      }
      enum "diffie-hellman-group14-sha1" {
        description
          "Diffie-Hellman key exchange with SHA-1 as HASH and
           Oakley Group 14 (2048-bit MODP Group).";
      }
      enum "diffie-hellman-group14-sha256" {
        description
          "Diffie-Hellman key exchange with SHA-256 as HASH and
           Oakley Group 14 (2048-bit MODP Group).";
      }
      enum "diffie-hellman-group1-sha1" {
        description
          "The diffie-hellman-group1-sha1 algorithm.";
      }
      enum "rsa2048-sha256" {
        description
          "rsa2048 kex algorith";
      }
    }
    description
      "List of kex algorithms.";
  }

  typedef encryption-algorithm {
    type enumeration {
      enum "aes128-ctr" {
        description
          "The aes128-ctr algorithm.";
      }
      enum "aes128-cbc" {
        description
          "The aes128-cbc algorithm.";
      }
      enum "aes192-ctr" {
        description
          "The aes192-ctr algorithm.";
      }
      enum "aes192-cbc" {
        description
          "The aes192-cbc algorithm.";
      }
      enum "aes256-ctr" {
        description
          "The aes256-ctr algorithm.";
      }
      enum "aes256-cbc" {
        description
          "The aes256-cbc algorithm.";
      }
      enum "aes128-gcm-at-openssh-dot-com" {
        description
          "The aes128-gcm@openssh.com algorithm.";
      }
      enum "aes256-gcm-at-openssh-dot-com" {
        description
          "The aes256-gcm@openssh.com algorithm.";
      }
      enum "AEAD_AES_128_GCM" {
        description
          "The aes128-gcm algorithm.";
      }
      enum "AEAD_AES_256_GCM" {
        description
          "The aes256-gcm algorithm.";
      }
      enum "chacha20-poly1305-at-openssh-dot-com" {
        description
          "The chacha20-poly1305@openssh.com algorithm.";
      }
      enum "3des-cbc" {
        description
          "The 3des-cbc algorithm.";
      }
    }
    description
      "List of encryption algorithms.";
  }

  typedef mac-algorithm {
    type enumeration {
      enum "hmac-md5-etm-at-openssh-dot-com" {
        description
          "The hmac-md5-etm@openssh.com algorithm.";
      }
      enum "hmac-sha1-etm-at-openssh-dot-com" {
        description
          "The hmac-sha1-etm@openssh.com algorithm.";
      }
      enum "hmac-sha2-256-etm-at-openssh-dot-com" {
        description
          "The hmac-sha2-256-etm@openssh.com algorithm.";
      }
      enum "hmac-sha2-512-etm-at-openssh-dot-com" {
        description
          "The hmac-sha2-512-etm@openssh.com algorithm.";
      }
      enum "hmac-ripemd160-etm-at-openssh-dot-com" {
        description
          "The hmac-ripemd160-etm@openssh.com algorithm.";
      }
      enum "hmac-ripemd160-at-openssh-dot-com" {
        description
          "The hmac-ripemd160@openssh.com algorithm.";
      }
      enum "hmac-md5" {
        description
          "The hmac-md5 algorithm.";
      }
      enum "hmac-sha1" {
        description
          "The hmac-sha1 algorithm.";
      }
      enum "hmac-sha2-256" {
        description
          "The hmac-sha2-256 algorithm.";
      }
      enum "hmac-sha2-512" {
        description
          "The hmac-sha2-512 algorithm.";
      }
      enum "hmac-ripemd160" {
        description
          "The hmac-ripemd160 algorithm.";
      }
    }
    description
      "List of mac algorithms.";
  }

  typedef pka-algorithm {
    type enumeration {
      enum "ssh-dss" {
        description
          "Digital Signature Algorithm using SHA-1 as the
           hashing algorithm.";
      }
      enum "ssh-rsa" {
        description
          "RSASSA-PKCS1-v1_5 signature scheme using SHA-1 as the
           hashing algorithm.";
      }
      enum "ssh-ed25519" {
        description
          "The ssh-ed25519 algorithm.";
      }
      enum "ecdsa-sha2-nistp256" {
        description
          "Elliptic Curve Digital Signature Algorithm (ECDSA) using the
           nistp256 curve and the SHA2 family of hashing algorithms.";
      }
      enum "ecdsa-sha2-nistp384" {
        description
          "Elliptic Curve Digital Signature Algorithm (ECDSA) using the
           nistp384 curve and the SHA2 family of hashing algorithms.";
      }
      enum "ecdsa-sha2-nistp521" {
        description
          "Elliptic Curve Digital Signature Algorithm (ECDSA) using the
           nistp521 curve and the SHA2 family of hashing algorithms.";
      }
      enum "ssh-ed25519-cert-v01-at-openssh-dot-com" {
        description
          "The ssh-ed25519 algorithm.";
      }
      enum "rsa-sha2-256" {
        description
          "The rsa-sha2-256 algorithm.";
      }
      enum "rsa-sha2-512" {
        description
          "The rsa-sha2-512 algorithm.";
      }
    }
    description
      "List of public key authentication algorithms.";
  }

  typedef ssh-key-generation-status {
    type enumeration {
      enum "invalid" {
        value 0;
        description
          "Invalid result.";
      }
      enum "generating" {
        value 1;
        description
          "The key is being generated.";
      }
      enum "generated" {
        value 2;
        description
          "The key has been generated.";
      }
      enum "failure" {
        value 3;
        description
          "The key generation failed.";
      }
    }
    description
      "The result of the SSH key generation.";
  }

  typedef ssh-host-key {
    type binary;
    description
      "The binary public key data for this SSH key, as
       specified by RFC 4253, Section 6.6, i.e.:

         string    certificate or public key format
                   identifier
         byte[n]   key/certificate data.";
    reference
      "RFC 4253: The Secure Shell (SSH) Transport Layer
                 Protocol";
  }

  grouping transport-params-grouping {
    description
      "A reusable grouping for SSH transport parameters.";
    container host-key {
      description
        "Parameters regarding host key.";
      leaf-list host-key-alg {
        type pka-algorithm;
        ordered-by user;
        description
          "Acceptable host key algorithms in order of descending
           preference.

           If this leaf-list is not configured (has zero elements)
           the acceptable host key algorithms are implementation-
           defined.";
      }
    }

    container key-exchange {
      description
        "Parameters regarding key exchange.";
      leaf-list key-exchange-alg {
        type kex-algorithm;
        min-elements 1;
        ordered-by user;
        description
          "Acceptable key exchange algorithms in order of descending
           preference.

           If this leaf-list is not configured (has zero elements)
           the acceptable key exchange algorithms are implementation
           defined.";
      }
    }

    container encryption {
      description
        "Parameters regarding encryption.";
      leaf-list encryption-alg {
        type encryption-algorithm;
        min-elements 1;
        ordered-by user;
        description
          "Acceptable encryption algorithms in order of descending
           preference.

           If this leaf-list is not configured (has zero elements)
           the acceptable encryption algorithms are implementation
           defined.";
      }
    }

    container mac {
      description
        "Parameters regarding message authentication code (MAC).";
      leaf-list mac-alg {
        type mac-algorithm;
        min-elements 1;
        ordered-by user;
        description
          "Acceptable MAC algorithms in order of descending
           preference.

           If this leaf-list is not configured (has zero elements)
           the acceptable MAC algorithms are implementation-
           defined.";
      }
    }
  }

  grouping rekey-grouping {
    description
      "A reusable grouping for SSH rekey parameters.";
    container rekey-params {
      description
        "Parameters regarding rekey thresholds";
      leaf rekey-limit {
        type enumeration {
          enum "1G" {
            description
              "Transmit/Receive 1G bytes.";
          }
          enum "2G" {
            description
              "Transmit/Receive 2G bytes.";
          }
          enum "4G" {
            description
              "Transmit/Receive 4G bytes.";
          }
          enum "500M" {
            description
              "Transmit/Receive 500M bytes.";
          }
        }
        default "1G";
        description
          "This leaf specifies the number of bytes that are
           transmitted before the session key is renegotiated.";
      }

      leaf rekey-timeout {
        type uint32 {
          range "1..3600";
        }
        default "3600";
        description
          "This leaf specifies the max time (in seconds) that
           may pass before the session key is renegotiated.";
      }

      uses ciena-pro-types:admin-state {
        description
          "This leaf specifies the administrative
           state of SSH Server rekeying.";
        refine "admin-state" {
          default "Disabled";
        }
      }
    }
  }
}
