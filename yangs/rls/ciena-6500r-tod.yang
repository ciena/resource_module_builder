module ciena-6500r-tod {
  yang-version 1.1;
  namespace "urn:ciena:params:xml:ns:yang:ciena-6500r-tod";
  prefix tod;

  import ciena-common-version {
    prefix ciena-common-version;
  }
  import ciena-common-yang {
    prefix ciena-common-yang;
  }
  import ietf-yang-types {
    prefix yang;
  }

  organization
    "Ciena Corporation";
  contact
    "Web URL: http://www.ciena.com";
  description
    "This module describes Ciena's TOD set objects for the 6500r platform";

  revision 2020-10-07 {
    description
      "6500r Release 1.0-
       First release";
  }

  rpc set-system-tod {
    input {
      leaf new-system-tod {
        type yang:date-and-time;
        description
          "New system time of day to be set";
      }
    }
    output {
      leaf result {
        type boolean;
        description
          "Display system time of day set request result";
      }
      uses ciena-common-yang:rpc-result-common;
    }
  }
}
