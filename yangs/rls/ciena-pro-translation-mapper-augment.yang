module ciena-pro-translation-mapper-augment {
  yang-version 1.1;
  namespace "urn:ciena:params:xml:ns:yang:ciena-pro-translation-mapper-augment";
  prefix mapper-augment;

  import ciena-common-yang {
    prefix common-yang;
  }
  import ciena-common-version {
    prefix version;
  }
  import ciena-pro-model-translation {
    prefix m;
  }

  organization
    "Ciena Corporation";
  contact
    "Web URL: http://www.ciena.com";
  description
    "Augmentation to add in elements to improve performance";

  revision 2023-03-01 {
    description
      "Add the errors augment against loaded models.";
  }
  revision 2022-07-15 {
    description
      "Initial revision";
    version:string "1.0.0";
  }

  augment "/m:translation-service/m:loaded-models/m:model-data/m:mapping/m:sub-tree/m:equivalents" {
    common-yang:augment-name "_eq";
    leaf ext-target {
      type common-yang:target-node;
    }
  }

  augment "/m:translation-service/m:loaded-models/m:model-data/m:mapping/m:sub-tree/m:equivalents" {
    common-yang:augment-name "_eq2";
    leaf native-target {
      type common-yang:target-node;
    }
  }

  augment "/m:translation-service/m:loaded-models/m:model-data/m:mapping/m:sub-tree/m:native-equivalents" {
    common-yang:augment-name "_neq";
    leaf nat-target {
      type common-yang:target-node;
    }
  }

  augment "/m:translation-service/m:loaded-models/m:model-data/m:mapping/m:sub-tree/m:equivalents/m:map-type/m:multiple/m:multiple" {
    common-yang:augment-name "_eq-mult";
    leaf native-target {
      type common-yang:target-node;
    }
  }

  augment "/m:translation-service/m:loaded-models/m:model-data/m:mapping/m:sub-tree/m:native-equivalents/m:map-type/m:multiple/m:multiple" {
    common-yang:augment-name "_neq-mult";
    leaf nat-target {
      type common-yang:target-node;
    }
  }

  augment "/m:translation-service/m:loaded-models/m:model-data/m:mapping/m:sub-tree/m:discriminator/m:conditions" {
    common-yang:augment-name "_cond";
    leaf target {
      type common-yang:target-node;
    }
  }

  augment "/m:translation-service/m:loaded-models/m:model-data/m:mapping/m:sub-tree/m:discriminator/m:reverse-conditions" {
    common-yang:augment-name "_rcond";
    leaf target {
      type common-yang:target-node;
    }
  }

  augment "/m:translation-service/m:loaded-models" {
    common-yang:augment-name "_err";
    container errors {
      uses common-yang:rpc-result-common;
    }
  }
}
