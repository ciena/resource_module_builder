module ciena-common-test-module-container-matches {
  namespace "urn:ciena:params:xml:ns:yang:ciena-common-test-module-container-matches";
  prefix test-module-container-matches;

  import ciena-common-yang {
    prefix ciena-common-yang;
  }

  organization
    "Ciena Corporation";
  contact
    "Web URL: http://www.ciena.com";
  description
    "Test module for testing case where container name matches the module name.";

  revision 2023-06-29 {
    description
      "Initial revision.";
  }

  container ciena-common-test-module-container-matches {
    leaf a_leaf {
      description
        "Dummy leaf.";
      type uint32;
    }
  }
}
