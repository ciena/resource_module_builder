module ciena-osrp-osrp-graph {
  namespace "urn:ciena:params:xml:ns:yang:ciena-osrp-osrp-graph";
  prefix osrp-graph;

  import ciena-osrp-types {
    prefix ciena-osrp-types;
  }
  import ietf-yang-types {
    prefix yang;
  }
  import ciena-common-version {
    prefix ciena-common-version;
  }

  organization
    "Ciena Corporation";
  contact
    "Web URL: http://www.ciena.com
     Postal: Ciena India Pvt. Ltd.
     Sector 32, Plot 14,
     Gurgaon 122001,
     Haryana, India";
  description
    "This module describes Ciena's osrp Graph object for the 6500r platform";

  revision 2020-05-15 {
    description
      "6500r-series Release 2.0
       Initial version.";
    ciena-common-version:string "1.0.0";
  }

  list osrp-graph-node {
    key "node-id";
    uses osrp-graph-node-group;
    description
      "OSRP Graph Node.";
  }
  list osrp-graph-link {
    key "from-node-id from-port";
    uses osrp-graph-link-group;
    description
      "OSRP Graph Link.";
  }

  grouping osrp-graph-node-group {
    leaf node-id {
      type ciena-osrp-types:node-id-type;
      description
        "Node id.";
      mandatory true;
    }
    leaf node-name {
      type string;
      description
        "Node name.";
      mandatory true;
    }
    leaf version {
      type uint32;
      description
        "Node version.";
      mandatory true;
    }
    leaf type {
      type string;
      description
        "Node type.";
      mandatory false;
    }
    leaf state {
      type ciena-osrp-types:state;
      description
        "Specifies whether the node is blocked or not.";
    }
    leaf regens-avail {
      type uint16;
      description
        "Number of regen banks available.";
      mandatory false;
    }
    leaf assigned-color {
      type ciena-osrp-types:hex-triplet;
      description
        "Color assigned to node (in hex-triplet format, e.g, #f4c430)";
      mandatory false;
    }
  }

  grouping osrp-graph-link-group {
    leaf from-node-id {
      type ciena-osrp-types:node-id-type;
      description
        "From Node id.";
      mandatory true;
    }
    leaf from-port {
      type uint32;
      description
        "From port Id.";
      mandatory true;
    }
    leaf to-node-id {
      type ciena-osrp-types:node-id-type;
      description
        "To Node id.";
      mandatory true;
    }
    leaf to-port {
      type uint32;
      description
        "To port Id.";
      mandatory true;
    }
    leaf admin-weight {
      type uint32;
      description
        "Administrative weight which specifies the level of importance given to the link.";
      default "5040";
    }
    leaf grid-type {
      type ciena-osrp-types:link-type;
      description
        "Grid type of link.";
    }
    leaf advertised-bandwidth {
      type uint16;
      description
        "Advertised bandwidth (number of bits set = number of 6.25 slots available). Max. 1536.";
    }
    leaf maximum-bandwidth {
      type uint16;
      description
        "Maximum bandwidth (number of bits set = number of 6.25 slots available). Max. 1536.";
    }
    leaf spectrum-metrics {
      type yang:hex-string {
        length "0..384";
      }
      description
        "Spectrum available on link.";
    }
    leaf state {
      type ciena-osrp-types:state;
      description
        "Specifies whether the link is blocked or not.";
    }
  }
}
