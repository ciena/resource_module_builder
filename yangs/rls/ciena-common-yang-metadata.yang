module ciena-common-yang-metadata {
  yang-version 1.1;
  namespace "urn:ciena:params:xml:ns:yang:ciena-common-yang-metadata";
  prefix metadata;

  import ciena-common-yang {
    prefix ciena-common-yang;
  }
  import ciena-common-version {
    prefix version;
  }

  organization
    "Ciena Corporation";
  contact
    "Web URL: http://www.ciena.com/
     Postal:  7035 Ridge Road
             Hanover, Maryland 21076
             U.S.A.
     Phone:   +1 800-921-1144
     Fax:     +1 410-694-5750";
  description
    "Holds extension definitions that contain metadata extracted from the yang
     files.";

  revision 2023-05-08 {
    description
      "Added presence to metadata";
    version:version "version" {
      version:string "1.5.0";
    }
  }
  revision 2023-05-01 {
    description
      "Added min-elements and max-elements to metadata";
    version:version "version" {
      version:string "1.4.0";
    }
  }
  revision 2023-01-27 {
    description
      "Added target path to encryption metadata";
    version:version "version" {
      version:string "1.3.0";
    }
  }
  revision 2023-01-27 {
    description
      "Added target path to encryption metadata";
    version:version "version" {
      version:string "1.3.0";
    }
  }
  revision 2022-11-01 {
    description
      "Added encryption metadata";
    version:version "version" {
      version:string "1.2.0";
    }
  }
  revision 2021-02-05 {
    description
      "Added sensitive metadata";
    version:version "version" {
      version:string "1.1.0";
    }
  }
  revision 2021-02-05 {
    description
      "Initial revision";
    version:version "version" {
      version:string "1.0.0";
    }
  }

  grouping metadata-grouping {
    leaf mandatory {
      type boolean;
      default "false";
      description
        "Flag that indicates if a leaf is mandatory";
    }
    leaf-list ranges {
      type decimal64 {
        fraction-digits 9;
      }
      description
        "List of numbers that indicate ranges permitted for the leaf.
          This is a list of pairs of numbers, representing sets of
          minimums and maximums.  If the value falls (inclusively) with
          any of the ranges, it is valid.  Single value ranges are
          encoded as that number repeated as both the minimum and the
          maximum.";
    }
    leaf sensitive {
      type boolean;
      default "false";
      description
        "Flag that indicates if a leaf is sensitive data (password,
          token, shared secrets).  Sensitive data can be optionally
          hidden during serialization.";
    }
    leaf encrypt {
      type uint16;
      description
        "The index of the encrypted field of this leaf";
    }
    leaf decrypt {
      type uint16;
      description
        "The index of the decrypted field of this leaf";
    }
    leaf target-path {
      type string;
      description
        "the path of the target yang. This field is used when
          the encrypt, decrypt field is not simply a silbing
          of each other but nested in encrypted containers.";
    }
    leaf max-elements {
      type uint32;
      description
        "If the corresponding attribute is a list or leaf-list
          max-elements defines the max list size. This provides compliance with RFC 6020.";
    }
    leaf min-elements {
      type uint32;
      description
        "If the corresponding attribute is a list or leaf-list
          min-elements defines the min list size.  This provides compliance with RFC 6020.";
    }
    leaf presence {
      type boolean;
      description
        "If the parameter is a container with presence keyword in yang.";
    }
  }

  ciena-common-yang:yang-data "yang-metadata" {
    container metadata {
      leaf mandatory {
        type boolean;
        default "false";
        description
          "Flag that indicates if a leaf is mandatory";
      }
      leaf-list ranges {
        type decimal64 {
          fraction-digits 9;
        }
        description
          "List of numbers that indicate ranges permitted for the leaf.
            This is a list of pairs of numbers, representing sets of
            minimums and maximums.  If the value falls (inclusively) with
            any of the ranges, it is valid.  Single value ranges are
            encoded as that number repeated as both the minimum and the
            maximum.";
      }
      leaf sensitive {
        type boolean;
        default "false";
        description
          "Flag that indicates if a leaf is sensitive data (password,
            token, shared secrets).  Sensitive data can be optionally
            hidden during serialization.";
      }
      leaf encrypt {
        type uint16;
        description
          "The index of the encrypted field of this leaf";
      }
      leaf decrypt {
        type uint16;
        description
          "The index of the decrypted field of this leaf";
      }
      leaf target-path {
        type string;
        description
          "the path of the target yang. This field is used when
            the encrypt, decrypt field is not simply a silbing
            of each other but nested in encrypted containers.";
      }
      leaf max-elements {
        type uint32;
        description
          "If the corresponding attribute is a list or leaf-list
            max-elements defines the max list size. This provides compliance with RFC 6020.";
      }
      leaf min-elements {
        type uint32;
        description
          "If the corresponding attribute is a list or leaf-list
            min-elements defines the min list size.  This provides compliance with RFC 6020.";
      }
      leaf presence {
        type boolean;
        description
          "If the parameter is a container with presence keyword in yang.";
      }
    }
  }

  grouping enum-group {
    leaf name {
      type string;
    }
    list map {
      key "value";
      leaf value {
        type uint64;
      }
      leaf enum {
        type string;
      }
    }
  }

  typedef element-types {
    type enumeration {
      enum root;
      enum module;
      enum list;
      enum container;
      enum any;
      enum rpc;
      enum action;
      enum notification;
      enum input;
      enum output;
    }
  }

  typedef leaf-types {
    type enumeration {
      enum uint8;
      enum uint16;
      enum uint32;
      enum uint64;
      enum int8;
      enum int16;
      enum int32;
      enum int64;
      enum decimal64;
      enum enum;
      enum string;
      enum bool;
      enum bits;
      enum instance-id;
    }
  }

  container model {
    list types {
      key "name";
      leaf name {
        type string;
      }
    }
    list element {
      key "path";
      leaf path {
        type string;
      }
      leaf type {
        type element-types;
      }
      leaf user-ordered {
        type boolean;
      }
      leaf config {
        type boolean;
      }
      leaf-list keys {
        type string;
      }
      list leaves {
        key "name";
        leaf name {
          type string;
        }
        leaf type {
          type leaf-types;
        }
        leaf min-length {
          type uint32;
        }
        leaf max-length {
          type uint32;
        }
        leaf config {
          type boolean;
        }
        leaf leaf-list {
          type boolean;
        }
        leaf key {
          type boolean;
        }
        leaf enum-ref {
          type leafref {
            path "../../../types/name";
          }
        }
        uses metadata-grouping;
      }
      list children {
        key "name";
        leaf name {
          type string;
        }
        leaf elem-ref {
          type leafref {
            path "../../path";
          }
        }
      }
    }
  }
}
