module ciena-osrp-common-channel-diagnostics {
  namespace "urn:ciena:params:xml:ns:yang:ciena-osrp-common-channel-diagnostics";
  prefix ciena-osrp-common-channel-diagnostics;

  import ciena-common-version {
    prefix ciena-common-version;
  }
  import ciena-osrp-common-types {
    prefix osrp-common-types;
  }

  organization
    "Ciena Corporation";
  contact
    "Web URL: http://www.ciena.com
     Postal: Ciena India Pvt. Ltd.
     Sector 32, Plot 14,
     Gurgaon 122001,
     Haryana, India";
  description
    "This module describes Ciena's osrp and osrp-rls-ra common end-to-end diagnostics data.";

  revision 2022-12-06 {
    description
      "Add line-out-mux-port leaf in ccs-instance.";
    ciena-common-version:string "1.4.0";
  }
  revision 2022-04-26 {
    description
      "Add nmc-instance-identifier field in channel-controller";
    ciena-common-version:string "1.3.0";
  }
  revision 2021-12-14 {
    description
      "Add optical-signal-fail leaf for rx-proxy.";
    ciena-common-version:string "1.2.0";
  }
  revision 2021-09-24 {
    description
      "Add rx-down and rx-degrade leaf for rx-proxy.";
    ciena-common-version:string "1.1.0";
  }
  revision 2021-08-05 {
    description
      "Initial revision.";
    ciena-common-version:string "1.0.0";
  }

  grouping ccs-instance-common {
    list ccs-instance {
      key "name";
      leaf name {
        type string;
        description
          "Indicates the name of the ccs-instance.";
      }
      leaf line-out-mux-port {
        type string;
        description
          "Name of the mux line-out port. It will be common out port for CMD
           and line-out port for RLA.";
      }
      list channel-controller {
        key "center-frequency";
        leaf center-frequency {
          type osrp-common-types:frequency-mhz;
          description
            "Specifies center frequency of Channel controller";
        }
        leaf nmc-instance {
          type string;
          description
            "Specifies nmc-instance of Channel controller";
        }
        leaf nmc-instance-identifier {
          type instance-identifier;
          description
            "nmc-instance-identifier";
        }
        leaf operational-state {
          type osrp-common-types:channel-operational-state;
          description
            "Specifies current operational state of channel controller.";
        }
        leaf additional-info {
          type string {
            length "0..1024";
          }
          description
            "Specifies additional info about channel controller status.";
        }
      }
    }
    list rx-status {
      key "port";
      leaf port {
        type string;
        description
          "The name of port.";
      }
      leaf rx-down {
        type boolean;
        description
          "RX down.";
      }
      leaf rx-degrade {
        type boolean;
        description
          "RX degrade.";
      }
      leaf optical-signal-fail {
        type boolean;
        description
          "Optical signal fail.";
      }
    }
  }
}
