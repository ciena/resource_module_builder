module ciena-6500r-template {
  namespace "urn:ciena:params:xml:ns:yang:ciena-6500r-template";
  prefix template;

  import ciena-6500r-types {
    prefix ciena-6500r-types;
  }
  import ciena-common-yang {
    prefix yang;
  }

  organization
    "Ciena Corporation";
  contact
    "Web URL: http://www.ciena.com/
     Postal:  7035 Ridge Road
             Hanover, Maryland 21076
             U.S.A.
     Phone:   +1 800-921-1144
     Fax:     +1 410-694-5750";
  description
    "This YANG file describes the API for the template service.  This
     service will manage templates of static or dynamic data used in a
     deployment.  This data represents models of cards and other data
     normally required in a configuration request.  This data can be
     queried via the template service and can optionally be used by
     services to extend a configuration with detailed boiler-plate
     information";

  revision 2015-04-07 {
    description
      "";
  }

  container template-options {
    description
      "Deployment options for the template service.";
    leaf templates-dir {
      type string;
      description
        "Directory that contains template files.";
    }
  }
  container template {
    anyxml input;
  }

  rpc template-get {
    input {
      leaf pec {
        type ciena-6500r-types:pec-code;
        description
          "Pec code";
      }
      leaf name {
        type string;
        description
          "name";
      }
    }
    output {
      anyxml template;
    }
  }
}
