submodule ciena-pro-fib-common {
  belongs-to ciena-pro-fib {
    prefix cn-fib;
  }

  import ciena-common-version {
    prefix ciena-common-version;
  }

  import openconfig-interfaces {
    prefix oc-if;
  }

  import openconfig-yang-types {
    prefix oc-yang;
  }

  import openconfig-inet-types {
    prefix oc-inet;
  }

  organization
    "Ciena Corporation";
  contact
    "Web URL: http://www.ciena.com/";
  description
    "Submodule containing definitions of groupings that are re-used
     across multiple contexts within the FIB model.";

  revision 2019-09-17 {
    ciena-common-version:string "0.0.1";
    description
      "Initial version";
  }

  grouping fib-nhop-structural {
    description
      "Structural grouping describing a next-hop entry.";
    container next-hops {
      config false;
      description
        "The list of next-hops that are to be used for entry within
         the FIB table. The structure of each next-hop is address
         family independent, such that it is possible to resolve fully
         how the next-hop is treated. For example:
         - Where ingress IPv4 unicast packets are to be forwarded via
          an MPLS LSP, the next-hop list should indicate the MPLS
          label stack that is used to the next-hop.
         - Where ingress MPLS labelled packets are to be forwarded to
          an IPv6 nexthop (for example, a CE within a VPN, then the
          popped label stack, and IPv6 next-hop address should be
          indicated).";
      list next-hop {
        key "index";
        config false;
        description
          "A next-hop associated with the forwarding instance.";
        leaf index {
          type leafref {
            path "../state/index";
          }
          config false;
          description
            "A unique index identifying the next-hop entry for the
             FIB entry";
        }

        container state {
          config false;
          description
            "Operational state parameters relating to the FIB
             next-hop entry";
          uses fib-common-entry-nexthop-state;
        }
      }
    }
  }

  grouping fib-common-entry-state {
    description
      "Operational state parameters relating to a forwarding entry";
    leaf packets-forwarded {
      type oc-yang:counter64;
      description
        "The number of packets which have matched, and been forwarded,
         based on the FIB entry.";
    }

    leaf octets-forwarded {
      type oc-yang:counter64;
      description
        "The number of octets which have matched, and been forwarded,
         based on the FIB entry";
    }

    leaf next-hop-group {
      type leafref {
        path "../../../../next-hop-groups/next-hop-group/state/id";
      }
      description
        "A reference to the next-hop-group that is in use for the entry
         within the FIB. Traffic is distributed across the set of next-hops
         within the next-hop group according to the weight.";
    }
  }

  grouping fib-common-entry-nexthop-state {
    description
      "Parameters relating to a next-hop.";
    leaf index {
      type uint64;
      description
        "A unique entry for the next-hop.";
    }

    leaf ip-address {
      type oc-inet:ip-address;
      description
        "The IP address of the next-hop system.";
    }

    leaf mac-address {
      type oc-yang:mac-address;
      description
        "The MAC address of the next-hop if resolved by the local
         network instance.";
    }

    uses oc-if:interface-ref-common;
  }

  grouping fib-next-hop-groups-structural {
    description
      "Logical grouping for groups of next-hops.";
    container next-hop-groups {
      config false;
      description
        "Surrounding container for groups of next-hops.";
      list next-hop-group {
        key "id";
        config false;
        description
          "An individual set of next-hops grouped into a common group.
           Each entry within an forwarding table points to a
           next-hop-group. Entries in the next-hop-group are forwarded to
           according to the weights specified for each next-hop group.
           If an entry within the next-hop group becomes unusable, for
           example due to an interface failure, the remaining entries
           are used until all entries become unusable - at which point
           the backup next-hop-group (if specified) is used.";
        leaf id {
          type leafref {
            path "../state/id";
          }
          description
            "A reference to a unique identifier for the next-hop-group.";
        }

        container state {
          config false;
          description
            "Operational state parameters relating to next-hop-groups.";
          uses fib-nhg-state;
        }

        container next-hops {
          config false;
          description
            "Surrounding container for the list of next-hops within
             the next-hop-group.";
          list next-hop {
            key "index";
            config false;
            description
              "An individual next-hop within the next-hop-group. Each
               next-hop is a reference to an entry within the next-hop
               list.";
            leaf index {
              type leafref {
                path "../state/index";
              }
              config false;
              description
                "A reference to the index for the next-hop within the
                 the next-hop-group.";
            }

            container state {
              config false;
              description
                "Operational state parameters related to a next-hop
                 within the next-hop-group.";
              uses fib-nhg-nh-state;
            }
          }
        }
      }
    }
  }

  grouping fib-nhg-state {
    description
      "Operational state parameters related to a next-hop-group.";
    leaf id {
      type uint64;
      description
        "A unique identifier for the next-hop-group. This index
         is not expected to be consistent across reboots, or
         reprogramming of the next-hop-group. When updating
         a next-hop-group, if the group is removed by the system
         or assigned an alternate identifier, the system should
         send telemetry notifications deleting the previous
         identifier. If the identifier of the next-hop-group
         is changed, all FIB entries that reference it must
         also be updated.";
    }

    leaf color {
      type uint64;
      description
        "An arbitrary colour that is used as an identifier for the next-hop
         group. Some next-hop resolutions may utilise the colour to select
         the particular next-hop-group that a routing entry should be resolved
         to. In this case, next-hop-group selection may be based on colour
         matches rather than the protocol specified next-hop.
         Regardless of whether the next-hop-group's specified colour is
         used to select an FIB's active forwarding entry, the next-hop-group
         referenced by an entry should be the currently active value.
         Next-hop-groups that are installed on the system through a protocol
         that allows injection of such entries (e.g., BGP using the SR-TE
         Policy SAFI, or gRPC-based RIB programming) should have the colour
         specified in the injecting protocol within this leaf.";
    }

    leaf backup-next-hop-group {
      type leafref {
        path "../../../next-hop-group/state/id";
      }
      description
        "The backup next-hop-group for the current group. When all
         entries within the next-hop group become unusable, the backup
         next-hop group is used if specified.";
    }
  }

  grouping fib-nhg-nh-state {
    description
      "Operational state parameters relating to an individual next-hop
       within the next-hop-group.";
    leaf index {
      type leafref {
        path "../../../../../../next-hops/next-hop/state/index";
      }
      description
        "A reference to the identifier for the next-hop to which
         the entry in the next-hop group corresponds.";
    }

    leaf weight {
      type uint64;
      description
        "The weight applied to the next-hop within the group. Traffic
         is balanced across the next-hops within the group in the
         proportion of weight/(sum of weights of the next-hops within
         the next-hop group).";
    }
  }
}
