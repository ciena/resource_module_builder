module ciena-6500r-local-fault-debug {
  namespace "urn:ciena:params:xml:ns:yang:ciena-6500r-local-fault-debug";
  prefix local-fault-debug;

  import ciena-common-version {
    prefix ciena-common-version;
  }

  organization
    "Ciena Corporation";
  contact
    "Web URL: http://www.ciena.com/
     Postal:  7035 Ridge Road
              Hanover, Maryland 21076
              U.S.A.
     Phone:   +1 800-921-1144
     Fax:     +1 410-694-5750";
  description
    "This modules describes Ciena's debug interface to Local fault Service";

  revision 2020-08-05 {
    description
      "Initial revision";
    ciena-common-version:string "1.0.0";
  }

  rpc lfs-debug {
    input {
      leaf command {
        type string;
        description
          "Local-fault debugging command.
           If not specified, the list of available commands are displayed in the response.";
      }
    }
    output {
      list output {
        key "o";
        leaf o {
          type string {
            length "1..132";
          }
        }
      }
    }
  }
}
