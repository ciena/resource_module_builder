module ciena-6500r-wsc {
  yang-version 1.1;
  namespace "urn:ciena:params:xml:ns:yang:ciena-6500r-wsc";
  prefix wsc;

  import ciena-6500r-ports {
    prefix ports;
  }

  import ciena-common-version {
    prefix version;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's wsc object for the 6500r platform";

  revision 2020-06-30 {
    version:version "version" {
      version:string "1.0.2";
    }
    description
      "Fix version formating";
  }
  revision 2020-03-20 {
    version:version "version" {
      version:string "1.0.1";
    }
    description
      "Add diagnostic container and port-failure leaf";
  }
  revision 2020-03-05 {
    version:version "version" {
      version:string "1.0.0";
    }
    description
      "Modifying Admin state to reflect the values sent/recieved via snmp";
  }
  revision 2019-04-01 {
    description
      "6500r Release 1.0";
  }

  grouping ciena-6500r-wsc-mount {
    list wsc {
      key "name";
      leaf name {
        type string;
        description
          "WSC Facility name";
      }

      leaf parent-port {
        type leafref {
          path "/ports:port/ports:name";
        }
        mandatory true;
        description
          "WSC facility parent port.";
      }

      leaf admin-state {
        type enumeration {
          enum "Enabled" {
            value 10;
            description
              "Service is Enabled.";
          }
          enum "Disabled" {
            value 12;
            description
              "Service is Disabled.";
          }
        }
        description
          "Identify the administrative state";
      }

      container diagnostic {
        config false;
        description
          "Facility diagnostic state";
        leaf port-failure {
          type boolean;
          description
            "Port failure";
        }
      }
    }
  }

  grouping ciena-6500r-wsc-mount-actions;

  uses ciena-6500r-wsc-mount;
}
