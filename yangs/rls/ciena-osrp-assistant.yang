module ciena-osrp-assistant {
  namespace "urn:ciena:params:xml:ns:yang:ciena-osrp-assistant";
  prefix osrp-assistant;

  import ciena-common-version {
    prefix ciena-common-version;
  }

  import ciena-osrp-types {
    prefix ciena-osrp-types;
  }

  organization
    "Ciena Corporation";
  contact
    "Web URL: http://www.ciena.com
     Postal: Ciena India Pvt. Ltd.
     Sector 32, Plot 14,
     Gurgaon 122001,
     Haryana, India";
  description
    "This module describes Ciena's OSRP PORT LINE
     object model for the 6500r platform";

  revision 2020-12-11 {
    ciena-common-version:string "1.2.0";
    description
      "Adding node-name as input field
       for handling rpc via osrp-rls-ra.";
  }
  revision 2020-10-06 {
    ciena-common-version:string "1.1.0";
    description
      "Making assistant little generic
       for all kind of osrp debugging commands.";
  }
  revision 2019-09-19 {
    ciena-common-version:string "1.0.0";
    description
      "6500r-series Release 2.0
       YANG cleanup.";
  }
  revision 2019-09-09 {
    description
      "Initial revision.";
  }

  rpc osrp-assistant {
    description
      "Request the directory server to start a domain instance.";
    input {
      leaf operation {
        type string {
          length "0..64";
        }
        mandatory true;
        description
          "Operation to perform.";
      }

      leaf command {
        type string {
          length "0..512";
        }
        mandatory false;
        description
          "Command to execute.";
      }

      leaf module {
        type string {
          length "0..512";
        }
        mandatory false;
        description
          "Name of the module to modify log-levels on.";
      }

      leaf node-name {
        type ciena-osrp-types:node-name;
        description
          "OSRP node name";
      }
    }

    output {
      leaf result {
        type string {
          length "0..100";
        }
        description
          "Output result message.";
      }

      leaf-list response {
        type string {
          length "0..1024";
        }
        description
          "Output response message.";
      }
    }
  }
}
