module ciena-pro-graph-node {
  namespace "urn:ciena:params:xml:ns:yang:ciena-pro-graph-node";
  prefix graph-node;

  import ciena-common-version {
    prefix version;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's graph node for the 6500r-Series platform";

  revision 2022-07-25 {
    description
      "Add graph-version in graph-node to support graph protocol version";
    version:version "version" {
      version:string "1.1.0";
    }
  }
  revision 2022-02-02 {
    description
      "Initial creation";
    version:version "version" {
      version:string "1.0.0";
    }
  }

  typedef node-type {
    type enumeration {
      enum none {
        description
          "A node that is not part of graph";
      }
      enum local {
        description
          "The local node, which is also part of the local site.";
      }
      enum site {
        description
          "The node is part of the local site.";
      }
      enum neighbour {
        description
          "Neighbour node but at a different site";
      }
    }
  }

  list graph-node {
    key "name";
    leaf name {
      type string;
      description
        "Node name";
    }
    leaf node-type {
      type node-type;
      default "none";
    }
    container graph-version {
      uses version:version {
        description
          "Supported graph protocol version";
      }
    }
  }
}
