module ciena-6500r-slots {
  yang-version 1.1;
  namespace "urn:ciena:params:xml:ns:yang:ciena-6500r-slots";
  prefix ciena-6500r-slots;

  import ciena-6500r-amps {
    prefix ciena-6500r-amps;
  }

  import ciena-6500r-chc {
    prefix ciena-6500r-chc;
  }

  import ciena-6500r-circuit-pack {
    prefix ciena-6500r-circuit-pack;
  }

  import ciena-pro-frequencies {
    prefix ciena-pro-frequencies;
  }

  import ciena-6500r-optmons {
    prefix ciena-6500r-optmons;
  }

  import ciena-6500r-pwrmon {
    prefix ciena-6500r-pwrmon;
  }

  import ciena-6500r-osc {
    prefix ciena-6500r-osc;
  }

  import ciena-6500r-pc {
    prefix ciena-6500r-pc;
  }

  import ciena-6500r-ports {
    prefix ciena-6500r-ports;
  }

  import ciena-6500r-voa {
    prefix ciena-6500r-voa;
  }

  import ciena-6500r-ramans {
    prefix ciena-6500r-ramans;
  }

  import ciena-6500r-telemetry {
    prefix ciena-6500r-telemetry;
  }

  import ciena-6500r-otdr {
    prefix ciena-6500r-otdr;
  }

  import ciena-6500r-otdr-card-if {
    prefix ciena-6500r-otdr-card-if;
  }

  import ciena-6500r-links {
    prefix ciena-6500r-links;
  }

  import ciena-6500r-protection {
    prefix ciena-6500r-protection;
  }

  import ciena-6500r-opm {
    prefix ciena-6500r-opm;
  }

  import ciena-6500r-otrx {
    prefix ciena-6500r-otrx;
  }

  import ciena-6500r-wsc {
    prefix ciena-6500r-wsc;
  }

  import ciena-6500r-connection-validation {
    prefix ciena-6500r-connection-validation;
  }

  import ciena-6500r-wss {
    prefix ciena-6500r-wss;
  }

  import ciena-6500r-pwr-profile {
    prefix ciena-6500r-pwr-profile;
  }

  import ciena-6500r-line-assoc {
    prefix ciena-6500r-line-assoc;
  }

  import ciena-6500r-dgff {
    prefix ciena-6500r-dgff;
  }

  import ciena-6500r-tx-proxy {
    prefix ciena-6500r-tx-proxy;
  }

  import ciena-6500r-rx-proxy {
    prefix ciena-6500r-rx-proxy;
  }

  import ciena-6500r-fan {
    prefix ciena-6500r-fan;
  }

  import ciena-6500r-power-supply {
    prefix ciena-6500r-power-supply;
  }

  import ciena-6500r-plug-defaults {
    prefix ciena-6500r-plug-defaults;
  }

  import ciena-6500r-facility-logical-map {
    prefix ciena-6500r-facility-logical-map;
  }

  import ciena-6500r-optical-control {
    prefix ciena-6500r-optical-control;
  }

  import ciena-pro-alarm-correlation {
    prefix ciena-pro-alarm-correlation;
  }

  import ciena-common-yang {
    prefix yang;
  }

  import ciena-6500r-types {
    prefix ciena-6500r-types;
  }

  import ietf-inet-types {
    prefix inet;
  }

  import ietf-yang-types {
    prefix ietf-yang;
  }

  import ciena-common-version {
    prefix ciena-common-version;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's 6500r platform slot model";

  revision 2021-05-20 {
    ciena-common-version:string "1.9.0";
    description
      "Mounted pwr-profile to slot inventory.";
  }
  revision 2021-05-11 {
    ciena-common-version:string "1.8.0";
    description
      "Mounted power-supply facility to slot config and inventory.";
  }
  revision 2021-03-25 {
    ciena-common-version:string "1.7.0";
    description
      "Mounted fan to slot config and inventory.";
  }
  revision 2021-03-19 {
    ciena-common-version:string "1.6.0";
    description
      "Mounted optical-control model to slot config.";
  }
  revision 2021-02-01 {
    ciena-common-version:string "1.5.0";
    description
      "Added tx-fault and rx-los diagnostic points.";
  }
  revision 2020-11-30 {
    ciena-common-version:string "1.4.0";
    description
      "Mounted tx-proxy and rx-proxy to inventory.";
  }
  revision 2020-11-12 {
    ciena-common-version:string "1.3.2";
    description
      "Added slot-empty diagnostic points.";
  }
  revision 2020-10-30 {
    ciena-common-version:string "1.3.1";
    description
      "Added telemetry-input-1,2,3 diagnostic points.";
  }
  revision 2020-08-06 {
    ciena-common-version:string "1.3.0";
    description
      "Mounted alarm-correlation model to the slot config";
  }
  revision 2020-06-17 {
    ciena-common-version:string "1.2.0";
    description
      "Added backplane-300mm value to form-factor enum";
  }
  revision 2020-04-01 {
    ciena-common-version:string "1.1.4";
    description
      "Added powered-uptime leaf in restart-complete notification";
  }
  revision 2020-02-28 {
    ciena-common-version:string "1.1.3";
    description
      "Added triple-high backplane-card-type";
  }
  revision 2020-03-18 {
    ciena-common-version:string "1.1.3";
    description
      "Removed last-restart-type and last-restart-time leaves";
  }
  revision 2020-01-31 {
    ciena-common-version:string "1.1.2";
    description
      "Added last-restart-type and last-restart-time leaves";
  }
  revision 2020-01-24 {
    ciena-common-version:string "1.1.1";
    description
      "changed corrupt-inventory name to corrupt-inventory-fault.";
  }
  revision 2020-01-23 {
    ciena-common-version:string "1.1.0";
    description
      "Added configuration-mismatch and fan-missing diagnostic points.";
  }
  revision 2020-01-13 {
    ciena-common-version:string "1.0.9";
    description
      "Added return codes for RPCs.";
  }
  revision 2020-01-06 {
    ciena-common-version:string "1.0.8";
    description
      "Change ctm-access-panel to ctm-front-panel";
  }
  revision 2019-12-12 {
    ciena-common-version:string "1.0.7";
    description
      "Added restart-complete notification";
  }
  revision 2019-12-10 {
    ciena-common-version:string "1.0.6";
    description
      "Added corrupt inventory, slc force fail, lan port down, software subsystem fault,
       hardware subsystem fault, low voltage fault, boot fail fault, power failure fault,
       internal management comms suspected, sid fault, cp running fallback Image Fault
       under diagnostic container";
  }
  revision 2019-10-18 {
    ciena-common-version:string "1.0.5";
    description
      "Added Intercard Suspected, latch open, disk Usage 75/90/100
       under diagnostic container";
  }
  revision 2019-08-28 {
    ciena-common-version:string "1.0.4";
    description
      "Added slot-reserved parameter, updated the descriptions
       for slot-occupied, card-present, card-provisioned";
  }
  revision 2019-06-18 {
    ciena-common-version:string "1.0.3";
    description
      "Added pwer-profile-manager to mounts.";
  }
  revision 2019-06-06 {
    ciena-common-version:string "1.0.2";
    description
      "Added Lamp Test RPC.";
  }
  revision 2019-06-03 {
    ciena-common-version:string "1.0.1";
    description
      "Added circuit pack fail under diagnostic container .";
  }
  revision 2019-05-10 {
    ciena-common-version:string "1.0.0";
    description
      "Added a new pim power failure fault alarm under diagnostic container .";
  }
  revision 2017-01-01 {
    description
      "Initial revision";
  }

  grouping card-info-grouping {
    leaf backplane-card-type {
      type enumeration {
        enum "single";
        enum "double-wide";
        enum "double-high";
        enum "quad";
        enum "triple-high";
      }
    }

    leaf-list occupies {
      type ciena-6500r-types:object-name;
      description
        "The number of slots occupied by this card";
    }
  }

  grouping ciena-6500r-slots-mount {
    list slots {
      key "name";
      leaf name {
        type ciena-6500r-types:object-name;
        description
          "The name of the slot.";
      }

      leaf card-present {
        type boolean;
        config false;
        description
          "The slot is serving as the host slot for a card that is physically present.";
      }

      leaf card-provisioned {
        type boolean;
        config false;
        description
          "The slot has been provisioned as the host slot for a card.";
      }

      leaf slot-occupied {
        type boolean;
        config false;
        description
          "A multi-slot card or filler is physically present in the slot, but is not the host slot.";
      }

      leaf slot-reserved {
        type boolean;
        config false;
        description
          "The slot has been provisioned for a multi-slot card, but is not the host slot.";
      }

      leaf parent {
        type instance-identifier;
        description
          "Parent object, values can be a shelf or another circuit pack if it is subslot or pluggable ";
      }

      leaf form-factor {
        type enumeration {
          enum "backplane";
          enum "access-panel";
          enum "ctm";
          enum "fan";
          enum "power";
          enum "i2c";
          enum "passive";
          enum "sfp";
          enum "sfpplus";
          enum "cfp";
          enum "cfp2";
          enum "xfp";
          enum "qsfp";
          enum "qsfp28";
          enum "ctm-front-panel";
          enum "backplane-300mm";
        }
      }

      leaf auto-provisioning {
        type boolean;
        description
          "Auto-provsioning support.";
      }

      list backplane-card-type {
        key "backplane-card-type";
        config false;
        uses card-info-grouping;
      }

      container diagnostic {
        config false;
        description
          "Diagnostic state";
        leaf unknown {
          type boolean;
          description
            "Equipment state unknown";
        }

        leaf mismatch {
          type boolean;
          description
            "Equipment state mismatch";
        }

        leaf missing {
          type boolean;
          description
            "Equipment state missing";
        }

        leaf filler-missing {
          type boolean;
          description
            "Equipment state filler-missing";
        }

        leaf prov-incompatible {
          type boolean;
          description
            "Equipment state prov-incompatible";
        }

        leaf auto-provisioning-mismatch {
          type boolean;
          description
            "Equipment state Auto-Provisioning Mismatch";
        }

        leaf hi-temp-warning {
          type boolean;
          description
            "Equipment state High Temperature warning";
        }

        leaf hi-temp {
          type boolean;
          description
            "Equipment state High Temperature";
        }

        leaf power-feed-failure {
          type boolean;
          description
            "Equipment state power feed failure";
        }

        leaf failed {
          type boolean;
          description
            "Equipment state circuit pack fail";
        }

        leaf intercard-suspected {
          type boolean;
          description
            "Equipment state Intercard Suspected Fault";
        }

        leaf latch-open {
          type boolean;
          description
            "Equipment state Latch Open";
        }

        leaf disk-usage-75 {
          type boolean;
          description
            "Equipment state Disk Usage at 75 percent";
        }

        leaf disk-usage-90 {
          type boolean;
          description
            "Equipment state Disk Usage at 90 percent";
        }

        leaf disk-usage-100 {
          type boolean;
          description
            "Equipment state Disk Usage Full";
        }

        leaf corrupt-inventory-fault {
          type boolean;
          description
            "Equipment state Corrupt Inventory Fault";
        }

        leaf slc-force-fail {
          type boolean;
          description
            "Equipment state SLC Force Fail";
        }

        leaf lan-port-down {
          type boolean;
          description
            "Equipment state Lan Port Down";
        }

        leaf software-subsystem-fail {
          type boolean;
          description
            "Equipment state Software Subsystem Fail";
        }

        leaf hardware-subsystem-fail {
          type boolean;
          description
            "Equipment state Hardware Subsystem Fail";
        }

        leaf low-voltage-fault {
          type boolean;
          description
            "Equipment state Low Voltage Fault";
        }

        leaf power-failure-fault {
          type boolean;
          description
            "Equipment state Power Failure Fault";
        }

        leaf boot-fail-fault {
          type boolean;
          description
            "Equipment state Boot Fail Fault";
        }

        leaf internal-management-comms-suspected {
          type boolean;
          description
            "Equipment state Internal Management Comms Suspected";
        }

        leaf sid-fault {
          type boolean;
          description
            "Equipment state SID Fault";
        }

        leaf cp-running-fallback-image-fault {
          type boolean;
          description
            "Equipment state CP Running Fallback Image Fault";
        }

        leaf configuration-mismatch {
          type boolean;
          description
            "Equipment state Configuration Mismatch, mixed power card type";
        }

        leaf fan-missing {
          type boolean;
          description
            "Equipment state Fan Missing";
        }

        leaf telemetry-input-1 {
          type boolean;
          description
            "Equipment state Telemetry Input 1";
        }

        leaf telemetry-input-2 {
          type boolean;
          description
            "Equipment state Telemetry Input 2";
        }

        leaf telemetry-input-3 {
          type boolean;
          description
            "Equipment state Telemetry Input 3";
        }

        leaf slot-empty {
          type boolean;
          description
            "Equipment state Slot Empty";
        }

        leaf tx-fault {
          type boolean;
          description
            "Equipment state LOS";
        }

        leaf rx-los {
          type boolean;
          description
            "Equipment state LOS";
        }
      }

      container inventory {
        yang:mount-start "ciena-6500r-amps";
        yang:mount-end "ciena-6500r-amps";
        yang:mount-start "ciena-6500r-chc";
        yang:mount-end "ciena-6500r-chc";
        yang:mount-start "ciena-6500r-circuit-pack";
        yang:mount-end "ciena-6500r-circuit-pack";
        yang:mount-start "ciena-pro-frequencies";
        yang:mount-end "ciena-pro-frequencies";
        yang:mount-start "ciena-6500r-optmons";
        yang:mount-end "ciena-6500r-optmons";
        yang:mount-start "ciena-6500r-pwrmon";
        yang:mount-end "ciena-6500r-pwrmon";
        yang:mount-start "ciena-6500r-osc";
        yang:mount-end "ciena-6500r-osc";
        yang:mount-start "ciena-6500r-pc";
        yang:mount-end "ciena-6500r-pc";
        yang:mount-start "ciena-6500r-ports";
        yang:mount-end "ciena-6500r-ports";
        yang:mount-start "ciena-6500r-voa";
        yang:mount-end "ciena-6500r-voa";
        yang:mount-start "ciena-6500r-ramans";
        yang:mount-end "ciena-6500r-ramans";
        yang:mount-start "ciena-6500r-telemetry";
        yang:mount-end "ciena-6500r-telemetry";
        yang:mount-start "ciena-6500r-otdr";
        yang:mount-end "ciena-6500r-otdr";
        yang:mount-start "ciena-6500r-otdr-card-if";
        yang:mount-end "ciena-6500r-otdr-card-if";
        yang:mount-start "ciena-6500r-links";
        yang:mount-end "ciena-6500r-links";
        yang:mount-start "ciena-6500r-protection";
        yang:mount-end "ciena-6500r-protection";
        yang:mount-start "ciena-6500r-opm";
        yang:mount-end "ciena-6500r-opm";
        yang:mount-start "ciena-6500r-otrx";
        yang:mount-end "ciena-6500r-otrx";
        yang:mount-start "ciena-6500r-wsc";
        yang:mount-end "ciena-6500r-wsc";
        yang:mount-start "ciena-6500r-connection-validation";
        yang:mount-end "ciena-6500r-connection-validation";
        yang:mount-start "ciena-6500r-wss";
        yang:mount-end "ciena-6500r-wss";
        yang:mount-start "ciena-6500r-pwr-profile";
        yang:mount-end "ciena-6500r-pwr-profile";
        yang:mount-start "ciena-6500r-line-assoc";
        yang:mount-end "ciena-6500r-line-assoc";
        yang:mount-start "ciena-6500r-dgff";
        yang:mount-end "ciena-6500r-dgff";
        yang:mount-start "ciena-6500r-tx-proxy";
        yang:mount-end "ciena-6500r-tx-proxy";
        yang:mount-start "ciena-6500r-rx-proxy";
        yang:mount-end "ciena-6500r-rx-proxy";
        yang:mount-start "ciena-6500r-fan";
        yang:mount-end "ciena-6500r-fan";
        yang:mount-start "ciena-6500r-power-supply";
        yang:mount-end "ciena-6500r-power-supply";
        yang:mount-start "ciena-6500r-slots";
        yang:mount-end "ciena-6500r-slots";
        uses ciena-6500r-amps:ciena-6500r-amps-mount-actions;

        uses ciena-6500r-amps:ciena-6500r-amps-mount;

        uses ciena-6500r-chc:ciena-6500r-chc-mount-actions;

        uses ciena-6500r-chc:ciena-6500r-chc-mount;

        uses ciena-6500r-circuit-pack:ciena-6500r-circuit-pack-mount-actions;

        uses ciena-6500r-circuit-pack:ciena-6500r-circuit-pack-mount;

        uses ciena-pro-frequencies:ciena-pro-frequencies-mount-actions;

        uses ciena-pro-frequencies:ciena-pro-frequencies-mount;

        uses ciena-6500r-optmons:ciena-6500r-optmons-mount-actions;

        uses ciena-6500r-optmons:ciena-6500r-optmons-mount;

        uses ciena-6500r-pwrmon:ciena-6500r-pwrmon-mount-actions;

        uses ciena-6500r-pwrmon:ciena-6500r-pwrmon-mount;

        uses ciena-6500r-osc:ciena-6500r-osc-mount-actions;

        uses ciena-6500r-osc:ciena-6500r-osc-mount;

        uses ciena-6500r-pc:ciena-6500r-pc-mount-actions;

        uses ciena-6500r-pc:ciena-6500r-pc-mount;

        uses ciena-6500r-ports:ciena-6500r-ports-mount-actions;

        uses ciena-6500r-ports:ciena-6500r-ports-mount;

        uses ciena-6500r-voa:ciena-6500r-voa-mount-actions;

        uses ciena-6500r-voa:ciena-6500r-voa-mount;

        uses ciena-6500r-ramans:ciena-6500r-ramans-mount-actions;

        uses ciena-6500r-ramans:ciena-6500r-ramans-mount;

        uses ciena-6500r-telemetry:ciena-6500r-telemetry-mount-actions;

        uses ciena-6500r-telemetry:ciena-6500r-telemetry-mount;

        uses ciena-6500r-otdr:ciena-6500r-otdr-mount-actions;

        uses ciena-6500r-otdr:ciena-6500r-otdr-mount;

        uses ciena-6500r-otdr-card-if:ciena-6500r-otdr-card-if-mount-actions;

        uses ciena-6500r-otdr-card-if:ciena-6500r-otdr-card-if-mount;

        uses ciena-6500r-links:ciena-6500r-links-mount-actions;

        uses ciena-6500r-links:ciena-6500r-links-mount;

        uses ciena-6500r-protection:ciena-6500r-protection-mount-actions;

        uses ciena-6500r-protection:ciena-6500r-protection-mount;

        uses ciena-6500r-opm:ciena-6500r-opm-mount-actions;

        uses ciena-6500r-opm:ciena-6500r-opm-mount;

        uses ciena-6500r-otrx:ciena-6500r-otrx-mount-actions;

        uses ciena-6500r-otrx:ciena-6500r-otrx-mount;

        uses ciena-6500r-wsc:ciena-6500r-wsc-mount-actions;

        uses ciena-6500r-wsc:ciena-6500r-wsc-mount;

        uses ciena-6500r-connection-validation:ciena-6500r-connection-validation-mount-actions;

        uses ciena-6500r-connection-validation:ciena-6500r-connection-validation-mount;

        uses ciena-6500r-wss:ciena-6500r-wss-mount-actions;

        uses ciena-6500r-wss:ciena-6500r-wss-mount;

        uses ciena-6500r-pwr-profile:ciena-6500r-pwr-profile-mount-actions;

        uses ciena-6500r-pwr-profile:ciena-6500r-pwr-profile-mount;

        uses ciena-6500r-line-assoc:ciena-6500r-line-assoc-mount-actions;

        uses ciena-6500r-line-assoc:ciena-6500r-line-assoc-mount;

        uses ciena-6500r-dgff:ciena-6500r-dgff-mount-actions;

        uses ciena-6500r-dgff:ciena-6500r-dgff-mount;

        uses ciena-6500r-tx-proxy:ciena-6500r-tx-proxy-mount-actions;

        uses ciena-6500r-tx-proxy:ciena-6500r-tx-proxy-mount;

        uses ciena-6500r-rx-proxy:ciena-6500r-rx-proxy-mount-actions;

        uses ciena-6500r-rx-proxy:ciena-6500r-rx-proxy-mount;

        uses ciena-6500r-fan:ciena-6500r-fan-mount-actions;

        uses ciena-6500r-fan:ciena-6500r-fan-mount;

        uses ciena-6500r-power-supply:ciena-6500r-power-supply-mount-actions;

        uses ciena-6500r-power-supply:ciena-6500r-power-supply-mount;

        list slots {
          key "name";
          leaf name {
            type ciena-6500r-types:object-name;
            description
              "The name of the slot.";
          }

          leaf card-present {
            type boolean;
            config false;
            description
              "The slot is serving as the host slot for a card that is physically present.";
          }

          leaf card-provisioned {
            type boolean;
            config false;
            description
              "The slot has been provisioned as the host slot for a card.";
          }

          leaf slot-occupied {
            type boolean;
            config false;
            description
              "A multi-slot card or filler is physically present in the slot, but is not the host slot.";
          }

          leaf slot-reserved {
            type boolean;
            config false;
            description
              "The slot has been provisioned for a multi-slot card, but is not the host slot.";
          }

          leaf parent {
            type instance-identifier;
            description
              "Parent object, values can be a shelf or another circuit pack if it is subslot or pluggable ";
          }

          leaf form-factor {
            type enumeration {
              enum "backplane";
              enum "access-panel";
              enum "ctm";
              enum "fan";
              enum "power";
              enum "i2c";
              enum "passive";
              enum "sfp";
              enum "sfpplus";
              enum "cfp";
              enum "cfp2";
              enum "xfp";
              enum "qsfp";
              enum "qsfp28";
              enum "ctm-front-panel";
              enum "backplane-300mm";
            }
          }

          leaf auto-provisioning {
            type boolean;
            description
              "Auto-provsioning support.";
          }

          list backplane-card-type {
            key "backplane-card-type";
            config false;
            uses card-info-grouping;
          }

          container diagnostic {
            config false;
            description
              "Diagnostic state";
            leaf unknown {
              type boolean;
              description
                "Equipment state unknown";
            }

            leaf mismatch {
              type boolean;
              description
                "Equipment state mismatch";
            }

            leaf missing {
              type boolean;
              description
                "Equipment state missing";
            }

            leaf filler-missing {
              type boolean;
              description
                "Equipment state filler-missing";
            }

            leaf prov-incompatible {
              type boolean;
              description
                "Equipment state prov-incompatible";
            }

            leaf auto-provisioning-mismatch {
              type boolean;
              description
                "Equipment state Auto-Provisioning Mismatch";
            }

            leaf hi-temp-warning {
              type boolean;
              description
                "Equipment state High Temperature warning";
            }

            leaf hi-temp {
              type boolean;
              description
                "Equipment state High Temperature";
            }

            leaf power-feed-failure {
              type boolean;
              description
                "Equipment state power feed failure";
            }

            leaf failed {
              type boolean;
              description
                "Equipment state circuit pack fail";
            }

            leaf intercard-suspected {
              type boolean;
              description
                "Equipment state Intercard Suspected Fault";
            }

            leaf latch-open {
              type boolean;
              description
                "Equipment state Latch Open";
            }

            leaf disk-usage-75 {
              type boolean;
              description
                "Equipment state Disk Usage at 75 percent";
            }

            leaf disk-usage-90 {
              type boolean;
              description
                "Equipment state Disk Usage at 90 percent";
            }

            leaf disk-usage-100 {
              type boolean;
              description
                "Equipment state Disk Usage Full";
            }

            leaf corrupt-inventory-fault {
              type boolean;
              description
                "Equipment state Corrupt Inventory Fault";
            }

            leaf slc-force-fail {
              type boolean;
              description
                "Equipment state SLC Force Fail";
            }

            leaf lan-port-down {
              type boolean;
              description
                "Equipment state Lan Port Down";
            }

            leaf software-subsystem-fail {
              type boolean;
              description
                "Equipment state Software Subsystem Fail";
            }

            leaf hardware-subsystem-fail {
              type boolean;
              description
                "Equipment state Hardware Subsystem Fail";
            }

            leaf low-voltage-fault {
              type boolean;
              description
                "Equipment state Low Voltage Fault";
            }

            leaf power-failure-fault {
              type boolean;
              description
                "Equipment state Power Failure Fault";
            }

            leaf boot-fail-fault {
              type boolean;
              description
                "Equipment state Boot Fail Fault";
            }

            leaf internal-management-comms-suspected {
              type boolean;
              description
                "Equipment state Internal Management Comms Suspected";
            }

            leaf sid-fault {
              type boolean;
              description
                "Equipment state SID Fault";
            }

            leaf cp-running-fallback-image-fault {
              type boolean;
              description
                "Equipment state CP Running Fallback Image Fault";
            }

            leaf configuration-mismatch {
              type boolean;
              description
                "Equipment state Configuration Mismatch, mixed power card type";
            }

            leaf fan-missing {
              type boolean;
              description
                "Equipment state Fan Missing";
            }

            leaf telemetry-input-1 {
              type boolean;
              description
                "Equipment state Telemetry Input 1";
            }

            leaf telemetry-input-2 {
              type boolean;
              description
                "Equipment state Telemetry Input 2";
            }

            leaf telemetry-input-3 {
              type boolean;
              description
                "Equipment state Telemetry Input 3";
            }

            leaf slot-empty {
              type boolean;
              description
                "Equipment state Slot Empty";
            }

            leaf tx-fault {
              type boolean;
              description
                "Equipment state LOS";
            }

            leaf rx-los {
              type boolean;
              description
                "Equipment state LOS";
            }
          }

          container inventory {
            yang:mount-start "ciena-6500r-amps";
            yang:mount-end "ciena-6500r-amps";
            yang:mount-start "ciena-6500r-chc";
            yang:mount-end "ciena-6500r-chc";
            yang:mount-start "ciena-6500r-circuit-pack";
            yang:mount-end "ciena-6500r-circuit-pack";
            yang:mount-start "ciena-pro-frequencies";
            yang:mount-end "ciena-pro-frequencies";
            yang:mount-start "ciena-6500r-optmons";
            yang:mount-end "ciena-6500r-optmons";
            yang:mount-start "ciena-6500r-pwrmon";
            yang:mount-end "ciena-6500r-pwrmon";
            yang:mount-start "ciena-6500r-osc";
            yang:mount-end "ciena-6500r-osc";
            yang:mount-start "ciena-6500r-pc";
            yang:mount-end "ciena-6500r-pc";
            yang:mount-start "ciena-6500r-ports";
            yang:mount-end "ciena-6500r-ports";
            yang:mount-start "ciena-6500r-voa";
            yang:mount-end "ciena-6500r-voa";
            yang:mount-start "ciena-6500r-ramans";
            yang:mount-end "ciena-6500r-ramans";
            yang:mount-start "ciena-6500r-telemetry";
            yang:mount-end "ciena-6500r-telemetry";
            yang:mount-start "ciena-6500r-otdr";
            yang:mount-end "ciena-6500r-otdr";
            yang:mount-start "ciena-6500r-otdr-card-if";
            yang:mount-end "ciena-6500r-otdr-card-if";
            yang:mount-start "ciena-6500r-links";
            yang:mount-end "ciena-6500r-links";
            yang:mount-start "ciena-6500r-protection";
            yang:mount-end "ciena-6500r-protection";
            yang:mount-start "ciena-6500r-opm";
            yang:mount-end "ciena-6500r-opm";
            yang:mount-start "ciena-6500r-otrx";
            yang:mount-end "ciena-6500r-otrx";
            yang:mount-start "ciena-6500r-wsc";
            yang:mount-end "ciena-6500r-wsc";
            yang:mount-start "ciena-6500r-connection-validation";
            yang:mount-end "ciena-6500r-connection-validation";
            yang:mount-start "ciena-6500r-wss";
            yang:mount-end "ciena-6500r-wss";
            yang:mount-start "ciena-6500r-pwr-profile";
            yang:mount-end "ciena-6500r-pwr-profile";
            yang:mount-start "ciena-6500r-line-assoc";
            yang:mount-end "ciena-6500r-line-assoc";
            yang:mount-start "ciena-6500r-dgff";
            yang:mount-end "ciena-6500r-dgff";
            yang:mount-start "ciena-6500r-tx-proxy";
            yang:mount-end "ciena-6500r-tx-proxy";
            yang:mount-start "ciena-6500r-rx-proxy";
            yang:mount-end "ciena-6500r-rx-proxy";
            yang:mount-start "ciena-6500r-fan";
            yang:mount-end "ciena-6500r-fan";
            yang:mount-start "ciena-6500r-power-supply";
            yang:mount-end "ciena-6500r-power-supply";
            yang:mount-start "ciena-6500r-slots";
            yang:mount-end "ciena-6500r-slots";
            uses ciena-6500r-amps:ciena-6500r-amps-mount-actions;

            uses ciena-6500r-amps:ciena-6500r-amps-mount;

            uses ciena-6500r-chc:ciena-6500r-chc-mount-actions;

            uses ciena-6500r-chc:ciena-6500r-chc-mount;

            uses ciena-6500r-circuit-pack:ciena-6500r-circuit-pack-mount-actions;

            uses ciena-6500r-circuit-pack:ciena-6500r-circuit-pack-mount;

            uses ciena-pro-frequencies:ciena-pro-frequencies-mount-actions;

            uses ciena-pro-frequencies:ciena-pro-frequencies-mount;

            uses ciena-6500r-optmons:ciena-6500r-optmons-mount-actions;

            uses ciena-6500r-optmons:ciena-6500r-optmons-mount;

            uses ciena-6500r-pwrmon:ciena-6500r-pwrmon-mount-actions;

            uses ciena-6500r-pwrmon:ciena-6500r-pwrmon-mount;

            uses ciena-6500r-osc:ciena-6500r-osc-mount-actions;

            uses ciena-6500r-osc:ciena-6500r-osc-mount;

            uses ciena-6500r-pc:ciena-6500r-pc-mount-actions;

            uses ciena-6500r-pc:ciena-6500r-pc-mount;

            uses ciena-6500r-ports:ciena-6500r-ports-mount-actions;

            uses ciena-6500r-ports:ciena-6500r-ports-mount;

            uses ciena-6500r-voa:ciena-6500r-voa-mount-actions;

            uses ciena-6500r-voa:ciena-6500r-voa-mount;

            uses ciena-6500r-ramans:ciena-6500r-ramans-mount-actions;

            uses ciena-6500r-ramans:ciena-6500r-ramans-mount;

            uses ciena-6500r-telemetry:ciena-6500r-telemetry-mount-actions;

            uses ciena-6500r-telemetry:ciena-6500r-telemetry-mount;

            uses ciena-6500r-otdr:ciena-6500r-otdr-mount-actions;

            uses ciena-6500r-otdr:ciena-6500r-otdr-mount;

            uses ciena-6500r-otdr-card-if:ciena-6500r-otdr-card-if-mount-actions;

            uses ciena-6500r-otdr-card-if:ciena-6500r-otdr-card-if-mount;

            uses ciena-6500r-links:ciena-6500r-links-mount-actions;

            uses ciena-6500r-links:ciena-6500r-links-mount;

            uses ciena-6500r-protection:ciena-6500r-protection-mount-actions;

            uses ciena-6500r-protection:ciena-6500r-protection-mount;

            uses ciena-6500r-opm:ciena-6500r-opm-mount-actions;

            uses ciena-6500r-opm:ciena-6500r-opm-mount;

            uses ciena-6500r-otrx:ciena-6500r-otrx-mount-actions;

            uses ciena-6500r-otrx:ciena-6500r-otrx-mount;

            uses ciena-6500r-wsc:ciena-6500r-wsc-mount-actions;

            uses ciena-6500r-wsc:ciena-6500r-wsc-mount;

            uses ciena-6500r-connection-validation:ciena-6500r-connection-validation-mount-actions;

            uses ciena-6500r-connection-validation:ciena-6500r-connection-validation-mount;

            uses ciena-6500r-wss:ciena-6500r-wss-mount-actions;

            uses ciena-6500r-wss:ciena-6500r-wss-mount;

            uses ciena-6500r-pwr-profile:ciena-6500r-pwr-profile-mount-actions;

            uses ciena-6500r-pwr-profile:ciena-6500r-pwr-profile-mount;

            uses ciena-6500r-line-assoc:ciena-6500r-line-assoc-mount-actions;

            uses ciena-6500r-line-assoc:ciena-6500r-line-assoc-mount;

            uses ciena-6500r-dgff:ciena-6500r-dgff-mount-actions;

            uses ciena-6500r-dgff:ciena-6500r-dgff-mount;

            uses ciena-6500r-tx-proxy:ciena-6500r-tx-proxy-mount-actions;

            uses ciena-6500r-tx-proxy:ciena-6500r-tx-proxy-mount;

            uses ciena-6500r-rx-proxy:ciena-6500r-rx-proxy-mount-actions;

            uses ciena-6500r-rx-proxy:ciena-6500r-rx-proxy-mount;

            uses ciena-6500r-fan:ciena-6500r-fan-mount-actions;

            uses ciena-6500r-fan:ciena-6500r-fan-mount;

            uses ciena-6500r-power-supply:ciena-6500r-power-supply-mount-actions;

            uses ciena-6500r-power-supply:ciena-6500r-power-supply-mount;
          }

          container config {
            yang:mount-start "ciena-6500r-amps";
            yang:mount-end "ciena-6500r-amps";
            yang:mount-start "ciena-6500r-chc";
            yang:mount-end "ciena-6500r-chc";
            yang:mount-start "ciena-6500r-plug-defaults";
            yang:mount-end "ciena-6500r-plug-defaults";
            yang:mount-start "ciena-6500r-circuit-pack";
            yang:mount-end "ciena-6500r-circuit-pack";
            yang:mount-start "ciena-pro-frequencies";
            yang:mount-end "ciena-pro-frequencies";
            yang:mount-start "ciena-6500r-optmons";
            yang:mount-end "ciena-6500r-optmons";
            yang:mount-start "ciena-6500r-pwrmon";
            yang:mount-end "ciena-6500r-pwrmon";
            yang:mount-start "ciena-6500r-osc";
            yang:mount-end "ciena-6500r-osc";
            yang:mount-start "ciena-6500r-pc";
            yang:mount-end "ciena-6500r-pc";
            yang:mount-start "ciena-6500r-ports";
            yang:mount-end "ciena-6500r-ports";
            yang:mount-start "ciena-6500r-facility-logical-map";
            yang:mount-end "ciena-6500r-facility-logical-map";
            yang:mount-start "ciena-6500r-voa";
            yang:mount-end "ciena-6500r-voa";
            yang:mount-start "ciena-6500r-ramans";
            yang:mount-end "ciena-6500r-ramans";
            yang:mount-start "ciena-6500r-telemetry";
            yang:mount-end "ciena-6500r-telemetry";
            yang:mount-start "ciena-6500r-otdr";
            yang:mount-end "ciena-6500r-otdr";
            yang:mount-start "ciena-6500r-links";
            yang:mount-end "ciena-6500r-links";
            yang:mount-start "ciena-6500r-protection";
            yang:mount-end "ciena-6500r-protection";
            yang:mount-start "ciena-6500r-opm";
            yang:mount-end "ciena-6500r-opm";
            yang:mount-start "ciena-6500r-otrx";
            yang:mount-end "ciena-6500r-otrx";
            yang:mount-start "ciena-6500r-wsc";
            yang:mount-end "ciena-6500r-wsc";
            yang:mount-start "ciena-6500r-tx-proxy";
            yang:mount-end "ciena-6500r-tx-proxy";
            yang:mount-start "ciena-6500r-connection-validation";
            yang:mount-end "ciena-6500r-connection-validation";
            yang:mount-start "ciena-6500r-wss";
            yang:mount-end "ciena-6500r-wss";
            yang:mount-start "ciena-6500r-pwr-profile";
            yang:mount-end "ciena-6500r-pwr-profile";
            yang:mount-start "ciena-6500r-line-assoc";
            yang:mount-end "ciena-6500r-line-assoc";
            yang:mount-start "ciena-6500r-dgff";
            yang:mount-end "ciena-6500r-dgff";
            yang:mount-start "ciena-6500r-rx-proxy";
            yang:mount-end "ciena-6500r-rx-proxy";
            yang:mount-start "ciena-6500r-optical-control";
            yang:mount-end "ciena-6500r-optical-control";
            yang:mount-start "ciena-pro-alarm-correlation";
            yang:mount-end "ciena-pro-alarm-correlation";
            yang:mount-start "ciena-6500r-fan";
            yang:mount-end "ciena-6500r-fan";
            yang:mount-start "ciena-6500r-power-supply";
            yang:mount-end "ciena-6500r-power-supply";
            yang:mount-start "ciena-6500r-slots";
            yang:mount-end "ciena-6500r-slots";
            uses ciena-6500r-amps:ciena-6500r-amps-mount-actions;

            uses ciena-6500r-amps:ciena-6500r-amps-mount;

            uses ciena-6500r-chc:ciena-6500r-chc-mount-actions;

            uses ciena-6500r-chc:ciena-6500r-chc-mount;

            uses ciena-6500r-plug-defaults:ciena-6500r-plug-defaults-mount-actions;

            uses ciena-6500r-plug-defaults:ciena-6500r-plug-defaults-mount;

            uses ciena-6500r-circuit-pack:ciena-6500r-circuit-pack-mount-actions;

            uses ciena-6500r-circuit-pack:ciena-6500r-circuit-pack-mount;

            uses ciena-pro-frequencies:ciena-pro-frequencies-mount-actions;

            uses ciena-pro-frequencies:ciena-pro-frequencies-mount;

            uses ciena-6500r-optmons:ciena-6500r-optmons-mount-actions;

            uses ciena-6500r-optmons:ciena-6500r-optmons-mount;

            uses ciena-6500r-pwrmon:ciena-6500r-pwrmon-mount-actions;

            uses ciena-6500r-pwrmon:ciena-6500r-pwrmon-mount;

            uses ciena-6500r-osc:ciena-6500r-osc-mount-actions;

            uses ciena-6500r-osc:ciena-6500r-osc-mount;

            uses ciena-6500r-pc:ciena-6500r-pc-mount-actions;

            uses ciena-6500r-pc:ciena-6500r-pc-mount;

            uses ciena-6500r-ports:ciena-6500r-ports-mount-actions;

            uses ciena-6500r-ports:ciena-6500r-ports-mount;

            uses ciena-6500r-facility-logical-map:ciena-6500r-facility-logical-map-mount-actions;

            uses ciena-6500r-facility-logical-map:ciena-6500r-facility-logical-map-mount;

            uses ciena-6500r-voa:ciena-6500r-voa-mount-actions;

            uses ciena-6500r-voa:ciena-6500r-voa-mount;

            uses ciena-6500r-ramans:ciena-6500r-ramans-mount-actions;

            uses ciena-6500r-ramans:ciena-6500r-ramans-mount;

            uses ciena-6500r-telemetry:ciena-6500r-telemetry-mount-actions;

            uses ciena-6500r-telemetry:ciena-6500r-telemetry-mount;

            uses ciena-6500r-otdr:ciena-6500r-otdr-mount-actions;

            uses ciena-6500r-otdr:ciena-6500r-otdr-mount;

            uses ciena-6500r-links:ciena-6500r-links-mount-actions;

            uses ciena-6500r-links:ciena-6500r-links-mount;

            uses ciena-6500r-protection:ciena-6500r-protection-mount-actions;

            uses ciena-6500r-protection:ciena-6500r-protection-mount;

            uses ciena-6500r-opm:ciena-6500r-opm-mount-actions;

            uses ciena-6500r-opm:ciena-6500r-opm-mount;

            uses ciena-6500r-otrx:ciena-6500r-otrx-mount-actions;

            uses ciena-6500r-otrx:ciena-6500r-otrx-mount;

            uses ciena-6500r-wsc:ciena-6500r-wsc-mount-actions;

            uses ciena-6500r-wsc:ciena-6500r-wsc-mount;

            uses ciena-6500r-tx-proxy:ciena-6500r-tx-proxy-mount-actions;

            uses ciena-6500r-tx-proxy:ciena-6500r-tx-proxy-mount;

            uses ciena-6500r-connection-validation:ciena-6500r-connection-validation-mount-actions;

            uses ciena-6500r-connection-validation:ciena-6500r-connection-validation-mount;

            uses ciena-6500r-wss:ciena-6500r-wss-mount-actions;

            uses ciena-6500r-wss:ciena-6500r-wss-mount;

            uses ciena-6500r-pwr-profile:ciena-6500r-pwr-profile-mount-actions;

            uses ciena-6500r-pwr-profile:ciena-6500r-pwr-profile-mount;

            uses ciena-6500r-line-assoc:ciena-6500r-line-assoc-mount-actions;

            uses ciena-6500r-line-assoc:ciena-6500r-line-assoc-mount;

            uses ciena-6500r-dgff:ciena-6500r-dgff-mount-actions;

            uses ciena-6500r-dgff:ciena-6500r-dgff-mount;

            uses ciena-6500r-rx-proxy:ciena-6500r-rx-proxy-mount-actions;

            uses ciena-6500r-rx-proxy:ciena-6500r-rx-proxy-mount;

            uses ciena-6500r-optical-control:ciena-6500r-optical-control-mount-actions;

            uses ciena-6500r-optical-control:ciena-6500r-optical-control-mount;

            uses ciena-pro-alarm-correlation:ciena-pro-alarm-correlation-mount-actions;

            uses ciena-pro-alarm-correlation:ciena-pro-alarm-correlation-mount;

            uses ciena-6500r-fan:ciena-6500r-fan-mount-actions;

            uses ciena-6500r-fan:ciena-6500r-fan-mount;

            uses ciena-6500r-power-supply:ciena-6500r-power-supply-mount-actions;

            uses ciena-6500r-power-supply:ciena-6500r-power-supply-mount;
          }
        }

        action restart {
          input {
            leaf resource {
              type instance-identifier;
              mandatory true;
              description
                "Resource to restart";
            }

            leaf restart-type {
              type enumeration {
                enum "warm" {
                  value 1;
                }
                enum "cold" {
                  value 2;
                }
              }
              mandatory true;
            }
          }

          output {
            uses yang:rpc-result-common;
          }
        }

        action protection-switch {
          input {
            leaf resource {
              type instance-identifier;
              mandatory true;
              description
                "Resource to operate a protection switch";
            }

            leaf switch-action {
              type enumeration {
                enum "release" {
                  value 1;
                }
                enum "manual" {
                  value 2;
                }
                enum "force" {
                  value 3;
                }
                enum "lockout" {
                  value 4;
                }
              }
              mandatory true;
            }
          }

          output {
            uses yang:rpc-result-common;
          }
        }

        action reraise-alarms {
          input {
            leaf resource {
              type instance-identifier;
              mandatory true;
              description
                "Resource to trigger a reraise of alarms";
            }
          }

          output {
            uses yang:rpc-result-common;
          }
        }

        action reraise-protection-switch-events {
          input {
            leaf resource {
              type instance-identifier;
              mandatory true;
              description
                "Resource to trigger a reraise of switch events";
            }
          }

          output {
            uses yang:rpc-result-common;
          }
        }

        action lamp-test {
          input {
            leaf resource {
              type instance-identifier;
              mandatory true;
              description
                "Resource to trigger a lamp test";
            }
          }

          output {
            uses yang:rpc-result-common;
          }
        }

        action snmp-audit {
          input {
            leaf audit-state {
              type enumeration {
                enum "enable" {
                  value 1;
                }
                enum "disable" {
                  value 2;
                }
              }
              mandatory true;
            }
          }
        }

        notification restart-complete {
          description
            "This notification is sent to report the completion of a circuit-pack restart.";
          leaf resource {
            type instance-identifier;
            description
              "Resource which completed the restart.";
          }

          leaf restart-type {
            type ciena-6500r-types:restart-type;
          }

          leaf uptime {
            type string {
              length "1..16";
            }
            description
              "Cumulative uptime since the unit was last restarted (warm or cold), in the format: days:hours:minutes:seconds (DDDD:HH:MM:SS).";
          }

          leaf powered-uptime {
            type string {
              length "1..16";
            }
            description
              "Cumulative time since the card was last powered on, in the format: days:hours:minutes:seconds (DDDD:HH:MM:SS).";
          }
        }
      }

      container config {
        yang:mount-start "ciena-6500r-amps";
        yang:mount-end "ciena-6500r-amps";
        yang:mount-start "ciena-6500r-chc";
        yang:mount-end "ciena-6500r-chc";
        yang:mount-start "ciena-6500r-plug-defaults";
        yang:mount-end "ciena-6500r-plug-defaults";
        yang:mount-start "ciena-6500r-circuit-pack";
        yang:mount-end "ciena-6500r-circuit-pack";
        yang:mount-start "ciena-pro-frequencies";
        yang:mount-end "ciena-pro-frequencies";
        yang:mount-start "ciena-6500r-optmons";
        yang:mount-end "ciena-6500r-optmons";
        yang:mount-start "ciena-6500r-pwrmon";
        yang:mount-end "ciena-6500r-pwrmon";
        yang:mount-start "ciena-6500r-osc";
        yang:mount-end "ciena-6500r-osc";
        yang:mount-start "ciena-6500r-pc";
        yang:mount-end "ciena-6500r-pc";
        yang:mount-start "ciena-6500r-ports";
        yang:mount-end "ciena-6500r-ports";
        yang:mount-start "ciena-6500r-facility-logical-map";
        yang:mount-end "ciena-6500r-facility-logical-map";
        yang:mount-start "ciena-6500r-voa";
        yang:mount-end "ciena-6500r-voa";
        yang:mount-start "ciena-6500r-ramans";
        yang:mount-end "ciena-6500r-ramans";
        yang:mount-start "ciena-6500r-telemetry";
        yang:mount-end "ciena-6500r-telemetry";
        yang:mount-start "ciena-6500r-otdr";
        yang:mount-end "ciena-6500r-otdr";
        yang:mount-start "ciena-6500r-links";
        yang:mount-end "ciena-6500r-links";
        yang:mount-start "ciena-6500r-protection";
        yang:mount-end "ciena-6500r-protection";
        yang:mount-start "ciena-6500r-opm";
        yang:mount-end "ciena-6500r-opm";
        yang:mount-start "ciena-6500r-otrx";
        yang:mount-end "ciena-6500r-otrx";
        yang:mount-start "ciena-6500r-wsc";
        yang:mount-end "ciena-6500r-wsc";
        yang:mount-start "ciena-6500r-tx-proxy";
        yang:mount-end "ciena-6500r-tx-proxy";
        yang:mount-start "ciena-6500r-connection-validation";
        yang:mount-end "ciena-6500r-connection-validation";
        yang:mount-start "ciena-6500r-wss";
        yang:mount-end "ciena-6500r-wss";
        yang:mount-start "ciena-6500r-pwr-profile";
        yang:mount-end "ciena-6500r-pwr-profile";
        yang:mount-start "ciena-6500r-line-assoc";
        yang:mount-end "ciena-6500r-line-assoc";
        yang:mount-start "ciena-6500r-dgff";
        yang:mount-end "ciena-6500r-dgff";
        yang:mount-start "ciena-6500r-rx-proxy";
        yang:mount-end "ciena-6500r-rx-proxy";
        yang:mount-start "ciena-6500r-optical-control";
        yang:mount-end "ciena-6500r-optical-control";
        yang:mount-start "ciena-pro-alarm-correlation";
        yang:mount-end "ciena-pro-alarm-correlation";
        yang:mount-start "ciena-6500r-fan";
        yang:mount-end "ciena-6500r-fan";
        yang:mount-start "ciena-6500r-power-supply";
        yang:mount-end "ciena-6500r-power-supply";
        yang:mount-start "ciena-6500r-slots";
        yang:mount-end "ciena-6500r-slots";
        uses ciena-6500r-amps:ciena-6500r-amps-mount-actions;

        uses ciena-6500r-amps:ciena-6500r-amps-mount;

        uses ciena-6500r-chc:ciena-6500r-chc-mount-actions;

        uses ciena-6500r-chc:ciena-6500r-chc-mount;

        uses ciena-6500r-plug-defaults:ciena-6500r-plug-defaults-mount-actions;

        uses ciena-6500r-plug-defaults:ciena-6500r-plug-defaults-mount;

        uses ciena-6500r-circuit-pack:ciena-6500r-circuit-pack-mount-actions;

        uses ciena-6500r-circuit-pack:ciena-6500r-circuit-pack-mount;

        uses ciena-pro-frequencies:ciena-pro-frequencies-mount-actions;

        uses ciena-pro-frequencies:ciena-pro-frequencies-mount;

        uses ciena-6500r-optmons:ciena-6500r-optmons-mount-actions;

        uses ciena-6500r-optmons:ciena-6500r-optmons-mount;

        uses ciena-6500r-pwrmon:ciena-6500r-pwrmon-mount-actions;

        uses ciena-6500r-pwrmon:ciena-6500r-pwrmon-mount;

        uses ciena-6500r-osc:ciena-6500r-osc-mount-actions;

        uses ciena-6500r-osc:ciena-6500r-osc-mount;

        uses ciena-6500r-pc:ciena-6500r-pc-mount-actions;

        uses ciena-6500r-pc:ciena-6500r-pc-mount;

        uses ciena-6500r-ports:ciena-6500r-ports-mount-actions;

        uses ciena-6500r-ports:ciena-6500r-ports-mount;

        uses ciena-6500r-facility-logical-map:ciena-6500r-facility-logical-map-mount-actions;

        uses ciena-6500r-facility-logical-map:ciena-6500r-facility-logical-map-mount;

        uses ciena-6500r-voa:ciena-6500r-voa-mount-actions;

        uses ciena-6500r-voa:ciena-6500r-voa-mount;

        uses ciena-6500r-ramans:ciena-6500r-ramans-mount-actions;

        uses ciena-6500r-ramans:ciena-6500r-ramans-mount;

        uses ciena-6500r-telemetry:ciena-6500r-telemetry-mount-actions;

        uses ciena-6500r-telemetry:ciena-6500r-telemetry-mount;

        uses ciena-6500r-otdr:ciena-6500r-otdr-mount-actions;

        uses ciena-6500r-otdr:ciena-6500r-otdr-mount;

        uses ciena-6500r-links:ciena-6500r-links-mount-actions;

        uses ciena-6500r-links:ciena-6500r-links-mount;

        uses ciena-6500r-protection:ciena-6500r-protection-mount-actions;

        uses ciena-6500r-protection:ciena-6500r-protection-mount;

        uses ciena-6500r-opm:ciena-6500r-opm-mount-actions;

        uses ciena-6500r-opm:ciena-6500r-opm-mount;

        uses ciena-6500r-otrx:ciena-6500r-otrx-mount-actions;

        uses ciena-6500r-otrx:ciena-6500r-otrx-mount;

        uses ciena-6500r-wsc:ciena-6500r-wsc-mount-actions;

        uses ciena-6500r-wsc:ciena-6500r-wsc-mount;

        uses ciena-6500r-tx-proxy:ciena-6500r-tx-proxy-mount-actions;

        uses ciena-6500r-tx-proxy:ciena-6500r-tx-proxy-mount;

        uses ciena-6500r-connection-validation:ciena-6500r-connection-validation-mount-actions;

        uses ciena-6500r-connection-validation:ciena-6500r-connection-validation-mount;

        uses ciena-6500r-wss:ciena-6500r-wss-mount-actions;

        uses ciena-6500r-wss:ciena-6500r-wss-mount;

        uses ciena-6500r-pwr-profile:ciena-6500r-pwr-profile-mount-actions;

        uses ciena-6500r-pwr-profile:ciena-6500r-pwr-profile-mount;

        uses ciena-6500r-line-assoc:ciena-6500r-line-assoc-mount-actions;

        uses ciena-6500r-line-assoc:ciena-6500r-line-assoc-mount;

        uses ciena-6500r-dgff:ciena-6500r-dgff-mount-actions;

        uses ciena-6500r-dgff:ciena-6500r-dgff-mount;

        uses ciena-6500r-rx-proxy:ciena-6500r-rx-proxy-mount-actions;

        uses ciena-6500r-rx-proxy:ciena-6500r-rx-proxy-mount;

        uses ciena-6500r-optical-control:ciena-6500r-optical-control-mount-actions;

        uses ciena-6500r-optical-control:ciena-6500r-optical-control-mount;

        uses ciena-pro-alarm-correlation:ciena-pro-alarm-correlation-mount-actions;

        uses ciena-pro-alarm-correlation:ciena-pro-alarm-correlation-mount;

        uses ciena-6500r-fan:ciena-6500r-fan-mount-actions;

        uses ciena-6500r-fan:ciena-6500r-fan-mount;

        uses ciena-6500r-power-supply:ciena-6500r-power-supply-mount-actions;

        uses ciena-6500r-power-supply:ciena-6500r-power-supply-mount;

        list slots {
          key "name";
          leaf name {
            type ciena-6500r-types:object-name;
            description
              "The name of the slot.";
          }

          leaf card-present {
            type boolean;
            config false;
            description
              "The slot is serving as the host slot for a card that is physically present.";
          }

          leaf card-provisioned {
            type boolean;
            config false;
            description
              "The slot has been provisioned as the host slot for a card.";
          }

          leaf slot-occupied {
            type boolean;
            config false;
            description
              "A multi-slot card or filler is physically present in the slot, but is not the host slot.";
          }

          leaf slot-reserved {
            type boolean;
            config false;
            description
              "The slot has been provisioned for a multi-slot card, but is not the host slot.";
          }

          leaf parent {
            type instance-identifier;
            description
              "Parent object, values can be a shelf or another circuit pack if it is subslot or pluggable ";
          }

          leaf form-factor {
            type enumeration {
              enum "backplane";
              enum "access-panel";
              enum "ctm";
              enum "fan";
              enum "power";
              enum "i2c";
              enum "passive";
              enum "sfp";
              enum "sfpplus";
              enum "cfp";
              enum "cfp2";
              enum "xfp";
              enum "qsfp";
              enum "qsfp28";
              enum "ctm-front-panel";
              enum "backplane-300mm";
            }
          }

          leaf auto-provisioning {
            type boolean;
            description
              "Auto-provsioning support.";
          }

          list backplane-card-type {
            key "backplane-card-type";
            config false;
            uses card-info-grouping;
          }

          container diagnostic {
            config false;
            description
              "Diagnostic state";
            leaf unknown {
              type boolean;
              description
                "Equipment state unknown";
            }

            leaf mismatch {
              type boolean;
              description
                "Equipment state mismatch";
            }

            leaf missing {
              type boolean;
              description
                "Equipment state missing";
            }

            leaf filler-missing {
              type boolean;
              description
                "Equipment state filler-missing";
            }

            leaf prov-incompatible {
              type boolean;
              description
                "Equipment state prov-incompatible";
            }

            leaf auto-provisioning-mismatch {
              type boolean;
              description
                "Equipment state Auto-Provisioning Mismatch";
            }

            leaf hi-temp-warning {
              type boolean;
              description
                "Equipment state High Temperature warning";
            }

            leaf hi-temp {
              type boolean;
              description
                "Equipment state High Temperature";
            }

            leaf power-feed-failure {
              type boolean;
              description
                "Equipment state power feed failure";
            }

            leaf failed {
              type boolean;
              description
                "Equipment state circuit pack fail";
            }

            leaf intercard-suspected {
              type boolean;
              description
                "Equipment state Intercard Suspected Fault";
            }

            leaf latch-open {
              type boolean;
              description
                "Equipment state Latch Open";
            }

            leaf disk-usage-75 {
              type boolean;
              description
                "Equipment state Disk Usage at 75 percent";
            }

            leaf disk-usage-90 {
              type boolean;
              description
                "Equipment state Disk Usage at 90 percent";
            }

            leaf disk-usage-100 {
              type boolean;
              description
                "Equipment state Disk Usage Full";
            }

            leaf corrupt-inventory-fault {
              type boolean;
              description
                "Equipment state Corrupt Inventory Fault";
            }

            leaf slc-force-fail {
              type boolean;
              description
                "Equipment state SLC Force Fail";
            }

            leaf lan-port-down {
              type boolean;
              description
                "Equipment state Lan Port Down";
            }

            leaf software-subsystem-fail {
              type boolean;
              description
                "Equipment state Software Subsystem Fail";
            }

            leaf hardware-subsystem-fail {
              type boolean;
              description
                "Equipment state Hardware Subsystem Fail";
            }

            leaf low-voltage-fault {
              type boolean;
              description
                "Equipment state Low Voltage Fault";
            }

            leaf power-failure-fault {
              type boolean;
              description
                "Equipment state Power Failure Fault";
            }

            leaf boot-fail-fault {
              type boolean;
              description
                "Equipment state Boot Fail Fault";
            }

            leaf internal-management-comms-suspected {
              type boolean;
              description
                "Equipment state Internal Management Comms Suspected";
            }

            leaf sid-fault {
              type boolean;
              description
                "Equipment state SID Fault";
            }

            leaf cp-running-fallback-image-fault {
              type boolean;
              description
                "Equipment state CP Running Fallback Image Fault";
            }

            leaf configuration-mismatch {
              type boolean;
              description
                "Equipment state Configuration Mismatch, mixed power card type";
            }

            leaf fan-missing {
              type boolean;
              description
                "Equipment state Fan Missing";
            }

            leaf telemetry-input-1 {
              type boolean;
              description
                "Equipment state Telemetry Input 1";
            }

            leaf telemetry-input-2 {
              type boolean;
              description
                "Equipment state Telemetry Input 2";
            }

            leaf telemetry-input-3 {
              type boolean;
              description
                "Equipment state Telemetry Input 3";
            }

            leaf slot-empty {
              type boolean;
              description
                "Equipment state Slot Empty";
            }

            leaf tx-fault {
              type boolean;
              description
                "Equipment state LOS";
            }

            leaf rx-los {
              type boolean;
              description
                "Equipment state LOS";
            }
          }

          container inventory {
            yang:mount-start "ciena-6500r-amps";
            yang:mount-end "ciena-6500r-amps";
            yang:mount-start "ciena-6500r-chc";
            yang:mount-end "ciena-6500r-chc";
            yang:mount-start "ciena-6500r-circuit-pack";
            yang:mount-end "ciena-6500r-circuit-pack";
            yang:mount-start "ciena-pro-frequencies";
            yang:mount-end "ciena-pro-frequencies";
            yang:mount-start "ciena-6500r-optmons";
            yang:mount-end "ciena-6500r-optmons";
            yang:mount-start "ciena-6500r-pwrmon";
            yang:mount-end "ciena-6500r-pwrmon";
            yang:mount-start "ciena-6500r-osc";
            yang:mount-end "ciena-6500r-osc";
            yang:mount-start "ciena-6500r-pc";
            yang:mount-end "ciena-6500r-pc";
            yang:mount-start "ciena-6500r-ports";
            yang:mount-end "ciena-6500r-ports";
            yang:mount-start "ciena-6500r-voa";
            yang:mount-end "ciena-6500r-voa";
            yang:mount-start "ciena-6500r-ramans";
            yang:mount-end "ciena-6500r-ramans";
            yang:mount-start "ciena-6500r-telemetry";
            yang:mount-end "ciena-6500r-telemetry";
            yang:mount-start "ciena-6500r-otdr";
            yang:mount-end "ciena-6500r-otdr";
            yang:mount-start "ciena-6500r-otdr-card-if";
            yang:mount-end "ciena-6500r-otdr-card-if";
            yang:mount-start "ciena-6500r-links";
            yang:mount-end "ciena-6500r-links";
            yang:mount-start "ciena-6500r-protection";
            yang:mount-end "ciena-6500r-protection";
            yang:mount-start "ciena-6500r-opm";
            yang:mount-end "ciena-6500r-opm";
            yang:mount-start "ciena-6500r-otrx";
            yang:mount-end "ciena-6500r-otrx";
            yang:mount-start "ciena-6500r-wsc";
            yang:mount-end "ciena-6500r-wsc";
            yang:mount-start "ciena-6500r-connection-validation";
            yang:mount-end "ciena-6500r-connection-validation";
            yang:mount-start "ciena-6500r-wss";
            yang:mount-end "ciena-6500r-wss";
            yang:mount-start "ciena-6500r-pwr-profile";
            yang:mount-end "ciena-6500r-pwr-profile";
            yang:mount-start "ciena-6500r-line-assoc";
            yang:mount-end "ciena-6500r-line-assoc";
            yang:mount-start "ciena-6500r-dgff";
            yang:mount-end "ciena-6500r-dgff";
            yang:mount-start "ciena-6500r-tx-proxy";
            yang:mount-end "ciena-6500r-tx-proxy";
            yang:mount-start "ciena-6500r-rx-proxy";
            yang:mount-end "ciena-6500r-rx-proxy";
            yang:mount-start "ciena-6500r-fan";
            yang:mount-end "ciena-6500r-fan";
            yang:mount-start "ciena-6500r-power-supply";
            yang:mount-end "ciena-6500r-power-supply";
            yang:mount-start "ciena-6500r-slots";
            yang:mount-end "ciena-6500r-slots";
            uses ciena-6500r-amps:ciena-6500r-amps-mount-actions;

            uses ciena-6500r-amps:ciena-6500r-amps-mount;

            uses ciena-6500r-chc:ciena-6500r-chc-mount-actions;

            uses ciena-6500r-chc:ciena-6500r-chc-mount;

            uses ciena-6500r-circuit-pack:ciena-6500r-circuit-pack-mount-actions;

            uses ciena-6500r-circuit-pack:ciena-6500r-circuit-pack-mount;

            uses ciena-pro-frequencies:ciena-pro-frequencies-mount-actions;

            uses ciena-pro-frequencies:ciena-pro-frequencies-mount;

            uses ciena-6500r-optmons:ciena-6500r-optmons-mount-actions;

            uses ciena-6500r-optmons:ciena-6500r-optmons-mount;

            uses ciena-6500r-pwrmon:ciena-6500r-pwrmon-mount-actions;

            uses ciena-6500r-pwrmon:ciena-6500r-pwrmon-mount;

            uses ciena-6500r-osc:ciena-6500r-osc-mount-actions;

            uses ciena-6500r-osc:ciena-6500r-osc-mount;

            uses ciena-6500r-pc:ciena-6500r-pc-mount-actions;

            uses ciena-6500r-pc:ciena-6500r-pc-mount;

            uses ciena-6500r-ports:ciena-6500r-ports-mount-actions;

            uses ciena-6500r-ports:ciena-6500r-ports-mount;

            uses ciena-6500r-voa:ciena-6500r-voa-mount-actions;

            uses ciena-6500r-voa:ciena-6500r-voa-mount;

            uses ciena-6500r-ramans:ciena-6500r-ramans-mount-actions;

            uses ciena-6500r-ramans:ciena-6500r-ramans-mount;

            uses ciena-6500r-telemetry:ciena-6500r-telemetry-mount-actions;

            uses ciena-6500r-telemetry:ciena-6500r-telemetry-mount;

            uses ciena-6500r-otdr:ciena-6500r-otdr-mount-actions;

            uses ciena-6500r-otdr:ciena-6500r-otdr-mount;

            uses ciena-6500r-otdr-card-if:ciena-6500r-otdr-card-if-mount-actions;

            uses ciena-6500r-otdr-card-if:ciena-6500r-otdr-card-if-mount;

            uses ciena-6500r-links:ciena-6500r-links-mount-actions;

            uses ciena-6500r-links:ciena-6500r-links-mount;

            uses ciena-6500r-protection:ciena-6500r-protection-mount-actions;

            uses ciena-6500r-protection:ciena-6500r-protection-mount;

            uses ciena-6500r-opm:ciena-6500r-opm-mount-actions;

            uses ciena-6500r-opm:ciena-6500r-opm-mount;

            uses ciena-6500r-otrx:ciena-6500r-otrx-mount-actions;

            uses ciena-6500r-otrx:ciena-6500r-otrx-mount;

            uses ciena-6500r-wsc:ciena-6500r-wsc-mount-actions;

            uses ciena-6500r-wsc:ciena-6500r-wsc-mount;

            uses ciena-6500r-connection-validation:ciena-6500r-connection-validation-mount-actions;

            uses ciena-6500r-connection-validation:ciena-6500r-connection-validation-mount;

            uses ciena-6500r-wss:ciena-6500r-wss-mount-actions;

            uses ciena-6500r-wss:ciena-6500r-wss-mount;

            uses ciena-6500r-pwr-profile:ciena-6500r-pwr-profile-mount-actions;

            uses ciena-6500r-pwr-profile:ciena-6500r-pwr-profile-mount;

            uses ciena-6500r-line-assoc:ciena-6500r-line-assoc-mount-actions;

            uses ciena-6500r-line-assoc:ciena-6500r-line-assoc-mount;

            uses ciena-6500r-dgff:ciena-6500r-dgff-mount-actions;

            uses ciena-6500r-dgff:ciena-6500r-dgff-mount;

            uses ciena-6500r-tx-proxy:ciena-6500r-tx-proxy-mount-actions;

            uses ciena-6500r-tx-proxy:ciena-6500r-tx-proxy-mount;

            uses ciena-6500r-rx-proxy:ciena-6500r-rx-proxy-mount-actions;

            uses ciena-6500r-rx-proxy:ciena-6500r-rx-proxy-mount;

            uses ciena-6500r-fan:ciena-6500r-fan-mount-actions;

            uses ciena-6500r-fan:ciena-6500r-fan-mount;

            uses ciena-6500r-power-supply:ciena-6500r-power-supply-mount-actions;

            uses ciena-6500r-power-supply:ciena-6500r-power-supply-mount;
          }

          container config {
            yang:mount-start "ciena-6500r-amps";
            yang:mount-end "ciena-6500r-amps";
            yang:mount-start "ciena-6500r-chc";
            yang:mount-end "ciena-6500r-chc";
            yang:mount-start "ciena-6500r-plug-defaults";
            yang:mount-end "ciena-6500r-plug-defaults";
            yang:mount-start "ciena-6500r-circuit-pack";
            yang:mount-end "ciena-6500r-circuit-pack";
            yang:mount-start "ciena-pro-frequencies";
            yang:mount-end "ciena-pro-frequencies";
            yang:mount-start "ciena-6500r-optmons";
            yang:mount-end "ciena-6500r-optmons";
            yang:mount-start "ciena-6500r-pwrmon";
            yang:mount-end "ciena-6500r-pwrmon";
            yang:mount-start "ciena-6500r-osc";
            yang:mount-end "ciena-6500r-osc";
            yang:mount-start "ciena-6500r-pc";
            yang:mount-end "ciena-6500r-pc";
            yang:mount-start "ciena-6500r-ports";
            yang:mount-end "ciena-6500r-ports";
            yang:mount-start "ciena-6500r-facility-logical-map";
            yang:mount-end "ciena-6500r-facility-logical-map";
            yang:mount-start "ciena-6500r-voa";
            yang:mount-end "ciena-6500r-voa";
            yang:mount-start "ciena-6500r-ramans";
            yang:mount-end "ciena-6500r-ramans";
            yang:mount-start "ciena-6500r-telemetry";
            yang:mount-end "ciena-6500r-telemetry";
            yang:mount-start "ciena-6500r-otdr";
            yang:mount-end "ciena-6500r-otdr";
            yang:mount-start "ciena-6500r-links";
            yang:mount-end "ciena-6500r-links";
            yang:mount-start "ciena-6500r-protection";
            yang:mount-end "ciena-6500r-protection";
            yang:mount-start "ciena-6500r-opm";
            yang:mount-end "ciena-6500r-opm";
            yang:mount-start "ciena-6500r-otrx";
            yang:mount-end "ciena-6500r-otrx";
            yang:mount-start "ciena-6500r-wsc";
            yang:mount-end "ciena-6500r-wsc";
            yang:mount-start "ciena-6500r-tx-proxy";
            yang:mount-end "ciena-6500r-tx-proxy";
            yang:mount-start "ciena-6500r-connection-validation";
            yang:mount-end "ciena-6500r-connection-validation";
            yang:mount-start "ciena-6500r-wss";
            yang:mount-end "ciena-6500r-wss";
            yang:mount-start "ciena-6500r-pwr-profile";
            yang:mount-end "ciena-6500r-pwr-profile";
            yang:mount-start "ciena-6500r-line-assoc";
            yang:mount-end "ciena-6500r-line-assoc";
            yang:mount-start "ciena-6500r-dgff";
            yang:mount-end "ciena-6500r-dgff";
            yang:mount-start "ciena-6500r-rx-proxy";
            yang:mount-end "ciena-6500r-rx-proxy";
            yang:mount-start "ciena-6500r-optical-control";
            yang:mount-end "ciena-6500r-optical-control";
            yang:mount-start "ciena-pro-alarm-correlation";
            yang:mount-end "ciena-pro-alarm-correlation";
            yang:mount-start "ciena-6500r-fan";
            yang:mount-end "ciena-6500r-fan";
            yang:mount-start "ciena-6500r-power-supply";
            yang:mount-end "ciena-6500r-power-supply";
            yang:mount-start "ciena-6500r-slots";
            yang:mount-end "ciena-6500r-slots";
            uses ciena-6500r-amps:ciena-6500r-amps-mount-actions;

            uses ciena-6500r-amps:ciena-6500r-amps-mount;

            uses ciena-6500r-chc:ciena-6500r-chc-mount-actions;

            uses ciena-6500r-chc:ciena-6500r-chc-mount;

            uses ciena-6500r-plug-defaults:ciena-6500r-plug-defaults-mount-actions;

            uses ciena-6500r-plug-defaults:ciena-6500r-plug-defaults-mount;

            uses ciena-6500r-circuit-pack:ciena-6500r-circuit-pack-mount-actions;

            uses ciena-6500r-circuit-pack:ciena-6500r-circuit-pack-mount;

            uses ciena-pro-frequencies:ciena-pro-frequencies-mount-actions;

            uses ciena-pro-frequencies:ciena-pro-frequencies-mount;

            uses ciena-6500r-optmons:ciena-6500r-optmons-mount-actions;

            uses ciena-6500r-optmons:ciena-6500r-optmons-mount;

            uses ciena-6500r-pwrmon:ciena-6500r-pwrmon-mount-actions;

            uses ciena-6500r-pwrmon:ciena-6500r-pwrmon-mount;

            uses ciena-6500r-osc:ciena-6500r-osc-mount-actions;

            uses ciena-6500r-osc:ciena-6500r-osc-mount;

            uses ciena-6500r-pc:ciena-6500r-pc-mount-actions;

            uses ciena-6500r-pc:ciena-6500r-pc-mount;

            uses ciena-6500r-ports:ciena-6500r-ports-mount-actions;

            uses ciena-6500r-ports:ciena-6500r-ports-mount;

            uses ciena-6500r-facility-logical-map:ciena-6500r-facility-logical-map-mount-actions;

            uses ciena-6500r-facility-logical-map:ciena-6500r-facility-logical-map-mount;

            uses ciena-6500r-voa:ciena-6500r-voa-mount-actions;

            uses ciena-6500r-voa:ciena-6500r-voa-mount;

            uses ciena-6500r-ramans:ciena-6500r-ramans-mount-actions;

            uses ciena-6500r-ramans:ciena-6500r-ramans-mount;

            uses ciena-6500r-telemetry:ciena-6500r-telemetry-mount-actions;

            uses ciena-6500r-telemetry:ciena-6500r-telemetry-mount;

            uses ciena-6500r-otdr:ciena-6500r-otdr-mount-actions;

            uses ciena-6500r-otdr:ciena-6500r-otdr-mount;

            uses ciena-6500r-links:ciena-6500r-links-mount-actions;

            uses ciena-6500r-links:ciena-6500r-links-mount;

            uses ciena-6500r-protection:ciena-6500r-protection-mount-actions;

            uses ciena-6500r-protection:ciena-6500r-protection-mount;

            uses ciena-6500r-opm:ciena-6500r-opm-mount-actions;

            uses ciena-6500r-opm:ciena-6500r-opm-mount;

            uses ciena-6500r-otrx:ciena-6500r-otrx-mount-actions;

            uses ciena-6500r-otrx:ciena-6500r-otrx-mount;

            uses ciena-6500r-wsc:ciena-6500r-wsc-mount-actions;

            uses ciena-6500r-wsc:ciena-6500r-wsc-mount;

            uses ciena-6500r-tx-proxy:ciena-6500r-tx-proxy-mount-actions;

            uses ciena-6500r-tx-proxy:ciena-6500r-tx-proxy-mount;

            uses ciena-6500r-connection-validation:ciena-6500r-connection-validation-mount-actions;

            uses ciena-6500r-connection-validation:ciena-6500r-connection-validation-mount;

            uses ciena-6500r-wss:ciena-6500r-wss-mount-actions;

            uses ciena-6500r-wss:ciena-6500r-wss-mount;

            uses ciena-6500r-pwr-profile:ciena-6500r-pwr-profile-mount-actions;

            uses ciena-6500r-pwr-profile:ciena-6500r-pwr-profile-mount;

            uses ciena-6500r-line-assoc:ciena-6500r-line-assoc-mount-actions;

            uses ciena-6500r-line-assoc:ciena-6500r-line-assoc-mount;

            uses ciena-6500r-dgff:ciena-6500r-dgff-mount-actions;

            uses ciena-6500r-dgff:ciena-6500r-dgff-mount;

            uses ciena-6500r-rx-proxy:ciena-6500r-rx-proxy-mount-actions;

            uses ciena-6500r-rx-proxy:ciena-6500r-rx-proxy-mount;

            uses ciena-6500r-optical-control:ciena-6500r-optical-control-mount-actions;

            uses ciena-6500r-optical-control:ciena-6500r-optical-control-mount;

            uses ciena-pro-alarm-correlation:ciena-pro-alarm-correlation-mount-actions;

            uses ciena-pro-alarm-correlation:ciena-pro-alarm-correlation-mount;

            uses ciena-6500r-fan:ciena-6500r-fan-mount-actions;

            uses ciena-6500r-fan:ciena-6500r-fan-mount;

            uses ciena-6500r-power-supply:ciena-6500r-power-supply-mount-actions;

            uses ciena-6500r-power-supply:ciena-6500r-power-supply-mount;
          }
        }

        action restart {
          input {
            leaf resource {
              type instance-identifier;
              mandatory true;
              description
                "Resource to restart";
            }

            leaf restart-type {
              type enumeration {
                enum "warm" {
                  value 1;
                }
                enum "cold" {
                  value 2;
                }
              }
              mandatory true;
            }
          }

          output {
            uses yang:rpc-result-common;
          }
        }

        action protection-switch {
          input {
            leaf resource {
              type instance-identifier;
              mandatory true;
              description
                "Resource to operate a protection switch";
            }

            leaf switch-action {
              type enumeration {
                enum "release" {
                  value 1;
                }
                enum "manual" {
                  value 2;
                }
                enum "force" {
                  value 3;
                }
                enum "lockout" {
                  value 4;
                }
              }
              mandatory true;
            }
          }

          output {
            uses yang:rpc-result-common;
          }
        }

        action reraise-alarms {
          input {
            leaf resource {
              type instance-identifier;
              mandatory true;
              description
                "Resource to trigger a reraise of alarms";
            }
          }

          output {
            uses yang:rpc-result-common;
          }
        }

        action reraise-protection-switch-events {
          input {
            leaf resource {
              type instance-identifier;
              mandatory true;
              description
                "Resource to trigger a reraise of switch events";
            }
          }

          output {
            uses yang:rpc-result-common;
          }
        }

        action lamp-test {
          input {
            leaf resource {
              type instance-identifier;
              mandatory true;
              description
                "Resource to trigger a lamp test";
            }
          }

          output {
            uses yang:rpc-result-common;
          }
        }

        action snmp-audit {
          input {
            leaf audit-state {
              type enumeration {
                enum "enable" {
                  value 1;
                }
                enum "disable" {
                  value 2;
                }
              }
              mandatory true;
            }
          }
        }

        notification restart-complete {
          description
            "This notification is sent to report the completion of a circuit-pack restart.";
          leaf resource {
            type instance-identifier;
            description
              "Resource which completed the restart.";
          }

          leaf restart-type {
            type ciena-6500r-types:restart-type;
          }

          leaf uptime {
            type string {
              length "1..16";
            }
            description
              "Cumulative uptime since the unit was last restarted (warm or cold), in the format: days:hours:minutes:seconds (DDDD:HH:MM:SS).";
          }

          leaf powered-uptime {
            type string {
              length "1..16";
            }
            description
              "Cumulative time since the card was last powered on, in the format: days:hours:minutes:seconds (DDDD:HH:MM:SS).";
          }
        }
      }
    }

    notification restart-complete {
      description
        "This notification is sent to report the completion of a circuit-pack restart.";
      leaf resource {
        type instance-identifier;
        description
          "Resource which completed the restart.";
      }

      leaf restart-type {
        type ciena-6500r-types:restart-type;
      }

      leaf uptime {
        type string {
          length "1..16";
        }
        description
          "Cumulative uptime since the unit was last restarted (warm or cold), in the format: days:hours:minutes:seconds (DDDD:HH:MM:SS).";
      }

      leaf powered-uptime {
        type string {
          length "1..16";
        }
        description
          "Cumulative time since the card was last powered on, in the format: days:hours:minutes:seconds (DDDD:HH:MM:SS).";
      }
    }
  }

  grouping ciena-6500r-slots-mount-actions {
    action restart {
      input {
        leaf resource {
          type instance-identifier;
          mandatory true;
          description
            "Resource to restart";
        }

        leaf restart-type {
          type enumeration {
            enum "warm" {
              value 1;
            }
            enum "cold" {
              value 2;
            }
          }
          mandatory true;
        }
      }

      output {
        uses yang:rpc-result-common;
      }
    }

    action protection-switch {
      input {
        leaf resource {
          type instance-identifier;
          mandatory true;
          description
            "Resource to operate a protection switch";
        }

        leaf switch-action {
          type enumeration {
            enum "release" {
              value 1;
            }
            enum "manual" {
              value 2;
            }
            enum "force" {
              value 3;
            }
            enum "lockout" {
              value 4;
            }
          }
          mandatory true;
        }
      }

      output {
        uses yang:rpc-result-common;
      }
    }

    action reraise-alarms {
      input {
        leaf resource {
          type instance-identifier;
          mandatory true;
          description
            "Resource to trigger a reraise of alarms";
        }
      }

      output {
        uses yang:rpc-result-common;
      }
    }

    action reraise-protection-switch-events {
      input {
        leaf resource {
          type instance-identifier;
          mandatory true;
          description
            "Resource to trigger a reraise of switch events";
        }
      }

      output {
        uses yang:rpc-result-common;
      }
    }

    action lamp-test {
      input {
        leaf resource {
          type instance-identifier;
          mandatory true;
          description
            "Resource to trigger a lamp test";
        }
      }

      output {
        uses yang:rpc-result-common;
      }
    }

    action snmp-audit {
      input {
        leaf audit-state {
          type enumeration {
            enum "enable" {
              value 1;
            }
            enum "disable" {
              value 2;
            }
          }
          mandatory true;
        }
      }
    }
  }

  uses ciena-6500r-slots-mount;

  rpc restart {
    input {
      leaf resource {
        type instance-identifier;
        mandatory true;
        description
          "Resource to restart";
      }

      leaf restart-type {
        type enumeration {
          enum "warm" {
            value 1;
          }
          enum "cold" {
            value 2;
          }
        }
        mandatory true;
      }
    }

    output {
      uses yang:rpc-result-common;
    }
  }

  rpc protection-switch {
    input {
      leaf resource {
        type instance-identifier;
        mandatory true;
        description
          "Resource to operate a protection switch";
      }

      leaf switch-action {
        type enumeration {
          enum "release" {
            value 1;
          }
          enum "manual" {
            value 2;
          }
          enum "force" {
            value 3;
          }
          enum "lockout" {
            value 4;
          }
        }
        mandatory true;
      }
    }

    output {
      uses yang:rpc-result-common;
    }
  }

  rpc reraise-alarms {
    input {
      leaf resource {
        type instance-identifier;
        mandatory true;
        description
          "Resource to trigger a reraise of alarms";
      }
    }

    output {
      uses yang:rpc-result-common;
    }
  }

  rpc reraise-protection-switch-events {
    input {
      leaf resource {
        type instance-identifier;
        mandatory true;
        description
          "Resource to trigger a reraise of switch events";
      }
    }

    output {
      uses yang:rpc-result-common;
    }
  }

  rpc lamp-test {
    input {
      leaf resource {
        type instance-identifier;
        mandatory true;
        description
          "Resource to trigger a lamp test";
      }
    }

    output {
      uses yang:rpc-result-common;
    }
  }

  rpc snmp-audit {
    input {
      leaf audit-state {
        type enumeration {
          enum "enable" {
            value 1;
          }
          enum "disable" {
            value 2;
          }
        }
        mandatory true;
      }
    }
  }
}
