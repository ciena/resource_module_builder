module ciena-6500r-system-debug {
  namespace "urn:ciena:params:xml:ns:yang:ciena-6500r-system-debug";
  prefix system-debug;

  import ciena-6500r-types {
    prefix ciena-6500r-types;
  }
  import ciena-common-version {
    prefix version;
  }
  import ciena-ddy-msg {
    prefix ciena-ddy-msg;
  }

  organization
    "Ciena Corporation";
  contact
    "Web URL: http://www.ciena.com/
     Postal:  7035 Ridge Road
              Hanover, Maryland 21076
              U.S.A.
     Phone:   +1 800-921-1144
     Fax:     +1 410-694-5750";
  description
    "This module provides debug capabilties for 6500r-system";

  revision 2022-07-13 {
    description
      "6500r-series Release 3.0
       Move identity alarmable to private yang";
    version:version "version" {
      version:string "2.0.0";
    }
  }
  revision 2020-10-05 {
    description
      "6500r-series Release 2.1
       Initial version";
    version:version "version" {
      version:string "1.0.0";
    }
  }

  identity alarmable {
    base ciena-ddy-msg:ddm-importance;
    description
      "If this service fails, this indicates it should be alarmed with
       a 'Software service failed' alarm.";
  }

  rpc set-spectrum-license-debug {
    input {
      leaf audit-cadence {
        type uint16;
        description
          "Audit cadence in seconds. A value of 0 will reset to system default";
      }
      leaf num-audits-before-refresh {
        type uint8;
        description
          "Number of audit cycles before refresh. A value of 0 will reset to system default";
      }
      leaf num-audits-before-nw-avail-refresh {
        type uint8;
        description
          "Number of audit cycles before network-available count refresh.
           A value of 0 will reset to system default";
      }
      leaf license-acceleration-factor {
        type uint8;
        description
          "local-used multiplier which accelerates the number of licenses
           to acquire. ie. 5 will acquire 5 per local-used
           A value of 0 will reset to system default";
      }
    }
  }

  rpc get-spectrum-license-debug {
    output {
      leaf audit-cadence {
        type uint16;
        description
          "Audit cadence in seconds";
      }
      leaf num-audits-before-refresh {
        type uint8;
        description
          "Number of audit cycles before refresh";
      }
      leaf num-audits-before-nw-avail-refresh {
        type uint8;
        description
          "Number of audit cycles before network-available count refresh";
      }
      leaf license-acceleration-factor {
        type uint8;
        description
          "local-used multiplier to accelerate the number of licenses to acquire";
      }
    }
  }
}
