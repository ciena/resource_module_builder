module ciena-common-deadlines {
  namespace "urn:ciena:params:xml:ns:yang:ciena-common-deadlines";
  prefix deadlines;

  import ciena-common-version {
    prefix version;
  }
  import ciena-common-exceptions {
    prefix except;
  }

  organization
    "Ciena Corporation";
  contact
    "Web URL: http://www.ciena.com/
     Postal:  7035 Ridge Road
             Hanover, Maryland 21076
             U.S.A.
     Phone:   +1 800-921-1144
     Fax:     +1 410-694-5750";
  description
    "Holds defintions to support deadlines.";

  revision 2021-05-02 {
    description
      "Initial revision.";
    reference
      "";
    version:version "version" {
      version:string "1.0.0";
    }
  }

  identity action-timeout {
    base except:exception;
    description
      "An exception type for timeouts.";
  }

  identity action-canceled {
    base except:exception;
    description
      "An exception type for canceled actions.";
  }
}
