module ciena-pro-netconf-debug {
  namespace "urn:ciena:params:xml:ns:yang:ciena-pro-netconf-debug";
  prefix pro-netconf-debug;

  import ciena-common-yang {
    prefix yang;
  }
  import ciena-common-version {
    prefix version;
  }

  organization
    "Ciena";
  contact
    "Web URL: http://www.ciena.com/
     Postal:  7035 Ridge Road
             Hanover, Maryland 21076
             U.S.A.
     Phone:   +1 800-921-1144
     Fax:     +1 410-694-5750";
  description
    "Options for Netconf messaging protocol.";

  revision 2022-04-04 {
    description
      "Initial revision";
    version:version "version" {
      version:string "1.0.0";
    }
  }

  rpc execute-rpc {
    description
      "Execute Raw RPC as raw XML input and return the response";
    input {
      leaf domain {
        description
          "Name of domain to execute RPC against.";
        type string;
      }
      leaf request {
        description
          "XML RPC Request to be sent via Netconf.";
        type string {
          yang:stringptr "true";
        }
      }
      leaf timeout {
        description
          "Timeout to wait for rpc response (in milliseconds).";
        type uint32;
        units "msecs";
        default "60000";
      }
    }
    output {
      uses yang:rpc-result-common;
      leaf response {
        description
          "XML RPC Response.";
        type string {
          yang:stringptr "true";
        }
      }
    }
  }
}
