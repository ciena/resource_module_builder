module ciena-osrp-common-osrp-object {
  yang-version 1.1;
  namespace "urn:ciena:params:xml:ns:yang:ciena-osrp-common-osrp-object";
  prefix ciena-osrp-common-osrp-object;

  import ciena-osrp-osrp-node {
    prefix ciena-osrp-osrp-node;
  }
  import ciena-osrp-osrp-link {
    prefix ciena-osrp-osrp-link;
  }
  import ciena-osrp-dtl {
    prefix ciena-osrp-dtl;
  }
  import ciena-osrp-dtl-set {
    prefix ciena-osrp-dtl-set;
  }
  import ciena-osrp-snc {
    prefix ciena-osrp-snc;
  }
  import ciena-osrp-snc-group {
    prefix ciena-osrp-snc-group;
  }
  import ciena-common-yang {
    prefix yang;
  }
  import ciena-osrp-types {
    prefix ciena-osrp-types;
  }
  import ciena-common-version {
    prefix ciena-common-version;
  }

  organization
    "Ciena Corporation";
  contact
    "Web URL: http://www.ciena.com
     Postal: Ciena India Pvt. Ltd.
     Sector 32, Plot 14,
     Gurgaon 122001,
     Haryana, India";
  description
    "This module describes Ciena's OSRP object model for the 6500r platform";

  revision 2023-05-10 {
    description
      "Added 'failure' leaf-list in 'check-conn-sync' action output.";
    ciena-common-version:string "2.2.0";
  }
  revision 2023-02-21 {
    description
      "Added 'check-conn-sync' action.";
    ciena-common-version:string "2.1.0";
  }
  revision 2022-08-22 {
    description
      "Removed obsolete/deprecated mount ciena-osrp-osrp-network-topology";
    ciena-common-version:string "2.0.0";
  }
  revision 2022-05-11 {
    description
      "Initial revision.";
    ciena-common-version:string "1.0.0";
  }

  grouping osrp-object-common-data {
    leaf node-name {
      type ciena-osrp-types:node-name;
      description
        "OSRP node name";
    }
    container object {
      yang:mount-start "ciena-osrp-osrp-node";
      uses ciena-osrp-osrp-node:ciena-osrp-osrp-node-mount-data;
      uses ciena-osrp-osrp-node:ciena-osrp-osrp-node-mount-actions-notifs;
      yang:mount-end "ciena-osrp-osrp-node";
      yang:mount-start "ciena-osrp-osrp-link";
      uses ciena-osrp-osrp-link:ciena-osrp-osrp-link-mount-data;
      uses ciena-osrp-osrp-link:ciena-osrp-osrp-link-mount-actions-notifs;
      yang:mount-end "ciena-osrp-osrp-link";
      yang:mount-start "ciena-osrp-dtl";
      uses ciena-osrp-dtl:ciena-osrp-dtl-mount-data;
      uses ciena-osrp-dtl:ciena-osrp-dtl-mount-actions-notifs;
      yang:mount-end "ciena-osrp-dtl";
      yang:mount-start "ciena-osrp-dtl-set";
      uses ciena-osrp-dtl-set:ciena-osrp-dtl-set-mount-data;
      uses ciena-osrp-dtl-set:ciena-osrp-dtl-set-mount-actions-notifs;
      yang:mount-end "ciena-osrp-dtl-set";
      yang:mount-start "ciena-osrp-snc";
      uses ciena-osrp-snc:ciena-osrp-snc-mount-data;
      uses ciena-osrp-snc:ciena-osrp-snc-mount-actions-notifs;
      yang:mount-end "ciena-osrp-snc";
      yang:mount-start "ciena-osrp-snc-group";
      uses ciena-osrp-snc-group:ciena-osrp-snc-group-mount-data;
      uses ciena-osrp-snc-group:ciena-osrp-snc-group-mount-actions-notifs;
      yang:mount-end "ciena-osrp-snc-group";
    }
  }

  grouping osrp-object-common-data-no-actions {
    leaf node-name {
      type ciena-osrp-types:node-name;
      description
        "OSRP node name";
    }
    container object {
      yang:mount-start "ciena-osrp-osrp-node";
      uses ciena-osrp-osrp-node:ciena-osrp-osrp-node-mount-data-no-actions;
      uses ciena-osrp-osrp-node:ciena-osrp-osrp-node-mount-actions-notifs;
      yang:mount-end "ciena-osrp-osrp-node";
      yang:mount-start "ciena-osrp-osrp-link";
      uses ciena-osrp-osrp-link:ciena-osrp-osrp-link-mount-data-no-actions;
      uses ciena-osrp-osrp-link:ciena-osrp-osrp-link-mount-actions-notifs;
      yang:mount-end "ciena-osrp-osrp-link";
      yang:mount-start "ciena-osrp-dtl";
      uses ciena-osrp-dtl:ciena-osrp-dtl-mount-data-no-actions;
      uses ciena-osrp-dtl:ciena-osrp-dtl-mount-actions-notifs;
      yang:mount-end "ciena-osrp-dtl";
      yang:mount-start "ciena-osrp-dtl-set";
      uses ciena-osrp-dtl-set:ciena-osrp-dtl-set-mount-data;
      uses ciena-osrp-dtl-set:ciena-osrp-dtl-set-mount-actions-notifs;
      yang:mount-end "ciena-osrp-dtl-set";
      yang:mount-start "ciena-osrp-snc";
      uses ciena-osrp-snc:ciena-osrp-snc-mount-data-no-actions;
      uses ciena-osrp-snc:ciena-osrp-snc-mount-actions-notifs;
      yang:mount-end "ciena-osrp-snc";
      yang:mount-start "ciena-osrp-snc-group";
      uses ciena-osrp-snc-group:ciena-osrp-snc-group-mount-data-no-actions;
      uses ciena-osrp-snc-group:ciena-osrp-snc-group-mount-actions-notifs;
      yang:mount-end "ciena-osrp-snc-group";
    }
  }

  grouping osrp-object-common {
    uses ciena-osrp-common-osrp-object:osrp-object-common-data;
    action check-conn-sync {
      description
        "Initiate osrp connections validation (Blocking call).";
      output {
        leaf-list result {
          description
            "Output result message.";
          type string;
        }
        leaf-list failure {
          description
            "Failure details message.";
          type string;
        }
      }
    }
    action initiate-conn-sync {
      description
        "Initiate osrp connections synchronisation (Non-Blocking call).";
      output {
        leaf-list result {
          description
            "Output result message.";
          type string;
        }
      }
    }
  }
}
