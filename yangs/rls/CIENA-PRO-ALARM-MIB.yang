module CIENA-PRO-ALARM-MIB {
  namespace "urn:ietf:params:xml:ns:yang:smiv2:CIENA-PRO-ALARM-MIB";
  prefix ciena-pro-alarm;

  import CIENA-PRO-TYPES-MIB {
    prefix ciena-pro;
  }
  import CIENA-SMI {
    prefix ciena-smi;
  }

  organization
    "Ciena Corporation";
  contact
    "Web: http://www.ciena.com
     Postal:   7035 Ridge Road
               Hanover, Maryland 21076
               U.S.A
     Phone:    +1 800-921-1144
     Fax:      +1 410-694-5750";
  description
    "This modules describes Ciena's alarm object.";

  revision 2020-10-01 {
    description
      "Initial Revision.";
  }

  container cienaProAlarmMIB {
    list cienaProActiveAlarmEntry {
      config false;
      key "cienaProAlarmId";
      description
        "";
      leaf cienaProAlarmId {
        type uint32;
        config false;
        description
          "Unique identifying value assigned to an alarm record.";
      }
      leaf cienaProAlarmName {
        type ciena-pro:DisplayString32;
        config false;
        description
          "Alarm name.";
      }
      leaf cienaProAlarmResource {
        type ciena-pro:DisplayString128;
        config false;
        description
          "Resource under alarm.";
      }
      leaf cienaProAlarmRaiseDateAndTime {
        type ciena-pro:DateTime;
        config false;
        description
          "Time alarm was raised.";
      }
      leaf cienaProAlarmClearDateAndTime {
        type ciena-pro:DateTime;
        config false;
        description
          "The time that the alarm was cleared.  Only present with alarm clear reports.";
      }
      leaf cienaProAlarmCause {
        type ciena-pro:DisplayString128;
        config false;
        description
          "Text representation of the cause of the alarm.";
      }
      leaf cienaProAlarmConditionType {
        type ciena-pro:DisplayString128;
        config false;
        description
          "The type of the alarm; used to group or classify similar or related alarms within a resource.  Only one alarm of any given condition type can be active against a given resource at a time. This allows classification of alarms into conditions, and then the highest condition is the one that prevails. Since different alarms can (and do) share condition types, it provides a form of a classification system.";
      }
      leaf cienaProAlarmDirection {
        type ciena-pro:AlarmDirection;
        config false;
        description
          "Direction indication of the alarm.";
      }
      leaf cienaProAlarmLocation {
        type ciena-pro:AlarmLocation;
        config false;
        description
          "Direction indication of the alarm.";
      }
      leaf cienaProAlarmSeverity {
        type ciena-pro:AlarmSeverity;
        config false;
        description
          "Severity, based on X.733 perceived severity.";
      }
      leaf cienaProAlarmServiceImpact {
        type ciena-pro:AlarmServiceImpact;
        config false;
        description
          "The object instance the alarm is raised against.";
      }
      leaf cienaProAlarmAdditionalInfo {
        type ciena-pro:DisplayString128;
        config false;
        description
          "Additional information supplied by system.";
      }
    }
    config false;
    leaf cienaProAlarmCountCritical {
      type uint32;
      config false;
      description
        "Count of visible, currently active alarms with critical severity.";
    }
    leaf cienaProAlarmCountMajor {
      type uint32;
      config false;
      description
        "Count of visible, currently active alarms with major severity.";
    }
    leaf cienaProAlarmCountMinor {
      type uint32;
      config false;
      description
        "Count of visible, currently active alarms with minor severity.";
    }
    leaf cienaProAlarmCountWarning {
      type uint32;
      config false;
      description
        "Count of visible, currently active alarms with warning severity.";
    }
  }
}
