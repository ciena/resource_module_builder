module ciena-pro-lcm-debug {
  namespace "urn:ciena:params:xml:ns:yang:ciena-pro-lcm-debug";
  prefix lcm-debug;

  import ciena-pro-state-machine {
    prefix sm;
  }
  import ciena-common-version {
    prefix ciena-common-version;
  }

  organization
    "Ciena";
  contact
    "Web URL: http://www.ciena.com/
     Postal:  7035 Ridge Road
           Hanover, Maryland 21076
           U.S.A.
     Phone:   +1 800-921-1144
     Fax:     +1 410-694-5750";
  description
    "Debug module for LCM";

  revision 2020-11-16 {
    description
      "Add RPC  to toggle internal fault";
    ciena-common-version:string "1.6.0";
  }
  revision 2018-12-15 {
    description
      "Initial Revision.";
    ciena-common-version:string "1.0.0";
  }

  rpc dbg-lcm-serv-event {
    description
      "Trigger a LCM event";
    input {
      leaf service-name {
        type string;
        description
          "Name of the service";
      }
      leaf event {
        type identityref {
          base sm:event;
        }
        description
          "Send a LCM event to a service. ";
      }
    }
    output {
      leaf result {
        type string;
        description
          "Return OK on success.";
      }
    }
  }

  rpc dbg-lcm-disable-policing {
    description
      "Disable LCM policing";
    output {
      leaf result {
        type string;
        description
          "Return OK on success.";
      }
    }
  }

  rpc dbg-lcm-toggle-internal-fault-flag {
    description
      "Toggle internal fault flag";
    input {
      leaf service-name {
        type string;
        description
          "Name of the service";
      }
      leaf value {
        type boolean;
        description
          "Set True/False";
      }
    }
    output {
      leaf result {
        type string;
        description
          "Return OK on success.";
      }
    }
  }

  rpc dbg-lcm-toggle-activation-flag {
    description
      "Set the activation flag value";
    input {
      leaf service-name {
        type string;
        description
          "Name of the service";
      }
      leaf value {
        type boolean;
        description
          "Set True/False";
      }
    }
    output {
      leaf result {
        type string;
        description
          "Return OK on success.";
      }
    }
  }

  rpc dbg-lcm-enable-policing {
    description
      "Enable LCM policing";
    output {
      leaf result {
        type string;
        description
          "Return OK on success.";
      }
    }
  }
}
