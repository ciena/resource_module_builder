module ciena-pro-neighbours-types {
  namespace "urn:ciena:params:xml:ns:yang:ciena-pro-neighbours-types";
  prefix neighbours-types;

  import ciena-common-version {
    prefix version;
  }

  organization
    "Ciena Corporation";
  contact
    "Web URL: http://www.ciena.com/
     Postal:  7035 Ridge Road
              Hanover, Maryland 21076
              U.S.A.
     Phone:   +1 800-921-1144
     Fax:     +1 410-694-5750";
  description
    "This model identifies neighbour types.";

  revision 2021-12-14 {
    description
      "Initial Revision";
    version:version "version" {
      version:string "1.0.0";
    }
  }

  identity neighbour-type {
    description
      "The base identity to represent the type of neighbour in the list";
  }

  identity site {
    base neighbour-type;
    description
      "The neighbour is part of the same site";
  }

  identity network {
    base neighbour-type;
    description
      "The neighbour is somewhere in the network but is not part of the same site";
  }
}
