module ciena-pro-ra {
  namespace "urn:ciena:params:xml:ns:yang:ciena-pro-ra";
  prefix pro-ra;

  import ciena-common-version {
    prefix version;
  }

  organization
    "Ciena Corporation";
  contact
    "Web URL: http://www.ciena.com/
     Postal:  7035 Ridge Road
             Hanover, Maryland 21076
             U.S.A.
     Phone:   +1 800-921-1144
     Fax:     +1 410-694-5750";
  description
    "This module is used to model the API for the generic Pro
     Resource Adaptor.  This generic service allows babel translations
     to be executed and fallback translations called for any supported
     externl models.";

  revision 2021-01-19 {
    description
      "Initial revision";
    version:version "version" {
      version:string "1.0.0";
    }
  }

  container adaptor {
    description
      "Element used for control and monitoring of the Resource
       Adaptor";
    leaf enabled {
      type boolean;
      default "false";
      description
        "Indicates if the resource adaptor is enabled or not.";
    }
    container caches {
      anyxml fallback;
      anyxml native;
      anyxml external;
    }
  }
}
