module ciena-common-test-deviations {
  yang-version 1.1;
  namespace "urn:ciena:params:xml:ns:yang:ciena-common-test-deviations";
  prefix test-dev;

  import ciena-common-test {
    prefix test;
  }

  organization
    "Ciena Corporation";
  contact
    "Web URL: http://www.ciena.com";
  description
    "Test module";

  revision 2021-01-18 {
    description
      "Change 'mandatory' deviation to leaf 'a' rather than 'd' so we
       can test the 'replace' operation without conflicting with the
       'default' in 'd'.";
  }
  revision 2020-12-05 {
    description
      "Initial revision";
  }

  deviation "/test:validation-test/test:a" {
    deviate add {
      default "12";
    }
    deviate replace {
      mandatory false;
    }
  }

  deviation "/test:validation-test/test:b" {
    deviate delete {
      default "22";
    }
    deviate add {
      mandatory true;
    }
  }

  deviation "/test:red/test:blue/test:a" {
    deviate add {
      default "12";
    }
  }

  deviation "/test:red/test:blue/test:b" {
    deviate delete {
      default "22";
    }
  }

  deviation "/test:red/test:blue/test:c" {
    deviate replace {
      default "123";
    }
  }

  deviation "/test:red/test:blue/test:d" {
    deviate replace {
      config false;
    }
  }

  deviation "/test:remove-via-deviation" {
    deviate not-supported;
  }
}
