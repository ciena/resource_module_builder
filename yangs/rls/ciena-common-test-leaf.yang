module ciena-common-test-leaf {
  yang-version 1.1;
  namespace "urn:ciena:params:xml:ns:yang:ciena-common-test-leaf";
  prefix tl;

  organization
    "Ciena Corporation";
  contact
    "Web URL: http://www.ciena.com";
  description
    "A module to test variations on leafs for DDF. These leafs are intended to
     be used to test features of the generator, serializer and other parts of
     the framework";

  revision 2019-10-25 {
    description
      "Initial revision";
  }

  container common-test-leaf {
    description
      "Container to group all of the leaf variations. Each leaf type has a sub-
       container that contains variations of the leaf type. Different types have
       different restrictions (length, pattern, etc).";
    container inst-id {
      leaf simple {
        type instance-identifier;
      }
    }
    container str {
      description
        "Variations on string leafs.";
      leaf simple {
        description
          "The simplest leaf type.";
        type string;
      }
      leaf len-range {
        description
          "Test with a single range with concrete numbers";
        type string {
          length "2 .. 7";
        }
      }
      leaf len-multi-range {
        description
          "Test with two disjoint ranges";
        type string {
          length "2 .. 7 | 48 .. 50";
        }
      }
    }
  }
  container enums {
    leaf weird-names {
      type enumeration {
        enum normal;
        enum with-dash;
        enum with_underscore;
        enum "with space";
        enum "256B/257B (some more text);" {
          description
            "Inspired by the following: '256B/257B (transcoded FEC-enabled data)'

             See also: BIFROST-24220";
        }
        enum α {
          description
            "Greek character 'alpha', example of unicode characters";
        }
        enum ملاس {
          description
            "'Hello' in Farsi/Arabic, example of right-to-left text (not actually done properly here)";
        }
        enum Reserved {
          description
            "Possible keyword";
        }
        enum _name_ {
          description
            "Legal but conflicts with some Python internal naming";
        }
        enum __name__ {
          description
            "Legal but conflicts with some Python internal naming";
        }
        enum __cls__ {
          description
            "Legal but conflicts with some Python internal naming";
        }
      }
      description
        "The RFC says that names may be any non-empty set of Unicode characters and no leading/trailing whitespace";
    }
  }
}
