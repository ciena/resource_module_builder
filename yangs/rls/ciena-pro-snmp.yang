module ciena-pro-snmp {
  namespace "urn:ciena:params:xml:ns:yang:ciena-pro-snmp";
  prefix ciena-pro-snmp;

  import ciena-common-version {
    prefix version;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's snmp model";

  revision 2021-03-20 {
    version:version "version" {
      version:string "1.0.0";
    }
    description
      "Initial revision.";
  }

  typedef status-type {
    type enumeration {
      enum "disable" {
        description
          "Disable state.";
      }
      enum "enable" {
        description
          "Enable state.";
      }
    }
    description
      "Status type - enable or disable";
  }

  container snmp-options {
    container server {
      leaf state {
        type status-type;
        mandatory true;
        description
          "Flag to enable or disable SNMP interface";
      }
    }
  }
}
