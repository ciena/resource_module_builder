module ciena-ddy-db {
  yang-version 1.1;
  namespace "urn:ciena:params:xml:ns:yang:ciena-ddy-db";
  prefix db;

  import ciena-common-yang {
    prefix ciena-common-yang;
  }
  import ietf-yang-types {
    prefix yang;
  }
  import ciena-common-exceptions {
    prefix ciena-common-exceptions;
  }
  import ciena-common-version {
    prefix ciena-common-version;
  }
  import ciena-ddy-db-wal {
    prefix ciena-ddy-db-wal;
  }

  organization
    "Ciena Corporation";
  contact
    "Web URL: http://www.ciena.com/
     Postal:  7035 Ridge Road
             Hanover, Maryland 21076
             U.S.A.
     Phone:   +1 800-921-1144
     Fax:     +1 410-694-5750";
  description
    "Ciena Database Yang Definitions.";

  revision 2023-07-18 {
    description
      "Added lock owners";
    ciena-common-version:string "1.30.0";
  }
  revision 2023-06-26 {
    description
      "Add an option to cache init so internal callers can
       use a move instead of a copy for performance.";
    ciena-common-version:string "1.29.0";
  }
  revision 2023-05-25 {
    description
      "Added db-file-max-count and db-config-persistent
       ddy-db-config structure.";
    ciena-common-version:string "1.28.0";
  }
  revision 2023-05-19 {
    description
      "Added error for missing db configuration file.";
    ciena-common-version:string "1.27.0";
  }
  revision 2023-05-01 {
    description
      "Added Id to db config structure.";
    ciena-common-version:string "1.26.0";
  }
  revision 2023-02-21 {
    description
      "Added data persistence feature.";
    ciena-common-version:string "1.25.0";
  }
  revision 2022-12-09 {
    description
      "Added audit feature.";
    ciena-common-version:string "1.24.0";
  }
  revision 2022-10-03 {
    description
      "Add ability to reset cache access stats";
    ciena-common-version:string "1.23.0";
  }
  revision 2022-09-25 {
    description
      "Add cache swap capability";
    ciena-common-version:string "1.22.0";
  }
  revision 2022-09-13 {
    description
      "Add cache access stats";
    ciena-common-version:string "1.21.0";
  }
  revision 2022-04-12 {
    description
      "Add db-target in deployment option";
    ciena-common-version:string "1.20.0";
  }
  revision 2022-01-04 {
    description
      "Add sorted option for cache and cache-option container.";
    ciena-common-version:string "1.19.0";
  }
  revision 2021-11-10 {
    description
      "Removed duplicate import for ciena-common-yang.
       Used ciena-common-yang grouping transaction-id";
    ciena-common-version:string "1.18.0";
  }
  revision 2021-11-01 {
    description
      "Added leaf proxy-service-name in create-db and ddy-db-config.
       Added action transaction-done";
    ciena-common-version:string "1.17.0";
  }
  revision 2021-10-19 {
    description
      "Add latest fullpath in db config location
       Added warning and errors for db recovery and
       save problems.";
    ciena-common-version:string "1.16.0";
  }
  revision 2021-10-18 {
    description
      "Add option to suppress diff when computing wal records";
    ciena-common-version:string "1.15.0";
  }
  revision 2021-10-08 {
    description
      "Add clean action for the db delete";
    ciena-common-version:string "1.14.0";
  }
  revision 2021-10-06 {
    description
      "Add new leaf wal-support to rpc create-db";
    ciena-common-version:string "1.13.0";
  }
  revision 2021-10-04 {
    description
      "Add new ddy-db-wal";
    ciena-common-version:string "1.12.0";
  }
  revision 2021-09-30 {
    description
      "Add enum and error code to capture a failure to recover the most
       recent incarnation on recovery.";
    ciena-common-version:string "1.11.0";
  }
  revision 2021-09-15 {
    description
      "Add a new cache attribute called publish-patches";
    ciena-common-version:string "1.10.0";
  }
  revision 2021-09-09 {
    description
      "Add enum for db file read/write status";
    ciena-common-version:string "1.9.0";
  }
  revision 2021-09-08 {
    description
      "Add options for coalescing.";
    ciena-common-version:string "1.8.0";
  }
  revision 2021-08-27 {
    description
      "Added leaf to support write-ahead log to
       database config and deployment options";
    ciena-common-version:string "1.7.0";
  }
  revision 2021-02-09 {
    description
      "Add a list for ddy-caches";
    ciena-common-version:string "1.6.0";
  }
  revision 2020-11-30 {
    description
      "Add ability to initialize a database from deployment data if
       there is no file present";
    ciena-common-version:string "1.5.0";
  }
  revision 2020-07-31 {
    description
      "Add upgrade from version in the database config";
    ciena-common-version:string "1.4.0";
  }
  revision 2020-06-29 {
    description
      "Add a database versioning framework to allow database upgrade";
    ciena-common-version:string "1.3.0";
  }
  revision 2020-05-19 {
    description
      "Changed datastore type to identity that can be extended
       by other modules as needed.

       Added a size leaf to databases";
    ciena-common-version:string "1.2.0";
  }
  revision 2019-05-02 {
    description
      "Added ability to report failure on recovery.  Added action to
       recover a database";
    ciena-common-version:string "1.1.0";
  }
  revision 2015-04-07 {
    description
      "Initial revision";
  }

  identity db-exception {
    base ciena-common-exceptions:exception;
  }

  identity db-locked {
    base ciena-common-exceptions:exception;
  }

  identity db-failed {
    base ciena-common-exceptions:exception;
  }

  identity db-incomplete {
    base ciena-common-yang:error-code;
    description
      "Indicates that the latest DB file could not be read on recovery
       and a fallback was successful to a previous incarnation.";
  }

  identity db-recovery-error {
    base ciena-common-yang:error-code;
    description
      "Indicates that the latest DB file could not be read on recovery
       and has been marked as failed.";
  }

  identity db-save-error {
    base ciena-common-yang:error-code;
    description
      "Indicates that the latest DB file could not be written
       and has been marked as failed.";
  }

  identity db-recovery-warning {
    base ciena-common-yang:warning;
    description
      "Indicates that the latest DB file could not be read on recovery
       but the problem was not fatal and the DB has not been marked as
       failed.";
  }

  identity db-audit-mismatch {
    base ciena-common-yang:error-code;
    description
      "Indicates that the latest DB file does not match the cached copy";
  }

  identity db-config-unavailable-error {
    base ciena-common-yang:error-code;
    description
      "Indicates that the DB configuration data could not be found.";
  }

  grouping coalescing-group {
    container coalescing {
      description
        "Options that dictate how the RAM cache is
         coalesced to a file.  When a DB is coalesced
         to a file, all patches in the write-ahead-log
         (if applicable) are applied and a new log
         is started.  The options in this container are
         'or-ed' together.  If multiple criteria are
         provided, coalescing will occur if any condition
         is true.";
      leaf max-time {
        type uint32 {
          range "0 .. 3600";
        }
        default "0";
        units "s";
        description
          "Max time to wait to trigger coalescing.  A time of
           0 will not trigger coalescing based on time expiry.
           Changing time from 0 to non-zero will reset the timer
           and trigger coalescing if change was detected prior
           to changing this attribute.";
      }
      leaf polling-time {
        type uint16 {
          range "1 .. 3600";
        }
        default "1";
        units "s";
        description
          "Interval to use while looking for changes to coalesce.";
      }
      leaf settling-time {
        type uint16 {
          range "0 .. 1000";
        }
        default "100";
        units "ms";
        description
          "Interval to wait while looking for additional changes
           after the first change is detected.  A time of 0 will
           not trigger coalescing based on settling-time.";
      }
      leaf incarnations {
        type uint32;
        default "0";
        description
          "Number of updates (including no-ops) to a database
           that can occur before coalescing occurs.  If not
           present or 0, incarnation counts will not be used for
           coalescing.";
      }
    }
  }

  grouping db-name-group {
    leaf name {
      type string;
      description
        "Name of the database.";
    }
  }

  typedef db-format {
    type enumeration {
      enum json-fmt;
      enum xml-fmt;
    }
  }

  typedef db-file-status {
    type enumeration {
      enum ok {
        description
          "Successful read/write of db";
      }
      enum read-file-does-not-exist {
        description
          "Unable to find the file specified ";
      }
      enum read-invalid-input {
        description
          "Invalid input was provided, unable to attempt to read db file.";
      }
      enum read-corrupt-size-zero {
        description
          "File was found, but is corrupt due to it being of size 0 bytes.";
      }
      enum read-corrupt-failed-serialization {
        description
          "File was found, but is corrupt due to it failing to serialize.";
      }
      enum read-corrupt-other {
        description
          "File was found, but is corrupt.";
      }
      enum write-failed {
        description
          "Failed to write the db to file";
      }
      enum read-failed-latest {
        description
          "The most recent file was present but could not be read.
           A successful read occurred on a previous incarnation";
      }
    }
    description
      "Return codes for attempting to read/write a database.";
  }

  grouping local-file-group {
    leaf path {
      type string;
      mandatory true;
      description
        "This is the path of the local file the database is saved to.";
    }
    leaf name {
      type string;
      mandatory true;
      description
        "This is the base of the filename of the local file the database is saved to.";
    }
    leaf fullpath {
      type string;
      config false;
      description
        "Combined name and path.";
    }
    leaf latest-fullpath {
      type string;
      config false;
      description
        "This is the full path of the latest file the database is saved to.";
    }
  }

  grouping ddy-db-config-group {
    leaf format {
      type db-format;
      default "xml-fmt";
      description
        "Data format for the file.";
    }
    leaf cached {
      type boolean;
      default "true";
      description
        "Indicates if the database should have RAM cache or not.
         Disabling the cache will save memory but will incur
         performance penalties on update.";
    }
    leaf flat {
      type boolean;
      description
        "Indicates if the access method for the database is
         flat (one level of hierarchy at a time), or full
         (entire hierarchy is processed for get and set
         actions)";
      default "true";
    }
    leaf init-from-depo {
      type ciena-common-yang:target-node;
      description
        "Indicates if the database should be initialized from
         deployment data if no database file exists at initialization.
         The target node that is supplied is used to get the data from
         the depo service and populate the database.";
    }
    leaf wal-support {
      type boolean;
      default "false";
      description
        "Indicates if the database should have write-ahead-logging
         support or not.Enabling the wal will write changes to a wal file
         stored on disk before doing actual modifications to the
         persistent database.";
    }
    leaf wal-diff {
      type boolean;
      default "true";
      description
        "Indicates if wal records should record the diff of each update
         or the raw request.  Using the diff can avoid unncessary writes
         of no-ops but can be more expensive during the in-line update.
         Diffs can also be avoided if there is already an external
         orchestrator (like service-broker) that limits changes to diffs.
         This only takes effect if wal-support is enabled.";
    }
    uses coalescing-group;
    leaf proxy-service-name {
      type string;
      description
        "Service name used by database to register for transaction complete";
    }
    leaf audit {
      type boolean;
      default "false";
      description
        "Indicates if the database should be audited after coalescing to
         make sure the cached copy matches the version in disk.  This
         has no effect if the database is not cached.  If there is a
         mismatch, the database will be marked as failed with a
         db-audit-mimatch reason.";
    }
    leaf persistent {
      type boolean;
      default "true";
      description
        "Indicates if the database should write any database-related files to
         disk. This is useful for scenarios where the single ddy-db interface is
         needed, but we have a separate persistence model. If a database is non-persistent,
         it must also be cached, and it must also have wal-support disabled.";
    }
    leaf db-config-persistent {
      type boolean;
      default "true";
      description
        "Indicates if the database configuration file should be written to disk.
         The file is required for conversions.";
    }
    leaf db-file-max-count {
      type uint8 {
        range "1 .. 5";
      }
      default "2";
      description
        "Indicates the maximum number of database files that should be stored
         for backup and recovery.To set the value 0, use persistent as false.";
    }
  }

  list ddy-db-config {
    config false;
    key "name";
    uses db-name-group;
    leaf version {
      type string;
      description
        "Current database version";
    }
    leaf upgrade-from-version {
      type string;
      description
        "The version of the database from which the upgrade was performed. The service can use this to determine if any
         additional database upgrade is required for the current database";
    }
    container location {
      uses local-file-group;
    }
    leaf initialized {
      type boolean;
      config false;
      description
        "This flag indicates that the database has been loaded";
    }
    leaf failed {
      type boolean;
      config false;
      default "false";
      description
        "This flag indicates that the database is not consistent.
         A failed database will not be written to disk";
    }
    leaf failed-reason {
      type db-file-status;
      description
        "If our database is not consistent, this field should give some
         indication as to why";
    }
    leaf locked {
      type boolean;
      default "false";
      config false;
      description
        "Indicates if the database is locked to prevent writes
         to disk.  This is set via the lock/unlock actions.";
    }
    leaf-list lock-owners {
      type string {
        ciena-common-yang:stringptr "true";
      }
      config false;
      description
        "Indicates who owns the lock.  If another lock is requested by
         the same owner, the lock will be granted.  If a lock is
         requested by a different owner, the database will remain locked
         and the owner will be added to the list.  When an unlock is requested
         with the second owner, the unlock will not be processed, but
         the list will be updated.  This allows lock/unlock requests to
         leave original lock states untouched if the system or another
         user has requested a lock and another client or user blindly does a
         lock/unlock.";
    }
    leaf id {
      type uint64;
      config false;
      description
        "Unique id for this database. This is used by the dbThread in order
         to verify that the db it is managing has not changed.";
    }
    uses ddy-db-config-group;
    action recover {
      description
        "Manually trigger the recovery of a database.  Will
         discard current contents and reevaluate failed flags";
      input {
        leaf publish-changes {
          type boolean;
          default "true";
          description
            "Flag to indicate if changes between the existing database
             and the recovered database should be published";
        }
      }
      output {
        uses ciena-common-yang:rpc-result-common;
      }
    }
    action unlock {
      description
        "Unlock the database to allow it to be written to disk. Any
         changes made while the database is locked will be flushed
         to disk after the lock is removed.";
      input {
        leaf lock-owner {
          type string;
          description
            "Indicates who is requesting the unlock.  If the db is already
             locked by the same owner, the unlock will be granted.  If a lock is
             owned by a different owner, the database will remain locked
             and the owner will be updated.  This allows lock/unlock
             requests to leave original lock states untouched if the system
             or another user has requested a lock and another client or
             user blindly does a lock/unlock.";
        }
      }
      output {
        uses ciena-common-yang:rpc-result-common;
      }
    }
    action lock {
      description
        "Lock the database from being written to disk. Any
         changes made while the database is locked will be flushed
         to disk after the lock is removed.";
      input {
        leaf lock-owner {
          type string;
          description
            "Indicates who is requesting the lock.  If the db is already
             locked by the same owner, the lock will be unaffected.  If a
             lock is owned by a different owner, the database will remain locked
             and the owner will not be updated.  This allows lock/unlock
             requests to leave original lock states untouched if the system
             or another user has requested a lock and another client or
             user blindly does a lock/unlock.";
        }
      }
      output {
        uses ciena-common-yang:rpc-result-common;
      }
    }
    action flush {
      description
        "Manually trigger the flushing of all contents to the file.  A
         locked or failed database cannot be flushed.";
      input {
        leaf force {
          type boolean;
          default "false";
          description
            "Flag to override the block on flushing a failed or locked
             database";
        }
        leaf lock-when-done {
          type boolean;
          default "false";
          description
            "Flag to indicate if the database should also be locked when
             the write is completed to prevent additional writes after
             the flush.";
        }
        leaf lock-owner {
          type string;
          description
            "Indicates who is requesting the lock.  If the db is already
             locked by the same owner, the lock will be unaffected.  If a
             lock is owned by a different owner, the database will remain locked
             and the owner will not be updated.  This allows lock/unlock
             requests to leave original lock states untouched if the system
             or another user has requested a lock and another client or
             user blindly does a lock/unlock.";
        }
      }
      output {
        uses ciena-common-yang:rpc-result-common;
      }
    }
    action clean {
      description
        "Delete the files associated with this database";
      input {
        leaf delete {
          type boolean;
          default "false";
          description
            "Flag to indicate if the database should also be deleted
             when the clean operation is done";
        }
      }
      output {
        uses ciena-common-yang:rpc-result-common;
      }
    }
    action transaction-done {
      description
        "Adds a record to wal file that indicates transaction is done";
      input {
        uses ciena-common-yang:transaction-id;
      }
      output {
        uses ciena-common-yang:rpc-result-common;
      }
    }
  }
  list ddy-db-data {
    config false;
    key "name";
    uses db-name-group;
    anyxml data;
    list transactions {
      key "id";
      leaf id {
        type string {
          length "64";
        }
      }
      list actions {
        key "action path";
        uses ciena-common-yang:yang-set-obj-input;
      }
    }
    leaf incarnation {
      type uint64;
      config false;
      description
        "Indicates how many updates have been performed on this database";
    }
    leaf saved-incarnation {
      type uint64;
      config false;
      description
        "Indicates the incarnation number saved to the file.
         If this doesn't match the incarnation, there is a
         misalignment between the in-memory database and the
         saved database";
    }
    leaf size {
      type uint32;
      config false;
      description
        "Indicates how much memory is occupied by the database.";
    }
    uses ciena-ddy-db-wal:ddy-db-wal-group;
  }

  grouping cache-name-group {
    leaf name {
      type string;
      description
        "Name of the cache.";
    }
  }

  grouping cache-swap-options {
    leaf timeout {
      type uint32;
      units "sec";
      default "600";
      description
        "If the last access time exceeds the timeout value, the cache is swapped to disk";
    }
    leaf enabled {
      type boolean;
      default "false";
      description
        "Enable/disable the cache swapping";
    }
  }

  grouping cache-group {
    uses cache-name-group;
    leaf filename {
      type string;
      description
        "Name of the file to initialize the cache from.";
    }
    leaf monitored {
      type boolean;
      default "true";
      description
        "Indicates that the file provided is to be continuously
         monitored and the db updated on file changes.";
    }
    container access {
      config false;
      description
        "Cache access statistics";
      leaf elapsed-time {
        type uint64;
        units "sec";
        description
          "Time elapsed in sec since the last access";
      }
      leaf last-access-time {
        type yang:date-and-time;
        description
          "Last access time";
      }
      leaf read-count {
        type uint64;
        description
          "Number of time the cache data was read";
      }
      leaf write-count {
        type uint64;
        description
          "Number of time the cache data was written to";
      }
    }
    leaf format {
      type db-format;
      default "xml-fmt";
      description
        "Data format for the file.";
    }
    leaf get-raw {
      type boolean;
      default "true";
      description
        "Indicates that the get function should return a
         raw pointer to the data in the cache.  If set to
         false, a copy of the data is returned.  This has
         a performance impact but means that the client
         does not need to do concurrency management";
    }
    leaf publish-patches {
      type boolean;
      default "false";
      description
        "Indicates that for any set operation, the new
         data shall be compared against the existing
         contents of a cache. If patches (diffs) are
         identified, they will be published.";
    }
    leaf sorted {
      type boolean;
      default "false";
      description
        "Indicates that yang lists are sorted in cache.
         If true, instead of linear search, binary search
         is performed on insert, delete, search and merge
         operations which gives better performance.";
    }
  }

  list ddy-caches {
    config false;
    key "name";
    description
      "List of active caches";
    uses cache-group;
    container swapping {
      description
        "Contains a set of configurable options to swap the idle cache to disk. The cache is restored from the disk for any read
         or write access. Swapping is not applied for caches configured as raw mode.  The purpose of this feature is to reduce the
         memory footprint of a process";
      uses cache-swap-options;
      leaf state {
        config false;
        type enumeration {
          enum in-memory {
            description
              "Cache is in the memory";
          }
          enum in-disk {
            description
              "Cache is copied to disk";
          }
        }
      }
    }
    leaf size {
      type uint32;
      description
        "Indicates how much memory is occupied by the cache.";
    }
    action fetch-data {
      description
        "Fetch data currently stored in the cache";
      output {
        uses ciena-common-yang:rpc-result-common;
        anyxml data {
          description
            "Data currently stored in the cache.";
        }
      }
    }
    action reset-access-counter {
      description
        "Reset the access statistics of the cache";
      output {
        uses ciena-common-yang:rpc-result-common;
      }
    }
  }
  container db-options {
    description
      "Deployment options for all databases in this domain";
    leaf base-path {
      type string;
      description
        "Base path for the databases to be created and recovered from.
         If not present, this directory will be created at startup.";
    }
    leaf wal-support {
      type boolean;
      default "false";
      description
        "Indicates if the database should have write-ahead-logging
         support or not.Enabling the wal will write changes to a wal file
         stored on disk before doing actual modifications to the
         persistent database.";
    }
    leaf wal-diff {
      type boolean;
      default "true";
      description
        "Indicates if wal records should record the diff of each update
         or the raw request.  Using the diff can avoid unncessary writes
         of no-ops but can be more expensive during the in-line update.
         Diffs can also be avoided if there is already an external
         orchestrator (like service-broker) that limits changes to diffs.
         This only takes effect if wal-support is enabled.";
    }
    leaf db-target {
      type string;
      description
        "db-target allows for a service to provide an alternative database
         back end while maintaining the same API for client applications.
         If a db-target is provided, all get/set/rpc calls will be forwarded
         to the service named as the target. This service can be remote or local.";
    }
  }

  identity datastore-type {
    description
      "The base identity for datastore types";
  }

  grouping datastore-id {
    description
      "Identity of the datastore";
    leaf id {
      type identityref {
        base datastore-type;
      }
      description
        "datastore ID representation.";
    }
  }

  grouping datastore {
    description
      "datastore data structure";
    container datastore {
      description
        "datastore data structure";
      ciena-common-yang:alias "ddy-db-datastore";
      uses datastore-id;
    }
  }

  container cache-swap-options {
    uses cache-swap-options;
    leaf directory {
      type string;
      default "/var/opt/cache-swap";
      description
        "Location of the directory where all the swap files are managed";
    }
  }

  rpc db-save {
    description
      "Save a snapshot of the specified database to disk.";
    input {
      uses db-name-group;
    }
  }

  rpc create-db {
    input {
      leaf name {
        type string;
        description
          "Name of the database to be created";
      }
      leaf filename {
        type string;
        description
          "Name of the file to initialize the database from.";
      }
      uses ddy-db-config-group;
    }
    output {
      uses ciena-common-yang:rpc-result-common;
    }
  }

  rpc create-cache {
    input {
      uses cache-group;
      container swapping {
        uses cache-swap-options;
      }
      container init {
        ciena-common-yang:alias "ddy-cache-data";
        anyxml data {
          description
            "Data to initialize the cache with.  Cannot be
             provided if a filename is also provided.";
        }
        leaf move {
          description
            "Flag for internal callers to indicate if data should moved
             or copied to the cache.  Moving is faster if it is possible";
          type boolean;
          default "false";
        }
      }
    }
    output {
      uses ciena-common-yang:rpc-result-common;
    }
  }

  rpc delete-cache {
    input {
      uses cache-name-group;
    }
    output {
      uses ciena-common-yang:rpc-result-common;
    }
  }

  rpc flush-and-lock-all {
    description
      "Flushes all databases and locks them so clients that need to
       copy or move database files can do so without worrying about
       files moving.";
    input {
      leaf force {
        type boolean;
        default "false";
        description
          "Flag to override the block on flushing a failed or locked
           database";
      }
      leaf lock-owner {
        type string;
        description
          "Indicates who is requesting the lock.  If the db is already
           locked by the same owner, the lock will be unaffected.  If a
           lock is owned by a different owner, the database will remain locked
           and the owner will not be updated.  This allows lock/unlock
           requests to leave original lock states untouched if the system
           or another user has requested a lock and another client or
           user blindly does a lock/unlock.";
      }
    }
    output {
      uses ciena-common-yang:rpc-result-common;
    }
  }

  rpc unlock-all {
    description
      "Unlocks all databases.";
    input {
      leaf lock-owner {
        type string;
        description
          "Indicates who is requesting the unlock.  If the db is already
           locked by the same owner, the unlock will be granted.  If a lock is
           owned by a different owner, the database will remain locked
           and the owner list will be updated.  This allows lock/unlock
           requests to leave original lock states untouched if the system
           or another user has requested a lock and another client or
           user blindly does a lock/unlock.";
      }
    }
    output {
      uses ciena-common-yang:rpc-result-common;
    }
  }
}
