module ciena-pro-coherent-device-otsi-diagnostics-types {
  namespace "urn:ciena:ns:yang:coherent-device-otsi-diagnostics-types";
  prefix coherent-device-otsi-diagnostics-types;

  import ciena-common-version {
    prefix version;
  }
  import ciena-pro-wavelogic-device-extension-types {
    prefix wavelogic-device-extension-types;
  }

  organization
    "Ciena Corporation";
  contact
    "Web URL: http://www.ciena.com/
     Postal:  7035 Ridge Road
              Hanover, Maryland 21076
              U.S.A.
     Phone:   +1 800-921-1144
     Fax:     +1 410-694-5750";
  description
    "OTSI diagnostic data definitions for coherent devices.";

  revision 2024-01-01 {
    description
      "Initial version.";
    version:version "version" {
      version:string "1.0.0";
    }
    reference
      "1.0.0";
  }

  grouping coherent-device-otsi-diagnostics-common-group {
    leaf prov-mismatch {
      type boolean;
      default "false";
      description
        "One or more OTSI provisionable parameters is not supported by the hardware currently
         present. This condition is active for parameters other than tx-frequency and tx-power
         that have separate conditions. To resolve compare the user provisioned values to the actual
         values applied to hardware and re-provision any parameter that has not been applied
         to the hardware.";
    }
    leaf tx-off {
      type boolean;
      default "false";
      description
        "The device transmitter is currently disabled. This can occur due to administrative
         action to disable the transmitter or automatically due to system behaviour such as
         consequent-action in the presence of a signal failure. If the condition is due to
         provisioning it will clear when the transmitter-state is re-enabled. If the condition
         is due to system consequent action application, it will clear when the source fault is
         resolved. See other defects that are active for the source fault.";
    }
    leaf tx-provisioning-required {
      type boolean;
      default "false";
      description
        "An indication that the device transmitter requires provisioning to become operational.
         This condition is cleared by ensuring that the tx-frequency and tx-power are provisioned.";
    }
    leaf tx-tuning-in-progress {
      type boolean;
      default "false";
      description
        "An indication that the device transmitter is currently tuning to the provisioned frequency.
         The condition clears once the target frequency is reached.";
    }
    leaf tx-frequency-prov-mismatch {
      type boolean;
      default "false";
      description
        "The provisioned value for Tx frequency has not been applied to the hardware.
         The likely cause is the value is out-of-range for the specific devie that is present.
         Resolve the condition by configuring a value that is in range for the current device.";
    }
    leaf tx-power-prov-mismatch {
      type boolean;
      default "false";
      description
        "The provisioned value for Tx power has not been applied to the hardware.
         The likely cause is the value is out-of-range for the specific device that is present.
         Resolve the condition by configuring a value that is in range for the current device.";
    }
    leaf laser-frequency-out-of-range {
      type boolean;
      default "false";
      description
        "The difference between the nominal provisioned frequency and the actual frequency
         is out of specification tolerances.";
    }
    leaf rx-loss-of-signal {
      type boolean;
      default "false";
      description
        "Loss of signal in the Rx direction derived from low optical power fail threshold
         being crossed and a loss of frame for the signal.";
    }
    leaf rx-loss-of-channel {
      type boolean;
      default "false";
      description
        "";
    }
    leaf rx-loss-of-clock {
      type boolean;
      default "false";
      description
        "";
    }
    leaf rx-loss-of-frame {
      type boolean;
      default "false";
      description
        "";
    }
    leaf rx-loss-of-multiframe {
      type boolean;
      default "false";
      description
        "";
    }
    leaf rx-remote-defect-indication {
      type boolean;
      default "false";
      description
        "";
    }
    leaf pre-fec-signal-fail {
      type boolean;
      default "false";
      description
        "";
    }
    leaf pre-fec-signal-degrade {
      type boolean;
      default "false";
      description
        "";
    }
    leaf server-signal-fail {
      type boolean;
      default "false";
      description
        "Indication that server-signal-fail has been detected at the OTSI layer.
         This indication is status only and not suitable for driving protection.";
    }
    description
      "OTSI diagnostic data";
  }

  grouping otsi-lane-power-threshold-diagnostics-group {
    leaf rx-power-low-alarm {
      type boolean;
      description
        "Low alarm threshold crossed.";
    }
    leaf rx-power-high-alarm {
      type boolean;
      description
        "High alarm threshold crossed.";
    }
    leaf rx-power-low-warning {
      type boolean;
      description
        "Low warning threshold crossed.";
    }
    leaf rx-power-high-warning {
      type boolean;
      description
        "High warning threshold crossed.";
    }
    leaf tx-power-low-alarm {
      type boolean;
      description
        "Low alarm threshold crossed.";
    }
    leaf tx-power-high-alarm {
      type boolean;
      description
        "High alarm threshold crossed.";
    }
    leaf tx-power-low-warning {
      type boolean;
      description
        "Low warning threshold crossed.";
    }
    leaf tx-power-high-warning {
      type boolean;
      description
        "High warning threshold crossed.";
    }
    description
      "Signal lane power threshold status.";
  }

  grouping otsi-lane-power-channel-threshold-diagnostics-group {
    leaf rx-channel-power-low-alarm {
      type boolean;
      description
        "Channel low alarm threshold crossed.";
    }
    leaf rx-channel-power-high-alarm {
      type boolean;
      description
        "Channel high alarm threshold crossed.";
    }
    leaf rx-channel-power-low-warning {
      type boolean;
      description
        "Channel low warning threshold crossed.";
    }
    leaf rx-channel-power-high-warning {
      type boolean;
      description
        "Channel high warning threshold crossed.";
    }
    description
      "Signal lane power channel threshold status.";
  }

  grouping coherent-device-otsi-diagnostics-lane-group {
    list lane {
      key "lane-index";
      leaf lane-index {
        type uint8 {
          range "1..max";
        }
        description
          "";
      }
      uses otsi-lane-power-threshold-diagnostics-group;
      uses otsi-lane-power-channel-threshold-diagnostics-group;
      description
        "";
    }
    description
      "Per lane diagnostic defects.";
  }

  grouping coherent-device-otsi-diagnostics-group {
    container diagnostics {
      uses coherent-device-otsi-diagnostics-common-group;
      uses coherent-device-otsi-diagnostics-lane-group;
      uses wavelogic-device-extension-types:wavelogic-device-otsi-diagnostics-group;
      description
        "";
    }
    description
      "";
  }
}
