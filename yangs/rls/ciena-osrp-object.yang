module ciena-osrp-object {
  yang-version 1.1;
  namespace "urn:ciena:params:xml:ns:yang:ciena-osrp-object";
  prefix osrp-object;

  import ciena-osrp-common-osrp-object {
    prefix ciena-osrp-common-osrp-object;
  }
  import ciena-common-version {
    prefix ciena-common-version;
  }

  organization
    "Ciena Corporation";
  contact
    "Web URL: http://www.ciena.com
     Postal: Ciena India Pvt. Ltd.
     Sector 32, Plot 14,
     Gurgaon 122001,
     Haryana, India";
  description
    "This module describes Ciena's OSRP object model for the 6500r platform";

  revision 2022-05-11 {
    description
      "grouped osrp-object to common yang.";
    ciena-common-version:string "1.2.0";
  }
  revision 2021-09-15 {
    description
      "Removed ciena-osrp-osrp-alarm (unused) under mount point.
       mounted ciena-osrp-osrp-network-topology marked as deprecated.";
    ciena-common-version:string "1.1.0";
  }
  revision 2021-02-18 {
    description
      "introduced 'osrp-object-common' grouping.";
    ciena-common-version:string "1.0.1";
  }
  revision 2021-02-18 {
    description
      "Initial revision.";
    ciena-common-version:string "1.0.0";
  }

  list osrp-object {
    description
      "Configuration data and operational data of OSRP objects";
    key "node-name";
    uses ciena-osrp-common-osrp-object:osrp-object-common;
  }
}
