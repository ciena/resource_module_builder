module ciena-pro-software-ctmp {
  namespace "urn:ciena:params:xml:ns:yang:ciena-pro-software-ctmp";
  prefix ciena-pro-software-ctmp;

  organization
    "Ciena Corporation";
  contact
    "Web URL: http://www.ciena.com/";
  description
    "This module defines software upgrade support for Ciena's 6500r CTMp family of cards";

  revision 2018-08-03 {
    description
      "Initial version";
  }
}
