module ciena-ddy-msg-stats {
  namespace "urn:ciena:params:xml:ns:yang:ciena-ddy-msg-stats";
  prefix ddy-msg-stats;

  import ciena-common-version {
    prefix version;
  }
  import ciena-common-yang {
    prefix yang;
  }

  organization
    "Ciena Corporation";
  contact
    "Web URL: http://www.ciena.com/
     Postal:  7035 Ridge Road
             Hanover, Maryland 21076
             U.S.A.
     Phone:   +1 800-921-1144
     Fax:     +1 410-694-5750";
  description
    "This is the model for the statistic portion of data driven messaging component of the
     Bifrost framework.";

  revision 2023-11-08 {
    description
      "Add notif-format-mismatch drop counter";
    version:version "version" {
      version:string "0.7.0";
    }
  }
  revision 2022-01-31 {
    description
      "Add format-mismatch drop counter";
    version:version "version" {
      version:string "0.6.0";
    }
  }
  revision 2021-03-28 {
    description
      "Introduce egress publication drop counter";
    version:version "version" {
      version:string "0.5.0";
    }
  }
  revision 2021-03-01 {
    description
      "Add priority queue counters";
    version:version "version" {
      version:string "0.4.0";
    }
  }
  revision 2020-12-11 {
    description
      "Add more detailed ingress/egress counters";
    version:version "version" {
      version:string "0.3.0";
    }
  }
  revision 2020-12-11 {
    description
      "Add list protocol-mismatches";
    version:version "version" {
      version:string "0.2.0";
    }
  }
  revision 2019-11-28 {
    description
      "Initial revision";
    version:version "version" {
      version:string "0.1.0";
    }
  }

  grouping protocol-monitor-statistics {
    yang:alias "protocol-mon-stats";
    leaf ingress-request {
      type uint64;
      description
        "Number of incoming requests";
    }
    leaf ingress-response {
      type uint64;
      description
        "Number of responses for the incoming requests";
    }
    leaf egress-request {
      type uint64;
      description
        "Number of outgoing requests";
    }
    leaf egress-response {
      type uint64;
      description
        "Number of responses received for the outgoing requests";
    }
    leaf egress-response-timeout {
      type uint64;
      description
        "Number of response timeouts for the outgoing requests";
    }
    leaf sent-publication {
      type uint64;
      description
        "Number of publications";
    }
    leaf received-publication {
      type uint64;
      description
        "Number of publications received";
    }
    leaf dropped {
      type uint64;
      description
        "Number of dropped packets";
    }
    leaf format-mismatch {
      type uint64;
      description
        "Number of dropped packets due to protocol format mismatch";
    }
    leaf notif-format-mismatch {
      type uint64;
      description
        "Number of dropped notifications packets due to protocol format mismatch";
    }
    container egress {
      container system {
        leaf request {
          type uint64;
          description
            "Number of outgoing system requests";
        }
        leaf response {
          type uint64;
          description
            "Number of responses from the system requests";
        }
        leaf response-timeout {
          type uint64;
          description
            "Number of timeout responses";
        }
        leaf sent-publication {
          type uint64;
          description
            "Number of publications";
        }
        leaf crud-dropped {
          type uint64;
          description
            "Number of outgoing system messages dropped";
        }
        leaf publication-dropped {
          type uint64;
          description
            "Number of outgoing system publication dropped";
        }
      }
      container high {
        leaf request {
          type uint64;
          description
            "Number of outgoing priority requests";
        }
        leaf response {
          type uint64;
          description
            "Number of responses from the priority requests";
        }
        leaf response-timeout {
          type uint64;
          description
            "Number of timeout responses";
        }
        leaf sent-publication {
          type uint64;
          description
            "Number of publication";
        }
        leaf crud-dropped {
          type uint64;
          description
            "Number of outgoing priority messages dropped";
        }
        leaf publication-dropped {
          type uint64;
          description
            "Number of outgoing priority publication dropped";
        }
      }
      container medium {
        leaf request {
          type uint64;
          description
            "Number of outgoing priority requests";
        }
        leaf response {
          type uint64;
          description
            "Number of responses from the priority requests";
        }
        leaf response-timeout {
          type uint64;
          description
            "Number of timeout responses";
        }
        leaf sent-publication {
          type uint64;
          description
            "Number of publications";
        }
        leaf crud-dropped {
          type uint64;
          description
            "Number of outgoing priority messages dropped";
        }
        leaf publication-dropped {
          type uint64;
          description
            "Number of outgoing priority publication dropped";
        }
      }
      container low {
        leaf request {
          type uint64;
          description
            "Number of outgoing priority requests";
        }
        leaf response {
          type uint64;
          description
            "Number of responses from the priority requests";
        }
        leaf response-timeout {
          type uint64;
          description
            "Number of timeout responses";
        }
        leaf sent-publication {
          type uint64;
          description
            "Number of publication sent";
        }
        leaf crud-dropped {
          type uint64;
          description
            "Number of outgoing priority messages dropped";
        }
        leaf publication-dropped {
          type uint64;
          description
            "Number of outgoing priority publication dropped";
        }
      }
    }
    container ingress {
      container system {
        description
          "System messages";
        leaf request {
          type uint64;
          description
            "Number of incoming system requests";
        }
        leaf response {
          type uint64;
          description
            "Number of responses due to the incoming system requests";
        }
        leaf received-publication {
          type uint64;
          description
            "Number of publication received";
        }
        leaf request-processing-hwm {
          type uint64;
          units "ns";
          description
            "The maximum length of time it took to process a request";
        }
        leaf publication-processing-hwm {
          type uint64;
          description
            "The maximum length of time it took to process a publication";
        }
        leaf dropped {
          type uint64;
          description
            "Number of outgoing system message dropped";
        }
        container publication-message-queue {
          leaf dropped {
            type uint64;
            description
              "Dropped due to queue is full";
          }
          leaf current-utilization {
            type decimal64 {
              fraction-digits 2;
            }
            description
              "Current utilization of the queue";
          }
          leaf utilization-hwm {
            type decimal64 {
              fraction-digits 2;
            }
            description
              "Queue utilization high watermark";
          }
          leaf message-age-hwm {
            type uint64;
            description
              "The age of the oldest message in the queue";
          }
        }
        container crud-message-queue {
          leaf dropped {
            type uint64;
            description
              "Dropped due to queue is full";
          }
          leaf current-utilization {
            type decimal64 {
              fraction-digits 2;
            }
            description
              "Current utilization of the queue";
          }
          leaf utilization-hwm {
            type decimal64 {
              fraction-digits 2;
            }
            description
              "Queue utilization high watermark";
          }
          leaf message-age-hwm {
            type uint64;
            description
              "The age of the oldest message in the queue";
          }
        }
      }
      container high {
        description
          "High priority messages";
        leaf request {
          type uint64;
          description
            "Number of incoming priority requests";
        }
        leaf response {
          type uint64;
          description
            "Number of responses from the priority requests";
        }
        leaf received-publication {
          type uint64;
          description
            "Number of publication received";
        }
        leaf request-processing-hwm {
          type uint64;
          units "ns";
          description
            "The maximum length of time it took to process a request";
        }
        leaf publication-processing-hwm {
          type uint64;
          description
            "The maximum length of time it took to process a publication";
        }
        leaf dropped {
          type uint64;
          description
            "Number of outgoing priority message dropped";
        }
        container publication-message-queue {
          leaf dropped {
            type uint64;
            description
              "Dropped due to the queue is full";
          }
          leaf current-utilization {
            type decimal64 {
              fraction-digits 2;
            }
            description
              "Current size of the high priority queue";
          }
          leaf utilization-hwm {
            type decimal64 {
              fraction-digits 2;
            }
            description
              "Queue utilization high watermark";
          }
          leaf message-age-hwm {
            type uint64;
            description
              "The age of the oldest message in the queue";
          }
        }
        container crud-message-queue {
          leaf dropped {
            type uint64;
            description
              "Dropped due to queue is full";
          }
          leaf current-utilization {
            type decimal64 {
              fraction-digits 2;
            }
            description
              "Current utilization of the queue";
          }
          leaf utilization-hwm {
            type decimal64 {
              fraction-digits 2;
            }
            description
              "Queue utilization high watermark";
          }
          leaf message-age-hwm {
            type uint64;
            description
              "The age of the oldest message in the queue";
          }
        }
      }
      container medium {
        description
          "Medium priority messages";
        leaf request {
          type uint64;
          description
            "Number of incoming priority requests";
        }
        leaf response {
          type uint64;
          description
            "Number of responses from the priority requests";
        }
        leaf received-publication {
          type uint64;
          description
            "Number of publication received";
        }
        leaf request-processing-hwm {
          type uint64;
          units "ns";
          description
            "The maximum length of time it took to process a request";
        }
        leaf publication-processing-hwm {
          type uint64;
          description
            "The maximum length of time it took to process a publication";
        }
        leaf dropped {
          type uint64;
          description
            "Number of outgoing priority message dropped";
        }
        container publication-message-queue {
          leaf dropped {
            type uint64;
            description
              "Dropped due to queue is full";
          }
          leaf current-utilization {
            type decimal64 {
              fraction-digits 2;
            }
            description
              "Current size of the medium priority queue";
          }
          leaf utilization-hwm {
            type decimal64 {
              fraction-digits 2;
            }
            description
              "Queue utilization high watermark";
          }
          leaf message-age-hwm {
            type uint64;
            description
              "The age of the oldest message in the queue";
          }
        }
        container crud-message-queue {
          leaf dropped {
            type uint64;
            description
              "Dropped due to queue is full";
          }
          leaf current-utilization {
            type decimal64 {
              fraction-digits 2;
            }
            description
              "Current utilization of the queue";
          }
          leaf utilization-hwm {
            type decimal64 {
              fraction-digits 2;
            }
            description
              "Queue utilization high watermark";
          }
          leaf message-age-hwm {
            type uint64;
            description
              "The age of the oldest message in the queue";
          }
        }
      }
      container low {
        description
          "Low priority messages";
        leaf request {
          type uint64;
          description
            "Number of incoming priority requests";
        }
        leaf response {
          type uint64;
          description
            "Number of responses from the priority requests";
        }
        leaf received-publication {
          type uint64;
          description
            "Number of publication received";
        }
        leaf request-processing-hwm {
          type uint64;
          units "ns";
          description
            "The maximum length of time it took to process a request";
        }
        leaf publication-processing-hwm {
          type uint64;
          description
            "The maximum length of time it took to process a publication";
        }
        leaf dropped {
          type uint64;
          description
            "Number of outgoing priority message dropped";
        }
        container publication-message-queue {
          leaf dropped {
            type uint64;
            description
              "Dropped due to queue is full";
          }
          leaf current-utilization {
            type decimal64 {
              fraction-digits 2;
            }
            description
              "Current utilization of the queue";
          }
          leaf utilization-hwm {
            type decimal64 {
              fraction-digits 2;
            }
            description
              "Queue utilization high watermark";
          }
          leaf message-age-hwm {
            type uint64;
            description
              "The age of the oldest message in the queue";
          }
        }
        container crud-message-queue {
          leaf dropped {
            type uint64;
            description
              "Dropped due to queue is full";
          }
          leaf current-utilization {
            type decimal64 {
              fraction-digits 2;
            }
            description
              "Current utilization of the queue";
          }
          leaf utilization-hwm {
            type decimal64 {
              fraction-digits 2;
            }
            description
              "Queue utilization high watermark";
          }
          leaf message-age-hwm {
            type uint64;
            description
              "The age of the oldest message in the queue";
          }
        }
      }
    }
  }

  container msg-stats {
    description
      "Contains statistics incoming and outgoing requests";
    config false;
    list protocol-mismatches {
      key "domain";
      leaf domain {
        type string;
        description
          "Domain with mismatch in transport protocol";
      }
    }
    container total {
      description
        "Contains the aggregate statistics for all incoming and outgoing requests";
      uses protocol-monitor-statistics;
    }
    list protocols {
      key "protocol";
      leaf protocol {
        type string;
        description
          "Name of the transport protocol";
      }
      uses protocol-monitor-statistics;
    }
  }
}
