module ciena-pro-nmc {
  namespace "urn:ciena:params:xml:ns:yang:ciena-pro-nmc";
  prefix pro-nmc;

  import ciena-common-version {
    prefix ciena-common-version;
  }
  import ciena-pro-optical-types {
    prefix ciena-pro-optical-types;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's network media channel (NMC) object.";

  revision 2022-01-11 {
    description
      "Adding snc-circuit-id";
    ciena-common-version:version "version" {
      ciena-common-version:string "1.2.0";
    }
  }
  revision 2021-11-11 {
    description
      "Adding effective-mc-occupancy";
    ciena-common-version:version "version" {
      ciena-common-version:string "1.1.0";
    }
  }
  revision 2020-08-01 {
    description
      "Initial version";
    ciena-common-version:version "version" {
      ciena-common-version:string "1.0.0";
    }
  }

  grouping nmc {
    leaf network-id {
      type string;
      description
        "This is used to stitch network media channel fragments end-to-end and must ideally be set
         to the network unique identifier of the end-to-end network media channel this fragment relates
         to or at a minimum to the center frequency value";
    }
    leaf owner {
      type string;
      description
        "This identifies the provisioning ownership of this network media channel";
    }
    leaf center-freq {
      type ciena-pro-optical-types:frequency;
      mandatory true;
      description
        "Center frequency of the network media channel";
    }
    leaf spectral-width {
      type ciena-pro-optical-types:frequency;
      mandatory true;
      description
        "Spectral width of the network media channel";
    }
    leaf effective-mc-occupancy {
      type ciena-pro-optical-types:frequency;
      description
        "The amount of spectral width within the mc that the nmc effectively occupies including dead band or guard band.
         Photonic control uses this to convert PSD to total power. The conversion needs to account for the dead space so that the
         power of the NMC achieves the average PSD across the mc bandwidth";
    }
    leaf user-label {
      type string;
      description
        "User provisioned label";
    }
    leaf snc-circuit-id {
      type string;
      description
        "This is the control plane sub-network connection (SNC) circuit ID associated with this NMC.";
    }
  }
}
