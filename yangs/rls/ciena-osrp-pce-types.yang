module ciena-osrp-pce-types {
  namespace "urn:ciena:params:xml:ns:yang:ciena-osrp-pce-types";
  prefix ciena-osrp-pce-types;

  import ciena-common-version {
    prefix ciena-common-version;
  }

  organization
    "Ciena Corporation";
  contact
    "Web URL: http://www.ciena.com
     Postal: Ciena India Pvt. Ltd.
     Sector 32, Plot 14,
     Gurgaon 122001,
     Haryana, India";
  description
    "This module describes Ciena's OSRP-PCE data types.";

  revision 2019-10-14 {
    ciena-common-version:string "1.0.0";
    description
      "6500r-series Release 2.0
       YANG cleanup.";
  }

  typedef node-id-type {
    type uint64;
  }

  typedef port-id-type {
    type uint64;
  }

  typedef node-name {
    type string {
      length "3..512";
    }
  }

  typedef hex-triplet {
    type string {
      length "10";
    }
  }

  typedef link-name {
    type string {
      length "1..1024";
    }
  }

  typedef frequency-mhz {
    type uint32;
    units "MHz";
  }

  typedef timeperiod-msec {
    type uint32 {
      range "0..3600000";
    }
    units "milliseconds";
  }

  typedef timeperiod-usec {
    type uint32 {
      range "0..3600000000";
    }
    units "microseconds";
  }

  typedef yes-no {
    type enumeration {
      enum "no";
      enum "yes";
    }
  }

  typedef state {
    type enumeration {
      enum "unblocked";
      enum "blocked";
    }
  }

  typedef link-type {
    type enumeration {
      enum "dwdm-50ghz-classic";
      enum "dwdm-100ghz-classic";
      enum "dwdm-flexgrid-classic";
      enum "dwdm-flexgrid-enhanced";
      enum "dwdm-50ghz-enhanced";
      enum "dwdm-100ghz-enhanced";
      enum "dwdm-fixed-flexgrid-enhanced";
    }
  }

  typedef rsa-constraint {
    type enumeration {
      enum "optimal";
      enum "route-availability";
      enum "blocked-link";
      enum "blocked-node";
      enum "node-version";
      enum "link-type";
      enum "regen-availability";
      enum "hops-inclusion";
      enum "hops-exclusion";
      enum "paths-exclusion";
      enum "direct-attach";
      enum "color-pattern-exclusion";
      enum "regen-reuse";
      enum "bandwidth-reuse";
      enum "spectrum-exclusive";
      enum "spectrum-assignment";
      enum "sparse-route";
      enum "spectrum-preferred";
      enum "route-computation-timeout";
    }
  }

  typedef rsa-route-order-algorithm {
    type enumeration {
      enum "shortest-path-first";
      enum "maximum-route-diversity";
    }
  }

  typedef rsa-result {
    type enumeration {
      enum "passed";
      enum "failed-dueto-destination-unreachable";
      enum "failed-dueto-system-busy";
      enum "failed-dueto-temporary-failure";
      enum "failed-dueto-out-of-memory";
      enum "failed-dueto-qos-unavailable";
      enum "failed-dueto-internal-error";
      enum "failed-dueto-request-queue-full";
      enum "failed-dueto-path-computation-timeout";
      enum "failed-dueto-link-not-present";
      enum "failed-dueto-node-not-present";
      enum "failed-dueto-max-admin-weight-exceeded";
      enum "failed-dueto-no-diverse-route-found";
      enum "failed-dueto-link-blocked";
      enum "failed-dueto-node-blocked";
      enum "failed-dueto-link-excluded";
      enum "failed-dueto-path-excluded";
      enum "failed-dueto-regen-unavailable";
      enum "failed-dueto-ing-da-link-constraint-failed";
      enum "failed-dueto-eg-da-link-constraint-failed";
      enum "failed-dueto-path-c-and-l-band";
      enum "failed-dueto-path-not-found";
      enum "failed-dueto-spectrum-allocation-failed";
      enum "failed-dueto-rsa-mc-spec-unspec";
      enum "failed-dueto-nmc-spec-unspec";
      enum "failed-dueto-mc-out-of-range";
      enum "failed-dueto-nmc-out-of-range";
      enum "failed-dueto-mc-size-out-of-range";
      enum "failed-dueto-nmc-out-of-range-mc";
      enum "failed-dueto-nmc-gap-insufficient";
      enum "failed-dueto-nmc-resolution-error";
      enum "failed-dueto-nmc-count-zero";
      enum "failed-dueto-nmc-expansion-insufficient-bw";
      enum "failed-dueto-nmc-expansion-alloc-error";
      enum "failed-dueto-nmc-too-close-to-edge";
      enum "failed-dueto-nmc-width-zero";
      enum "failed";
    }
  }

  grouping route-data-info {
    leaf name {
      type string {
        length "0..1024";
      }
      description
        "Key of route.";
    }

    list route-data {
      key "nodename";
      description
        "Transit List of hops in route.";
      uses ciena-osrp-pce-types:hop-info;
    }
  }

  grouping hop-info {
    leaf nodename {
      type node-name;
      description
        "Node name.";
    }

    leaf link {
      type link-name;
      description
        "Link name.";
    }
  }
}
