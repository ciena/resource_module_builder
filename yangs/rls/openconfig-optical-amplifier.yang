module openconfig-optical-amplifier {
  yang-version 1;
  namespace "http://openconfig.net/yang/optical-amplfier";
  prefix oc-opt-amp;

  import openconfig-platform {
    prefix oc-platform;
  }

  import openconfig-transport-line-common {
    prefix oc-line-com;
  }

  import openconfig-types {
    prefix oc-types;
  }

  import openconfig-extensions {
    prefix oc-ext;
  }

  organization
    "OpenConfig working group";
  contact
    "OpenConfig working group
     www.openconfig.net";
  description
    "This model describes configuration and operational state data
     for optical amplifiers, deployed as part of a transport
     line system.";

  revision 2019-12-06 {
    description
      "Add DYNAMIC_GAIN mode and related leaves.";
    reference
      "0.5.0";
  }
  revision 2018-11-21 {
    description
      "Add OpenConfig module metadata extensions.";
    reference
      "0.4.1";
  }
  revision 2017-10-02 {
    description
      "Add support for fiber type profile and physical component
       association for amplifier gain blocks.";
    reference
      "0.4.0";
  }
  revision 2017-09-08 {
    description
      "Correct bug with OSC interfaces";
    reference
      "0.3.1";
  }
  revision 2017-07-08 {
    description
      "Add monitor port type and refs to hw ports, ";
    reference
      "0.3.0";
  }
  revision 2017-03-28 {
    description
      "Added min/max/avg stats, status for media channels, OCM, APS";
    reference
      "0.2.0";
  }
  revision 2016-03-31 {
    description
      "Initial public release";
    reference
      "0.1.0";
  }

  oc-ext:openconfig-version "0.5.0";
  oc-ext:regexp-posix;
  oc-ext:catalog-organization "openconfig";
  oc-ext:origin "openconfig";

  identity OPTICAL_AMPLIFIER_TYPE {
    description
      "Type definition for different types of optical amplifiers";
  }

  identity EDFA {
    base OPTICAL_AMPLIFIER_TYPE;
    description
      "Erbium doped fiber amplifer (EDFA)";
  }

  identity FORWARD_RAMAN {
    base OPTICAL_AMPLIFIER_TYPE;
    description
      "Forward pumping Raman amplifier";
  }

  identity BACKWARD_RAMAN {
    base OPTICAL_AMPLIFIER_TYPE;
    description
      "Backward pumping Raman amplifier";
  }

  identity HYBRID {
    base OPTICAL_AMPLIFIER_TYPE;
    description
      "Hybrid backward pumping Raman + EDFA amplifier";
  }

  identity GAIN_RANGE {
    description
      "Base type for expressing the gain range for a switched gain
       amplifier.  The gain range is expressed as a generic setting,
       e.g., LOW/MID/HIGH. The actual db range will be determined
       by the implementation.";
  }

  identity LOW_GAIN_RANGE {
    base GAIN_RANGE;
    description
      "LOW gain range setting";
  }

  identity MID_GAIN_RANGE {
    base GAIN_RANGE;
    description
      "MID gain range setting";
  }

  identity HIGH_GAIN_RANGE {
    base GAIN_RANGE;
    description
      "HIGH gain range setting";
  }

  identity FIXED_GAIN_RANGE {
    base GAIN_RANGE;
    description
      "Fixed or non-switched gain amplfier";
  }

  identity OPTICAL_AMPLIFIER_MODE {
    description
      "Type definition for different types of optical amplifier
       operating modes";
  }

  identity CONSTANT_POWER {
    base OPTICAL_AMPLIFIER_MODE;
    description
      "Constant power mode. In constant power mode, the amplifier
       will maintain a constant output power by adjusting the
       amplifier gain and/or related variable optical attenuators";
  }

  identity CONSTANT_GAIN {
    base OPTICAL_AMPLIFIER_MODE;
    description
      "Constant gain mode. In constant gain mode, the amplifier
       will maintain a constant amplifier gain";
  }

  identity DYNAMIC_GAIN {
    base OPTICAL_AMPLIFIER_MODE;
    description
      "Dynamic gain mode. In dynamic gain mode, the amplifier will
       automatically adjust gain to stay within parameters defined
       by:
       - target-gain
       - min-gain
       - max-gain";
  }

  identity FIBER_TYPE_PROFILE {
    description
      "Type definition for different profiles of fiber types";
  }

  identity DSF {
    base FIBER_TYPE_PROFILE;
    description
      "Dispersion shifted fiber";
  }

  identity LEAF {
    base FIBER_TYPE_PROFILE;
    description
      "Large effective area fiber";
  }

  identity SSMF {
    base FIBER_TYPE_PROFILE;
    description
      "Standard single mode fiber";
  }

  identity TWC {
    base FIBER_TYPE_PROFILE;
    description
      "True wave classic";
  }

  identity TWRS {
    base FIBER_TYPE_PROFILE;
    description
      "True wave reduced slope";
  }

  grouping optical-amplifier-config {
    description
      "Configuration data for optical amplifiers";
    leaf name {
      type string;
      description
        "User-defined name assigned to identify a specific amplifier
         in the device";
    }

    leaf type {
      type identityref {
        base OPTICAL_AMPLIFIER_TYPE;
      }
      description
        "Type of the amplifier";
    }

    leaf target-gain {
      type decimal64 {
        fraction-digits 2;
        range "0..max";
      }
      units "dB";
      description
        "Positive gain applied by the amplifier. This is used
         when the amp-mode is in CONSTANT_GAIN or DYNAMIC_GAIN
         mode to set the target gain that the amplifier should
         achieve.";
    }

    leaf min-gain {
      type decimal64 {
        fraction-digits 2;
      }
      units "dBm";
      description
        "The minimum allowed gain of the amplifier. This is used
         when the amp-mode is in CONSTANT_POWER or DYNAMIC_GAIN mode
         to prevent the gain from dropping below a desired threshold.
         If left empty, the platform will apply a minimum gain based
         on hardware specifications.";
    }

    leaf max-gain {
      type decimal64 {
        fraction-digits 2;
      }
      units "dBm";
      description
        "The maximum allowed gain of the amplifier. This is used
         when the amp-mode is in CONSTANT_POWER or DYNAMIC_GAIN mode
         to prevent the gain from exceeding a desired threshold. If
         left empty, the platform will apply a maximum gain based on
         hardware specifications.";
    }

    leaf target-gain-tilt {
      type decimal64 {
        fraction-digits 2;
      }
      units "dB";
      description
        "Gain tilt control";
    }

    leaf gain-range {
      type identityref {
        base GAIN_RANGE;
      }
      description
        "Selected gain range.  The gain range is a platform-defined
         value indicating the switched gain amplifier setting";
    }

    leaf amp-mode {
      type identityref {
        base OPTICAL_AMPLIFIER_MODE;
      }
      description
        "The operating mode of the amplifier";
    }

    leaf target-output-power {
      type decimal64 {
        fraction-digits 2;
      }
      units "dBm";
      description
        "Output optical power of the amplifier.";
    }

    leaf max-output-power {
      type decimal64 {
        fraction-digits 2;
      }
      units "dBm";
      description
        "The maximum optical output power of the amplifier. This
         may be used to prevent the output power from exceeding a
         desired threshold.";
    }

    leaf enabled {
      type boolean;
      description
        "Turns power on / off to the amplifiers gain module.";
    }

    leaf fiber-type-profile {
      type identityref {
        base FIBER_TYPE_PROFILE;
      }
      description
        "The fiber type profile specifies details about the
         fiber type which are needed to accurately determine
         the gain and perform efficient amplification. This is
         only needed for Raman type amplifiers.";
    }
  }

  grouping optical-amplifier-state {
    description
      "Operational state data for optical amplifiers";
    leaf component {
      type leafref {
        path "/oc-platform:components/oc-platform:component/oc-platform:name";
      }
      description
        "Reference to the system-supplied physical component that
         the amplifier gain block is contained within. Multiple
         amplifier gain blocks may be contained within the same
         physical component.";
    }

    leaf ingress-port {
      type leafref {
        path "/oc-platform:components/oc-platform:component/oc-platform:name";
      }
      description
        "Reference to system-supplied name of the amplifier ingress
         port. This leaf is only valid for ports of type INGRESS.";
    }

    leaf egress-port {
      type leafref {
        path "/oc-platform:components/oc-platform:component/oc-platform:name";
      }
      description
        "Reference to system-supplied name of the amplifier egress
         port. This leaf is only valid for ports of type EGRESS.";
    }

    container actual-gain {
      description
        "The actual gain applied by the amplifier in units of
         0.01dB. If avg/min/max statistics are not supported,
         just supply the instant value";
      uses oc-types:avg-min-max-instant-stats-precision2-dB;
    }

    container actual-gain-tilt {
      description
        "The actual tilt applied by the amplifier in units of
         0.01dB. If avg/min/max statistics are not supported,
         just supply the instant value";
      uses oc-types:avg-min-max-instant-stats-precision2-dB;
    }

    container input-power-total {
      description
        "The total input optical power of this port in units
         of 0.01dBm. If avg/min/max statistics are not supported,
         just supply the instant value";
      uses oc-types:avg-min-max-instant-stats-precision2-dBm;
    }

    container input-power-c-band {
      description
        "The C band (consisting of approximately 191 to 195 THz or
         1530nm to 1565 nm) input optical power of this port in units
         of 0.01dBm. If avg/min/max statistics are not supported,
         just supply the instant value";
      uses oc-types:avg-min-max-instant-stats-precision2-dBm;
    }

    container input-power-l-band {
      description
        "The L band (consisting of approximately 184 to 191 THz or
         1565 to 1625 nm) input optical power of this port in units
         of 0.01dBm. If avg/min/max statistics are not supported,
         just supply the instant value";
      uses oc-types:avg-min-max-instant-stats-precision2-dBm;
    }

    container output-power-total {
      description
        "The total output optical power of this port in units
         of 0.01dBm. If avg/min/max statistics are not supported,
         just supply the instant value";
      uses oc-types:avg-min-max-instant-stats-precision2-dBm;
    }

    container output-power-c-band {
      description
        "The C band (consisting of approximately 191 to 195 THz or
         1530nm to 1565 nm)output optical power of this port in units
         of 0.01dBm. If avg/min/max statistics are not supported,
         just supply the instant value";
      uses oc-types:avg-min-max-instant-stats-precision2-dBm;
    }

    container output-power-l-band {
      description
        "The L band (consisting of approximately 184 to 191 THz or
         1565 to 1625 nm)output optical power of this port in units
         of 0.01dBm. If avg/min/max statistics are not supported,
         just supply the instant value";
      uses oc-types:avg-min-max-instant-stats-precision2-dBm;
    }

    container laser-bias-current {
      description
        "The current applied by the system to the transmit laser to
         achieve the output power. The current is expressed in mA
         with up to two decimal precision. If avg/min/max statistics
         are not supported, just supply the instant value";
      uses oc-types:avg-min-max-instant-stats-precision2-mA;
    }

    container optical-return-loss {
      description
        "The optical return loss (ORL) is the ratio of the light
         reflected back into the port to the light launched out of
         the port. ORL is in units of 0.01dBm. If avg/min/max
         statistics are not supported, just supply the instant value";
      uses oc-types:avg-min-max-instant-stats-precision2-dBm;
    }
  }

  grouping optical-amplifier-top {
    description
      "Top-level grouping for optical amplifier data";
    container optical-amplifier {
      description
        "Enclosing container for amplifiers and supervisory channels";
      container amplifiers {
        description
          "Enclosing container for list of amplifiers";
        list amplifier {
          key "name";
          description
            "List of optical amplifiers present in the device";
          leaf name {
            type leafref {
              path "../config/name";
            }
            description
              "Reference to the name of the amplifier";
          }

          container config {
            description
              "Configuration data for the amplifier";
            uses optical-amplifier-config;
          }

          container state {
            config false;
            description
              "Operational state data for the amplifier";
            uses optical-amplifier-config;

            uses optical-amplifier-state;
          }
        }
      }

      container supervisory-channels {
        description
          "Enclosing container for list of supervisory channels";
        list supervisory-channel {
          key "interface";
          description
            "List of supervisory channels";
          leaf interface {
            type leafref {
              path "../config/interface";
            }
            description
              "Reference to the interface of the supervisory channel";
          }

          uses oc-line-com:optical-osc-top;
        }
      }
    }
  }

  uses optical-amplifier-top;
}
