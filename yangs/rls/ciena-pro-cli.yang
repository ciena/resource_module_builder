module ciena-pro-cli {
  namespace "urn:ciena:params:xml:ns:yang:ciena-pro-cli";
  prefix ciena-pro-cli;

  import ciena-common-yang {
    prefix yang;
  }

  import ciena-common-version {
    prefix version;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's CLI model";

  revision 2021-04-21 {
    version:version "version" {
      version:string "1.3.0";
    }
    description
      "Removed table binds entry and RPC for custom CLI output";
  }
  revision 2020-12-22 {
    version:version "version" {
      version:string "1.2.0";
    }
    description
      "Added table binds entry and RPC for custom CLI output";
  }
  revision 2020-07-08 {
    version:version "version" {
      version:string "1.1.0";
    }
    description
      "Add in CLI options to control the prompt.";
  }
  revision 2020-03-30 {
    version:version "version" {
      version:string "1.0.0";
    }
    description
      "Initial revision.";
  }

  container cli {
    description
      "CLI config options";
    container config {
      leaf prompt {
        type string;
        description
          "Prompt to use.  Overrides the prompt-sources if both exist.";
      }

      leaf-list prompt-sources {
        type yang:target-node;
        description
          "Sources to use for a prompt.  Will look for each one and stop
           when one exists.  If the 'prompt' leaf exists, this list is ignnored";
      }
    }
  }

  rpc kill-session {
    description
      "Force the termination of a CLI session.";
    input {
      leaf session-id {
        type uint64;
        mandatory true;
        description
          "Particular session to kill.";
      }
    }
  }
}
