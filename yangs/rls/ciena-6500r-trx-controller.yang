module ciena-6500r-trx-controller {
  namespace "urn:ciena:params:xml:ns:yang:ciena-6500r-trx-controller";
  prefix trx-controller;

  import ciena-6500r-types {
    prefix common-types;
  }

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's Tx Controller Object";

  revision 2020-01-01 {
    description
      "RLS Release 2.0";
  }

  list trx-controller {
    description
      "TRX controller instances";
    key "name";
    leaf name {
      type common-types:object-name;
      description
        "The name of the controller";
    }
    uses common-types:admin-state;
  }
}
