module ciena-osrp-common-types {
  namespace "urn:ciena:params:xml:ns:yang:ciena-osrp-common-types";
  prefix osrp-common-types;

  import ciena-common-version {
    prefix ciena-common-version;
  }

  organization
    "Ciena Corporation";
  contact
    "Web URL: http://www.ciena.com
     Postal: Ciena India Pvt. Ltd.
     Sector 32, Plot 14,
     Gurgaon 122001,
     Haryana, India";
  description
    "This module describes Ciena's OSRP conn & port data types for usage in Osrp objects model.";

  revision 2023-04-24 {
    description
      "Added 'osrp-port-fault-source' and 'osrp-port-fault-cause'.";
    ciena-common-version:string "1.13.0";
  }
  revision 2023-02-13 {
    description
      "Added 'first-channel-provisioning' in conn-action enum.";
    ciena-common-version:string "1.12.0";
  }
  revision 2023-01-23 {
    description
      "Changed conn-owner type from enumeration to string.";
    ciena-common-version:string "1.11.0";
  }
  revision 2023-01-13 {
    description
      "Added action to define operation to be performed while channel provisioning/deprovisioning.";
    ciena-common-version:string "1.10.0";
  }
  revision 2023-01-10 {
    description
      "Added user-loopback to enum 'conn-owner'.";
    ciena-common-version:string "1.9.0";
  }
  revision 2022-11-01 {
    description
      "Added regen-disabled fault to enum 'osrp-port-fault'.";
    ciena-common-version:string "1.8.0";
  }
  revision 2022-09-12 {
    description
      "Added connectivity-type.";
    ciena-common-version:string "1.7.0";
  }
  revision 2022-06-11 {
    description
      "Added osrp-pfg-type.";
    ciena-common-version:string "1.6.0";
  }
  revision 2021-12-19 {
    description
      "Added unidirectional down OMS fault to enum 'osrp-port-fault'.";
    ciena-common-version:string "1.5.0";
  }
  revision 2021-12-14 {
    description
      "Added new enum 'optical-signal-fail' under rx-proxy-status.";
    ciena-common-version:string "1.4.0";
  }
  revision 2021-12-10 {
    description
      "Added new enum 'optical-signal-fail' under 'osrp-port-fault'.";
    ciena-common-version:string "1.3.0";
  }
  revision 2021-10-30 {
    description
      "band-type aligned with functional-group/roles band-types.";
    ciena-common-version:string "1.2.0";
  }
  revision 2021-10-28 {
    description
      "Added band specific OMS fault to enum osrp-port-fault.";
    ciena-common-version:string "1.1.0";
  }
  revision 2021-07-28 {
    description
      "Initial revision.";
    ciena-common-version:string "1.0.0";
  }

  typedef node-name {
    type string {
      length "3..512";
    }
  }

  typedef node-id-hex-type {
    type string {
      length "16";
    }
  }

  typedef osrp-admin-state {
    type enumeration {
      enum not-applicable;
      enum enabled;
      enum disabled;
    }
  }

  typedef osrp-operational-state {
    type enumeration {
      enum disabled;
      enum enabled;
    }
  }

  typedef osrp-port-direction {
    type enumeration {
      enum unknown;
      enum mux;
      enum demux;
    }
  }

  typedef osrp-port-role {
    type enumeration {
      enum unknown;
      enum boundary-in;
      enum boundary-out;
    }
  }

  typedef osrp-port-fault {
    type enumeration {
      enum none;
      enum c-band-down;
      enum c-band-blocked;
      enum c-band-degraded;
      enum och-down;
      enum och-degrade;
      enum l-band-down;
      enum l-band-blocked;
      enum l-band-degraded;
      enum optical-signal-fail;
      enum c-band-down-uni;
      enum l-band-down-uni;
      enum regen-disabled;
    }
  }

  typedef osrp-port-fault-source {
    type string {
      length "0..512";
    }
  }

  typedef osrp-port-fault-cause {
    type string {
      length "0..1024";
    }
  }

  typedef osrp-port-identifier {
    type string;
  }

  typedef band-type {
    type enumeration {
      enum BAND-1;
      enum BAND-2;
      enum BAND-3;
      enum BAND-4;
      enum BAND-5;
      enum BAND-C;
      enum BAND-L;
    }
  }

  typedef port-grid-type {
    type enumeration {
      enum C-BAND-FLEX;
      enum L-BAND-FLEX;
      enum C-L-BAND;
    }
  }

  typedef osrp-port-type {
    type enumeration {
      enum service;
      enum routing;
      enum internal;
    }
  }

  typedef osrp-pfg-type {
    type enumeration {
      enum unknown;
      enum channel;
      enum section;
      enum line;
      enum line-amp;
    }
  }

  typedef frequency-mhz {
    type uint32;
    units "MHz";
  }

  typedef timeperiod-msec {
    type uint32;
    units "milliseconds";
  }

  typedef osrp-local-mc-ckt-name {
    type string;
  }

  typedef osrp-local-mc-ckt-id {
    type string;
  }

  typedef osrp-local-nmc-ckt-name {
    type string;
  }

  typedef osrp-local-nmc-ckt-id {
    type string;
  }

  typedef channel-type {
    type enumeration {
      enum dynamic;
      enum permanent;
    }
  }

  typedef conn-owner {
    type string;
  }

  typedef conn-action {
    type enumeration {
      enum create {
        value 1;
      }
      enum edit {
        value 2;
      }
      enum delete {
        value 4;
      }
      enum permanent-delete {
        value 8;
      }
      enum forced-delete-controller {
        value 16;
      }
      enum set-ase-replacement-holdoff {
        value 32;
      }
      enum first-channel-provisioning {
        value 64;
      }
    }
  }

  typedef transmission-mode {
    type string {
      length "0..32";
    }
  }

  typedef link-optimization-mode {
    type enumeration {
      enum standard;
      enum snr-performance;
      enum fast-tracking;
      enum spectral-efficiency;
      enum low-latency;
      enum narrow-bandwidth-channel;
      enum non-linear-channel;
      enum foreign-line;
      enum reserved-mode-1;
      enum reserved-mode-2;
      enum reserved-mode-3;
      enum custom;
      enum unknown;
    }
  }

  typedef chromatic-dispersion {
    type decimal64 {
      fraction-digits 2;
    }
    units "ps/nm";
  }

  typedef channel-operational-state {
    type enumeration {
      enum inactive {
        description
          "Initial channel state";
      }
      enum waiting-for-power {
        description
          "Channel is waiting for sufficient power to be selected for addition.";
      }
      enum pending-add {
        description
          "Channel has been selected for addition.";
      }
      enum adding {
        description
          "Channel is in the process of being added.";
      }
      enum in-service {
        description
          "Channel has been added.";
      }
      enum waiting-for-downstream {
        description
          "Channel is waiting for the downstream section mux to finish deleting to be selected for deletion.";
      }
      enum pending-delete {
        description
          "Channel has been selected for deletion.";
      }
      enum deleting {
        description
          "Channel is in the process of being deleted.";
      }
      enum faulted {
        description
          "Fault has been declared against the channel.";
      }
      enum pending-ase-replacement {
        description
          "The faulted channel has been selected for ASE replacement.";
      }
      enum replacing-with-ase {
        description
          "Channel is in the process of being replaced by ASE.";
      }
      enum ase {
        description
          "Channel has been replaced by ASE.";
      }
      enum unknown {
        description
          "Channel controller state is not known.";
      }
    }
  }

  typedef rx-proxy-status {
    type enumeration {
      enum rx-degrade;
      enum rx-down;
      enum no-fault;
      enum optical-signal-fail;
    }
  }

  typedef connectivity-type {
    type enumeration {
      enum logical-link;
      enum network-link;
      enum regen-mate;
      enum da-info;
    }
  }
}
