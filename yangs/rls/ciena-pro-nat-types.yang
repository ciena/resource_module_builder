module ciena-pro-nat-types {
  yang-version 1.1;
  namespace "urn:ciena:params:xml:ns:yang:ciena-pro-nat-types";
  prefix ciena-pro-nat-types;

  import ciena-common-version {
    prefix ciena-common-version;
  }
  import ciena-pro-interfaces {
    prefix pro-if;
  }

  organization
    "Ciena Corporation";
  contact
    "Web URL: http://www.ciena.com/
     Postal:  7035 Ridge Road
             Hanover, Maryland 21076
             U.S.A.
     Phone:   +1 800-921-1144
     Fax:     +1 410-694-5750";
  description
    "This module defines used for provisioning NAT instances. ";

  revision 2022-03-29 {
    description
      "Changing ip-protocol-type from identity to enum";
    ciena-common-version:string "1.1.0";
  }
  revision 2021-10-21 {
    description
      "Initial revision";
    ciena-common-version:string "1.0.0";
  }

  typedef port-num-range {
    type union {
      type string {
        pattern '(6553[0-5]|655[0-2][0-9]|65[0-4][0-9]{2}|6[0-4][0-9]{3}|[0-5][0-9]{4}|[0-9]{1,4})\.\.(6553[0-5]|655[0-2][0-9]|65[0-4][0-9]{2}|6[0-4][0-9]{3}|[0-5][0-9]{4}|[0-9]{1,4})';
      }
      type uint16 {
        range "0..65535";
      }
      type enumeration {
        enum ANY {
          description
            "Indicates any valid port number (e.g., wildcard)";
        }
      }
    }
    description
      "Port numbers may be represented as a single value,
       an inclusive range as <lower>..<higher>, or as ANY to
       indicate a wildcard.";
  }

  typedef ip-protocol-type {
    type union {
      type uint8 {
        range "0..254";
      }
      type enumeration {
        enum IP_TCP {
          description
            "Transmission Control Protocol (6)";
        }
        enum IP_UDP {
          description
            "User Datagram Protocol (17)";
        }
        enum IP_ICMP {
          description
            "Internet Control Message Protocol (1)";
        }
      }
    }
    description
      "The IP protocol number may be expressed as a valid protocol
       number (integer) or using a protocol type defined by the
       IP_PROTOCOL identity";
  }

  grouping interface-ref-universal {
    description
      "Universal reference to interfaces and sub-interfaces
       Can be specified using either the pro-if model or as a string and uint32";
    leaf associated-interface {
      type union {
        type leafref {
          path "/pro-if:interfaces/pro-if:interface/pro-if:name";
        }
        type string;
      }
      description
        "Reference to a base interface.  If a reference to a sub-interface is required, this leaf must be specified to indicate
         the base interface. If a string is used it must fully reference a base interface";
    }
    leaf associated-sub-interface {
      type union {
        type leafref {
          path "/pro-if:interfaces/pro-if:interface[pro-if:name=current()/../associated-interface]/pro-if:sub-interface/pro-if:name";
        }
        type uint32;
      }
      description
        "Reference to a sub-interface.  -- this requires the base interface to be specified using the interface leaf in this container.
         If only a reference to a base interface is required, this leaf should not be set.
         If a uint32 is used it must reference the base sub-interface";
    }
  }
}
