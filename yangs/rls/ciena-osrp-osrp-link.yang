module ciena-osrp-osrp-link {
  yang-version 1.1;
  namespace "urn:ciena:params:xml:ns:yang:ciena-osrp-link";
  prefix osrp-link;

  import ciena-osrp-types {
    prefix ciena-osrp-types;
  }

  import ciena-common-version {
    prefix ciena-common-version;
  }

  organization
    "Ciena Corporation";
  contact
    "Web URL: http://www.ciena.com
     Postal: Ciena India Pvt. Ltd.
     Sector 32, Plot 14,
     Gurgaon 122001,
     Haryana, India";
  description
    "This module describes Ciena's OSRP LINK
     object model for the 6500r platform";

  revision 2021-02-05 {
    ciena-common-version:string "1.4.1";
    description
      "remote-link-conifg, remote-line-config changed to remote-link-inventory, remote-line-inventory resp.";
  }
  revision 2020-12-29 {
    ciena-common-version:string "1.4.0";
    description
      "Node-id field extended to 8 bytes.";
  }
  revision 2020-12-08 {
    ciena-common-version:string "1.3.0";
    description
      "Renamed comms-config container to out-of-band-comms-config,
       removed comms-provisioning from the container and renamed it to comms,
       added range in admin-weight and release-hold-off, removed ietf-yang-types import.";
  }
  revision 2019-10-07 {
    ciena-common-version:string "1.2.0";
    description
      "Added logical-port-id for tlpi display for routing-port on osrp.";
  }
  revision 2019-10-01 {
    ciena-common-version:string "1.1.0";
    description
      "6500r-series Release 2.2
       Replacing boolean auto-provisioning with enumeration comms-provisioning.";
  }
  revision 2019-09-06 {
    ciena-common-version:string "1.0.0";
    description
      "6500r-series Release 2.0
       YANG cleanup.";
  }
  revision 2019-04-11 {
    description
      "Initial revision.";
  }

  grouping ciena-osrp-osrp-link-mount {
    list osrp-link {
      key "name";
      leaf name {
        type ciena-osrp-types:link-key;
        mandatory true;
        description
          "Name of osrp link.";
      }

      leaf admin-weight {
        type uint32 {
          range "1..65535";
        }
        default "5040";
        description
          "Administrative weight which specifies the level of importance given to the OSRP link.";
      }

      leaf advertised-bandwidth {
        type uint16;
        config false;
        description
          "Advertised bandwidth (number of bits set = number of 6.25 slots available). Max. 1536.";
      }

      leaf comms {
        type ciena-osrp-types:comms-prov-mode;
        config false;
        description
          "Specifies if comms provisioning mode on the link";
      }

      leaf grid-type {
        type ciena-osrp-types:grid-type;
        config false;
        description
          "Type of supported Grid on the link.";
      }

      leaf hello-state {
        type enumeration {
          enum "not-applicable";
          enum "down";
          enum "attempt";
          enum "one-way-inside";
          enum "two-way-inside";
          enum "one-way-outside";
          enum "two-way-outside";
        }
        config false;
        description
          "State of the Hello protocol finite state machine.";
      }

      leaf interface-id {
        type uint32;
        config false;
        description
          "Interface id of the link.";
      }

      leaf is-master {
        type ciena-osrp-types:yes-no;
        config false;
        description
          "Specifies if this end of the OSRP link is the master.";
      }

      leaf label {
        type ciena-osrp-types:label;
      }

      leaf maximum-bandwidth {
        type uint16;
        config false;
        description
          "Maximum bandwidth (number of bits set = number of 6.25 slots). Max. 1536.";
      }

      container out-of-band-comms-config {
        leaf enable {
          type ciena-osrp-types:yes-no;
          default "no";
          description
            "Specifies whether comms signaling is enabled on this OSRP link.";
        }

        leaf remote-ip-address {
          type ciena-osrp-types:ip-address;
          description
            "Remote IP address of OSRP node for comms connectivity.(Format: n.n.n.n)";
        }

        leaf remote-node-id {
          type ciena-osrp-types:node-id-type;
          description
            "Remote Node ID for comms connectivity.";
        }

        leaf remote-udp-port {
          type ciena-osrp-types:comms-port-num;
          description
            "Remote UDP Port for comms connectivity.";
        }
      }

      leaf port-name {
        type string;
        config false;
        description
          "Name of osrp port associated with osrp-link.";
      }

      leaf-list prot-bundle-ids {
        type uint32;
        description
          "List of up to 20 protection bundles to which the OSRP link belongs.";
      }

      container remote-link-inventory {
        leaf admin-weight {
          type uint32;
          config false;
          description
            "Administrative weight associated with this OSRP link's remote side.";
        }

        leaf interface-id {
          type uint32;
          config false;
          description
            "Interface id of the remote link.";
        }

        leaf label {
          type ciena-osrp-types:label;
          config false;
          description
            "Label of the remote link.";
        }

        leaf link-name {
          type ciena-osrp-types:link-key;
          config false;
          description
            "Name of the remote link.";
        }

        leaf node-address {
          type ciena-osrp-types:node-address-type;
          config false;
          description
            "OSRP Node ID of remote link of 22 bytes (44 hexadecimal chars).";
        }

        leaf node-name {
          type ciena-osrp-types:node-name;
          config false;
          description
            "Name of the remote node.";
        }

        leaf node-type {
          type ciena-osrp-types:node-type;
          config false;
          description
            "Remote OSRP node type.";
        }

        leaf port-name {
          type string;
          config false;
          description
            "Name of osrp port associated with remote osrp-link.";
        }

        leaf-list prot-bundle-ids {
          type uint32;
          config false;
          description
            "List of up to 20 protection bundles to which the OSRP link remote side belongs.";
        }
      }

      leaf spectrum-snapshot {
        type string {
          length "384";
        }
        config false;
        description
          "Spectrum available on link.";
      }

      container line {
        leaf name {
          type ciena-osrp-types:link-key;
          config false;
          description
            "Line Name for the CTP";
        }

        leaf logical-port-identifier {
          type uint32;
          config false;
          description
            "Logical Port Id.";
        }

        leaf contained-ltp {
          type ciena-osrp-types:link-key;
          config false;
          description
            "contained LTP Name for the CTP";
        }

        leaf bandwidth-lockout {
          type ciena-osrp-types:yes-no;
          default "no";
          description
            "Indicates if bandwidth is locked on this link.";
        }

        leaf maintenance-mode {
          type ciena-osrp-types:yes-no;
          default "no";
          description
            "Indicates if faults to be ignored or not.";
        }

        leaf primary-state {
          type ciena-osrp-types:link-primary-state;
          description
            "Primary state of OSRP link.";
        }

        leaf release-hold-off {
          type ciena-osrp-types:timeperiod-sec {
            range "0..86400";
          }
          default "0";
          description
            "Line-Level hold-off timer delays the switch of traffic
             off a line until the end of the time period in sec. Range 0sec - 1day (0 - 86400) (in increments of 10secs). Default 0sec.";
        }

        container remote-line-inventory {
          leaf bandwidth-lockout {
            type ciena-osrp-types:yes-no;
            config false;
            description
              "Indicates if bandwidth is locked on remote OSRP line.";
          }

          leaf primary-state {
            type ciena-osrp-types:link-primary-state;
            config false;
            description
              "Primary state of remote OSRP link.";
          }

          leaf state {
            type ciena-osrp-types:state;
            config false;
            description
              "State of remote OSRP link.";
          }

          leaf virtual-path-connection-id {
            type uint16;
            config false;
            description
              "Common identifier of remote OSRP line.";
          }
        }

        leaf state {
          type ciena-osrp-types:state;
          config false;
          description
            "State of OSRP link.";
        }

        leaf virtual-path-connection-id {
          type uint16;
          default "0";
          description
            "Common identifier of OSRP line.";
        }
      }
    }
  }

  grouping ciena-osrp-osrp-link-mount-actions;

  uses ciena-osrp-osrp-link-mount;
}
