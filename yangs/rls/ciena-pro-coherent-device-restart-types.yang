module ciena-pro-coherent-device-restart-types {
  yang-version 1.1;
  namespace "urn:ciena:ns:yang:coherent-device-restart-types";
  prefix coherent-device-restart-types;

  import ietf-yang-types {
    prefix ietf-yang-types;
  }
  import ciena-common-version {
    prefix version;
  }

  organization
    "Ciena Corporation";
  contact
    "Web URL: http://www.ciena.com/
     Postal:  7035 Ridge Road
              Hanover, Maryland 21076
              U.S.A.
     Phone:   +1 800-921-1144
     Fax:     +1 410-694-5750";
  description
    "Restart definitions for coherent devices.";

  revision 2024-01-01 {
    description
      "Initial version.";
    version:version "version" {
      version:string "1.0.0";
    }
    reference
      "1.0.0";
  }

  typedef restart-reason-enum {
    type enumeration {
      enum unknown {
        description
          "The last restart reason is unknown.";
      }
      enum user {
        description
          "The last restart was manually triggered via the user interface.";
      }
      enum system {
        description
          "The last restart was triggered by the system.";
      }
      enum power-on {
        description
          "The last restart was due to a power-on event or device insertion.";
      }
    }
    description
      "";
  }

  typedef restart-type-enum {
    type enumeration {
      enum unknown {
        description
          "unknown";
      }
      enum warm {
        description
          "warm";
      }
      enum cold {
        description
          "cold";
      }
      enum reset {
        description
          "reset";
      }
    }
    description
      "";
  }

  grouping restart-status-group {
    leaf last-restart-reason {
      type restart-reason-enum;
      default "unknown";
      config false;
      description
        "";
    }
    leaf restart-type {
      type restart-type-enum;
      default "unknown";
      config false;
      description
        "";
    }
    leaf date-time-seconds {
      type uint32;
      default "0";
      config false;
      description
        "";
    }
    leaf date-time {
      type ietf-yang-types:date-and-time;
      config false;
      description
        "";
    }
    leaf on-since-seconds {
      type uint32;
      units "seconds";
      default "0";
      config false;
      description
        "Total uptime in seconds since the last initialization";
    }
    leaf on-since-date-time {
      type ietf-yang-types:date-and-time;
      config false;
      description
        "";
    }
    leaf lifetime {
      type uint32;
      units "minutes";
      default "0";
      config false;
      description
        "Lifetime of this device in minutes";
    }
    description
      "";
  }
}
