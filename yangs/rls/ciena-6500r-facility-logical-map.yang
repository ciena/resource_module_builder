module ciena-6500r-facility-logical-map {
  yang-version 1.1;
  namespace "urn:ciena:params:xml:ns:yang:ciena-6500r-facility-logical-map";
  prefix facility-logical-map;

  import ciena-common-version {
    prefix version;
  }

  organization
    "Ciena Corporation";
  contact
    "Web URL: http://www.ciena.com/
     Postal:  7035 Ridge Road
             Hanover, Maryland 21076
             U.S.A.
     Phone:   +1 800-921-1144
     Fax:     +1 410-694-5750";
  description
    "This module describes Ciena's facility logical index mapping object for the 6500r platform";

  revision 2021-05-04 {
    version:version "version" {
      version:string "0.1.0";
    }
    description
      "Add internal-name leaf and add ETHERNET type";
  }
  revision 2020-06-30 {
    version:version "version" {
      version:string "0.0.1";
    }
    description
      "Version formating";
  }
  revision 2019-02-20 {
    description
      "6500r Release 1.0";
  }

  grouping ciena-6500r-facility-logical-map-mount {
    list facility-logical-map {
      key "handle";
      leaf handle {
        type instance-identifier;
        description
          "The instance identifier of the facility";
      }

      leaf type {
        type enumeration {
          enum "OSC" {
            description
              "OSC facility";
          }
          enum "ETHERNET" {
            description
              "Ethernet";
          }
        }
      }

      leaf logical-index {
        type uint32;
        description
          "The snmp index of the facility";
      }

      leaf hardware-index {
        type uint32;
        description
          "The hardware index of the facility";
      }

      leaf internal-name {
        type string {
          length "1..16";
        }
        description
          "Internal name of the facility that the handle leaf points
           to.  This leaf represents the name of the IP interface
           created in the operating system which is associated
           with the facility.";
      }
    }
  }

  grouping ciena-6500r-facility-logical-map-mount-actions;

  uses ciena-6500r-facility-logical-map-mount;
}
