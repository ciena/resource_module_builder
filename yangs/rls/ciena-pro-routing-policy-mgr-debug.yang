module ciena-pro-routing-policy-mgr-debug {
  namespace "urn:ciena:params:xml:ns:yang:ciena-pro-routing-policy-mgr-debug";
  prefix ciena-pro-routing-policy-mgr-debug;

  organization
    "Ciena Corporation";
  contact
    "Web URL: http://www.ciena.com/
     Postal:  7035 Ridge Road
             Hanover, Maryland 21076
             U.S.A.
     Phone:   +1 800-921-1144
     Fax:     +1 410-694-5750";
  description
    "This modules describes Ciena's pro platform routing-policy-mgr debug facility.";

  revision 2019-12-12 {
    description
      "Initial revision";
  }

  grouping debug-control {
    description
      "List of debugging levels";
    leaf level {
      type uint32;
      description
        "What level to set debugging/logging to";
    }
  }

  grouping internal-states {
    description
      "Routing-policy-mgr process states";
    leaf init-in-progress {
      type boolean;
      description
        "Initialization in progress";
    }
    leaf is-db-recovered {
      type boolean;
      description
        "Internal DB recovered";
    }
    leaf db-valid {
      type boolean;
      description
        "Internal DB valid";
    }
  }

  container debug {
    uses debug-control;
    container states {
      config false;
      uses internal-states;
    }
  }
}
