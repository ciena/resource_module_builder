module ciena-6500r-guestos {
  yang-version 1.1;
  namespace "urn:ciena:params:xml:ns:yang:ciena-6500r-guestos";
  prefix guestos;

  import ciena-common-version {
    prefix ciena-common-version;
  }
  import ciena-common-yang {
    prefix ciena-common-yang;
  }

  organization
    "Ciena Corporation";
  contact
    "Web URL: http://www.ciena.com";
  description
    "This module describes Ciena's GuestOS objects for the 6500r platform";

  revision 2021-08-20 {
    description
      "6500r Release 1.0-
       First release";
    ciena-common-version:string "1.0.0";
  }

  rpc trigger-guestos-clean {
    input {
      leaf slot {
        type string;
        description
          "Which slot is to be cleaned.  'CTM' is the only supported option for now.";
      }
      leaf force-clean {
        type boolean;
        description
          "Force GuestOS clean if shelf upgrade is in progress";
      }
    }
    output {
      leaf result {
        type boolean;
      }
      uses ciena-common-yang:rpc-result-common;
    }
  }
}
