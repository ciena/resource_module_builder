module ciena-6500r-osrp-rls-ra-link-relation {
  namespace "urn:ciena:params:xml:ns:yang:ciena-6500r-osrp-rls-ra-link-relation";
  prefix link-relation;

  import ciena-6500r-osrp-rls-ra-types {
    prefix osrp-rls-ra-types;
  }
  import ciena-common-version {
    prefix ciena-common-version;
  }

  organization
    "Ciena Corporation";
  contact
    "Web URL: http://www.ciena.com
     Postal: Ciena India Pvt. Ltd.
     Sector 32, Plot 14,
     Gurgaon 122001,
     Haryana, India";
  description
    "This module describes Relation between BoundaryLink(osrp-port From and To Pair) and DiscreteLinks for the 6500r platform";

  revision 2020-09-25 {
    description
      "discrete-link-identifier type used for discrete-link-trail.";
    ciena-common-version:string "1.1.0";
  }
  revision 2020-09-22 {
    description
      "Initial revision.";
    ciena-common-version:string "1.0.0";
  }

  list link-relation {
    key "from to";
    uses link-relation-grouping;
  }

  grouping link-relation-grouping {
    leaf from {
      type osrp-rls-ra-types:osrp-port-identifier;
      description
        "From port of the BoundaryLink in relation.";
      mandatory true;
    }
    leaf to {
      type osrp-rls-ra-types:osrp-port-identifier;
      description
        "To port of the BoundaryLink in relation.";
      mandatory true;
    }
    leaf-list discrete-link-trail {
      type osrp-rls-ra-types:discrete-link-identifier;
      description
        "List of encoded discrete link names related to BoundaryLink (Min: 0, Max: 16).";
      min-elements 0;
      max-elements 16;
    }
  }
}
