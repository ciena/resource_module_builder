module ciena-logging-mgr-options {
  yang-version 1;
  namespace "urn:ciena:params:xml:ns:yang:ciena-logging-mgr-options";
  prefix ciena-logging-mgr-options;

  import ciena-common-version {
    prefix ciena-common-version;
  }
  import ciena-common-yang {
    prefix ciena-common-yang;
  }

  organization
    "Ciena Corporation";
  contact
    "Web URL: http://www.ciena.com/
     Postal:  7035 Ridge Road
             Hanover, Maryland 21076
             U.S.A.
     Phone:   +1 800-921-1144
     Fax:     +1 410-694-5750";
  description
    "This is the model for the logging options";

  revision 2023-08-29 {
    description
      "Initial revision for logging-mgr options";
  }

  grouping skip-database-check {
    description
      "Services to skip the database check for";
    leaf-list service-name {
      type string {
        ciena-common-yang:stringptr "true";
      }
      description
        "Service name to skip";
    }
  }

  container logging-options {
    description
      "Used by depo to define database options";
    uses skip-database-check;
  }
}
