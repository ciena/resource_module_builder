module ciena-pro-aaa-common {
  namespace "urn:ciena:params:xml:ns:yang:ciena-pro-aaa-common";
  prefix ciena-pro-aaa-common;

  import ciena-common-version {
    prefix ciena-common-version;
  }

  organization
    "Ciena Corporation";
  contact
    "Web URL: http://www.ciena.com/
     Postal:  7035 Ridge Road
             Hanover, Maryland 21076
             U.S.A.
     Phone:   +1 800-921-1144
     Fax:     +1 410-694-5750";
  description
    "This module defines the common types of AAA security
     functionality.";

  revision 2020-10-22 {
    ciena-common-version:string "0.4.0";
    description
      "Make model platform independent";
  }
  revision 2020-01-22 {
    ciena-common-version:string "0.3.1";
    description
      "Adding new typedef for IP address or FQDN string.";
  }
  revision 2020-01-22 {
    ciena-common-version:string "0.3.0";
    description
      "Adding sftp, debug, and console to the access-interface enumeration leafs.";
  }
  revision 2019-12-10 {
    ciena-common-version:string "0.2.1";
    description
      "Fixing typos in descriptions.";
  }
  revision 2019-09-05 {
    ciena-common-version:string "0.2.0";
    description
      "Adding access levels diag and initial.";
  }
  revision 2019-08-26 {
    ciena-common-version:string "0.1.0";
    description
      "Add gRPC to the access-interface enumeration leaf.";
  }
  revision 2019-01-05 {
    description
      "Initial version of common AAA types";
  }

  typedef user-name {
    type string {
      length "2..40";
    }
    description
      "User name string that has a range of 2 to 40 characters.
       Valid character includes alphanumeric and '-', '_', '.'";
  }

  typedef user-password {
    type string {
      length "8..128";
    }
    description
      "Clear text password string that shall be between 8 to 128 characters.";
  }

  typedef string-maxl-32 {
    type string {
      length "0..32";
    }
    description
      "Standard string that has a max length of 32 characters.";
  }

  typedef string-maxl-64 {
    type string {
      length "0..64";
    }
    description
      "Standard string that has a max length of 64 characters.";
  }

  typedef string-maxl-128 {
    type string {
      length "0..128";
    }
    description
      "Standard string that has a max length of 128 characters.";
  }

  typedef string-maxl-256 {
    type string {
      length "0..256";
    }
    description
      "Standard string that has a max length of 256 characters.";
  }

  typedef enabled-disabled-enum {
    type enumeration {
      enum "enabled" {
        description
          "enabled state.";
      }
      enum "disabled" {
        description
          "disabled state.";
      }
    }
    description
      "enabled or disabled type.";
  }

  typedef up-down-enum {
    type enumeration {
      enum "up" {
        description
          "up state.";
      }
      enum "down" {
        description
          "down state.";
      }
    }
    description
      "up or down type.";
  }

  typedef ipaddr-or-hostname {
    type string {
      length "1..63";
    }
    description
      "IP address or hostname string.";
  }

  typedef ipaddr-or-fqdn {
    type string {
      length "1..256";
    }
    description
      "IP address or FQDN string.";
  }

  typedef access-level {
    type enumeration {
      enum "limited" {
        description
          "User has limited (mostly read-only) privileges. Limited user shall
           - be a read only user with access to retrieve most of the system configurations.
           - NOT be able to retrieve most of  security configurations, except their own user and user session information.
           - be able to change their own password";
      }
      enum "admin" {
        description
          "User has administrative privileges. Admin user shall
           - be able to perform all the capabilities of limited user
           - be able to provision most of the system configurations
           - NOT be able to retrieve and provision most of  security configurations,
            except retrieve their own user and user session information
           - be able to change their own password";
      }
      enum "super" {
        description
          "User has superuser privileges. Super user shall
           - be able to perform all the capabilities of admin and limited user
           - be able to perform all retrieval and provisioning of security related configurations
             (Configuring  and retrieving users, user sessions, TACACS+, banners, ssh, intrusion ...)
           - be able to execute RPC ";
      }
      enum "diag" {
        description
          "User has debug shell access. Diag user shall
           - be able to perform all the capabilities of super user
           - be able to execute the CLI command diag-shell";
      }
      enum "initial" {
        description
          "User has very limited access. Initial user shall
           - only be able to change their own password
           - Note: can not create a user with initial access level, only used for default user.";
      }
    }
  }

  typedef authentication-type {
    type enumeration {
      enum "local" {
        description
          "Authentication based on local user list.";
      }
      enum "radius" {
        description
          "Remote authentication via RADIUS, if configured/enabled.";
      }
      enum "tacacs" {
        description
          "Remote authentication via TACACS+, if configured/enabled.";
      }
    }
  }

  typedef access-interface {
    type enumeration {
      enum "cli" {
        description
          "User is from CLI interface.";
      }
      enum "netconf" {
        description
          "User is from NETCONF interface.";
      }
      enum "rest" {
        description
          "User is from REST interface.";
      }
      enum "grpc" {
        description
          "User is from gRPC interface.";
      }
      enum "debug" {
        description
          "User is from SSH server debug port.";
      }
      enum "sftp" {
        description
          "User is from SSH server sftp port.";
      }
      enum "console" {
        description
          "User is from console port.";
      }
    }
  }
}
