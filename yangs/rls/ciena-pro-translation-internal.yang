module ciena-pro-translation-internal {
  yang-version 1.1;
  namespace "urn:ciena:params:xml:ns:yang:ciena-pro-translation-internal";
  prefix internal;

  import ciena-common-yang {
    prefix common-yang;
  }
  import ciena-common-version {
    prefix version;
  }
  import ciena-common-recording-agent {
    prefix recording;
  }

  organization
    "Ciena Corporation";
  contact
    "Web URL: http://www.ciena.com";
  description
    "Internal data to support model translations";

  revision 2024-03-05 {
    description
      "Adding tags for recordings";
    version:string "1.1.0";
  }
  revision 2022-07-15 {
    description
      "Initial revision";
    version:string "1.0.0";
  }

  identity translate-data {
    base recording:recording-type;
    description
      "Data translation.";
  }

  identity translate-filter {
    base recording:recording-type;
    description
      "Filter translation.";
  }

  container model-translate-internal {
    description
      "internal structure used to help model translator";
    leaf stringptr {
      type string {
        common-yang:stringptr "true";
      }
    }
  }
}
