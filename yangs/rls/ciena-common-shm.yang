module ciena-common-shm {
  namespace "urn:ciena:params:xml:ns:yang:ciena-common-shm";
  prefix shm;

  import ciena-common-version {
    prefix version;
  }

  organization
    "Ciena Corporation";
  contact
    "Web URL: http://www.ciena.com/
     Postal:  7035 Ridge Road
             Hanover, Maryland 21076
             U.S.A.
     Phone:   +1 800-921-1144
     Fax:     +1 410-694-5750";
  description
    "Model to represent a shared memory config and status";

  revision 2021-05-09 {
    description
      "Added 'enabled' option for the consumer.";
    version:version "version" {
      version:string "1.2.0";
    }
  }
  revision 2021-04-20 {
    description
      "Added 'unconfigured' state.";
    version:version "version" {
      version:string "1.1.0";
    }
  }
  revision 2021-01-24 {
    description
      "Initial revision";
    version:version "version" {
      version:string "1.0.0";
    }
  }

  container shared-memory {
    container config {
      leaf master {
        type boolean;
      }
      leaf base {
        type uint64;
      }
      leaf enabled {
        description
          "If set, the consumer will use the shared memory else it is ignored.";
        type boolean;
        default "true";
      }
    }
    container state {
      config false;
      leaf initialized {
        type boolean;
        default "false";
      }
      leaf master {
        type boolean;
      }
      leaf error {
        type enumeration {
          enum unconfigured;
          enum base-misalignment;
          enum offset-misalignment;
          enum version-misalignment;
        }
      }
      leaf base {
        type uint64;
      }
    }
  }
}
