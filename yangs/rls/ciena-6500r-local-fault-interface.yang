module ciena-6500r-local-fault-interface {
  namespace "urn:ciena:params:xml:ns:yang:ciena-6500r-local-fault-interface";
  prefix local-fault-interface;

  import ciena-common-version {
    prefix ciena-common-version;
  }

  import ciena-6500r-types {
    prefix types;
  }

  import ietf-yang-types {
    prefix yang;
  }

  organization
    "Ciena Corporation";
  contact
    "Web URL: http://www.ciena.com/
     Postal:  7035 Ridge Road
              Hanover, Maryland 21076
              U.S.A.
     Phone:   +1 800-921-1144
     Fax:     +1 410-694-5750";
  description
    "This modules describes Ciena's interface to Local fault Service";

  revision 2020-11-18 {
    ciena-common-version:string "1.1.0";
    description
      "Add a timestamp to the display-masked-alarms to indicate the time of
       the last state change.";
  }
  revision 2020-09-01 {
    ciena-common-version:string "1.0.0";
    description
      "Initial revision";
  }

  rpc display-masked-alarms {
    description
      "This rpc will display all the masked alarms for a given slot, however if the slot is not provided the rpc will display the masked alarms for all slots.";
    input {
      leaf slot-name {
        type types:object-name;
        description
          "The name of the slot";
      }
    }

    output {
      list masked-alarms {
        key "id";
        leaf id {
          type uint32;
          description
            "Unique identifying value assigned to an alarm record";
        }

        leaf name {
          type string;
          description
            "Alarm name.";
        }

        leaf resource {
          type instance-identifier;
          description
            "Resource under alarm";
        }

        leaf raise-time {
          type yang:date-and-time;
          description
            "Storage for a formatted timestamp value of format
             yyyy-mm-ddThh:mm:ssZ.";
        }
      }
    }
  }
}
