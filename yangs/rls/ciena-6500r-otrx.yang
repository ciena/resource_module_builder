module ciena-6500r-otrx {
  yang-version 1.1;
  namespace "urn:ciena:params:xml:ns:yang:ciena-6500r-otrx";
  prefix otrx;

  import ciena-6500r-types {
    prefix ciena-6500r-types;
  }

  import ciena-6500r-ports {
    prefix ports;
  }

  import ciena-common-version {
    prefix version;
  }

  organization
    "Ciena Corporation";
  contact
    "Web URL: http://www.ciena.com/
     Postal:  7035 Ridge Road
             Hanover, Maryland 21076
             U.S.A.
     Phone:   +1 800-921-1144
     Fax:     +1 410-694-5750";
  description
    "This module describes Ciena's otrx object for the 6500r platform";

  revision 2020-06-30 {
    version:version "version" {
      version:string "0.0.1";
    }
    description
      "Version formating";
  }
  revision 2019-02-01 {
    description
      "6500r Release 1.0";
  }

  grouping ciena-6500r-otrx-mount {
    list otrx {
      key "name";
      leaf name {
        type string {
          length "1..63";
        }
        description
          "OTRX facility name";
      }

      leaf parent-port {
        type leafref {
          path "/ports:port/ports:name";
        }
        mandatory true;
        description
          "OTRX Parent";
      }

      leaf launch-power {
        type ciena-6500r-types:power {
          range "-22.0..-16.0";
        }
        units "dBm";
        default "-16.0";
        description
          "OTRX launch power in dBm.";
      }

      leaf los-threshold {
        type ciena-6500r-types:power {
          range "-22.0..6.0";
        }
        units "dBm";
        default "-15.0";
        description
          "LOS threshold in dBm.";
      }

      leaf frequency {
        type ciena-6500r-types:frequency;
        default "191.250";
        config false;
        description
          "Frequency";
      }

      uses ciena-6500r-types:admin-state;
    }
  }

  grouping ciena-6500r-otrx-mount-actions;

  uses ciena-6500r-otrx-mount;
}
