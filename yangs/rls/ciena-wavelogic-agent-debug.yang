module ciena-wavelogic-agent-debug {
  namespace "urn:ciena:params:xml:ns:yang:ciena-wavelogic-agent-debug";
  prefix wavelogic-agent-debug;

  import ciena-common-version {
    prefix ciena-common-version;
  }

  organization
    "Ciena Corporation";
  contact
    "Web URL: http://www.ciena.com";
  description
    "Wavelogic Agent debug module";

  revision 2022-09-09 {
    description
      "Initial revision";
    ciena-common-version:string "1.0.0";
    reference
      "1.0.0";
  }

  container debug {
    container dump-cond-data {
      description
        "dump the conditioning data into a file";
      leaf dump {
        type boolean;
      }
      leaf filename {
        type string {
          length "0..100";
        }
        description
          "optional file name to dump the data";
      }
    }
    description
      "debug";
  }
}
