module ciena-pro-access-groups-options {
  namespace "urn:ciena:params:xml:ns:yang:ciena-pro-access-groups-options";
  prefix access-groups-options;

  import ciena-common-version {
    prefix ciena-common-version;
  }
  import ciena-common-yang {
    prefix yang;
  }

  organization
    "Ciena Corporation";
  contact
    "Web URL: http://www.ciena.com";
  description
    "This module provides deployment wide options for access groups.";

  revision 2023-04-12 {
    ciena-common-version:string "1.0.0";
    description
      "Initial revision.";
  }

  container access-groups-options {
    description
      "container to hold access control for internal resources
       which are not publicly exposed";
    leaf internal-resource-blocking {
      type boolean;
      default "false";
      description
        "this flag controls the access of internal resources.";
    }
  }
}
