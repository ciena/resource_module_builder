module ciena-swagger {

  namespace "urn:ciena:params:xml:ns:yang:ciena-swagger";

  prefix "swagger";

  import ciena-publish {
    prefix publish;
  }
 
  organization "Ciena Corporation";

  contact
    "Web URL: http://www.ciena.com/
     Postal:  7035 Ridge Road
             Hanover, Maryland 21076
             U.S.A.
     Phone:   +1 800-921-1144
     Fax:     +1 410-694-5750";

  description
    "This module defines extensions which are used to control the 
     Swagger specification generator.";

  revision 2017-09-15 {
    description
      "Added 'hidden' extension.";
    reference "";
  }

  revision 2016-12-07 {
    description
      "Removed unused imports.  Added description to extension.";
    reference "";
  }

  revision 2015-04-07 {
    description 
      "";
    reference "";
  }

  publish:enabled "false";

  extension support {
    argument value;
    description
      "A boolean value of \"true\" of \"false\", false is default.  If used
       within a module, it will trigger the module to be translated into a
       Swagger specification.  If false, the module will be ingnored by the
       yang-to-swagger translator.  Has no effect if used on any other nodes
       other than module.";
  }

  extension hidden {
    argument value;
    description
      "Hide a container or other YANG node from the Swagger UI.";
  }
}
