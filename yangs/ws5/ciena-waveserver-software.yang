module ciena-waveserver-software {
  namespace "urn:ciena:params:xml:ns:yang:ciena-ws:ciena-waveserver-software";
  prefix software;

  import ciena-ui {
    prefix ui;
  }
  import ciena-waveserver-typedefs {
    prefix cienawstypes;
  }
  import ciena-swagger {
    prefix swagger;
  }
  swagger:support "true";

  organization "Ciena Corporation";
  contact
    "Web URL: http://www.ciena.com/
     Postal:  7035 Ridge Road
             Hanover, Maryland 21076
             U.S.A.
     Phone:   +1 800-921-1144
     Fax:     +1 410-694-5750";
  description
    "This module defines Software Status and Upgrade support for Ciena's Waveserver Platform.";

  revision 2019-09-27 {
    description
      "Changed input descriptions for rpc's 'waveserver-software-check-local',
        'waveserver-software-activate', and 'waveserver-software-delete'.
       Added support for group software upgrade.
       Added leaf 'version-name' in grouping 'software-release-group'.
       Added grouping 'network-member-attribute-group'.
       Added container 'network'.
       Changed input 'url' to optional for rpc 'waveserver-software-download'.";
    reference "Waveserver Ai R1.5 user's guide.";
  }

  revision 2018-06-01 {
    description
      "Added 'delete-from-load' optional input argument to the install/activate/commit RPCs.
       Added 'software-clear-log', 'software-check-local', and 'software-check-remote' RPCs.
       Added new 'software-op-state' enum value for license check.";
    reference "Waveserver Ai R1.2 user's guide.";
  }

  revision 2017-12-07 {
    description
      "Added support for multi-step upgrade RPCs for 'download', 'activate', and 'commit'.
       Added 'upgrade-log' attribute support.";
    reference "Waveserver Ai R1.1 user's guide.";
  }

  revision 2017-09-07 {
    description
      "Waveserver Platform Data Model
      Migrated from Waveserver Classic R1.4 YANG model.
      Updated namespace to 'ciena-waveserver'.
      Updated 'software-op-state' and 'upgrade-op-state' enum values.
      Removed several unsupported attributes/containers/RPCs.
      Added WCS and Module status containers/attributes.
      Moved some common attributes into groupings.";
    reference "Waveserver Ai R1.0 user's guide.";
  }

  grouping software-device-status-group {
    description
      "Grouping for WCS and Module software status attributes.";
    leaf boot-zone {
      ui:ui-name "Boot Zone";
      type boot-zone;
      description
        "The boot zone for the specified device.";
    }
    leaf last-restart {
      ui:ui-name "Last Restart";
      type cienawstypes:string-maxl-32;
      description
        "The date and time of last restart in 'YYYY-MM-DD HH:MM:SS' format, or
         empty string if unknown.";
    }
    leaf last-restart-reason {
      ui:ui-name "Last Restart Reason";
      type cienawstypes:restart-reason;
      description
        "Cause for the last restart.";
    }
    leaf boot-image-a {
      ui:ui-name "Boot Image A";
      type cienawstypes:string-maxl-64;
      description
        "The boot image or firmware image name for zone A.";
    }
    leaf boot-image-b {
      ui:ui-name "Boot Image B";
      type cienawstypes:string-maxl-64;
      description
        "The boot image or firmware image name for zone B.";
    }
  }

  grouping software-release-group {
    description
      "Grouping for active and installed software release attributes.";
    leaf version {
      ui:ui-name "Version";
      type cienawstypes:string-maxl-32;
      description
        "The software release version.";
    }
    leaf build-number {
      ui:ui-name "Build Number";
      type cienawstypes:string-maxl-32;
      description
        "The software release build number.";
    }
    leaf build-tag {
      ui:ui-name "Build Tag";
      type cienawstypes:string-maxl-32;
      description
        "The software release build tag.";
    }
    leaf build-date {
      ui:ui-name "Build Date";
      type cienawstypes:string-maxl-32;
      description
        "The software release build date.";
    }
    leaf version-name {
      ui:ui-name "Version Name";
      type cienawstypes:string-maxl-64;
      description
        "The software release version name.";
    }
  }

  typedef software-rtncode {
    type uint32;
    description
      "Return code value used in the software module. 0 indicate success. A
       non-zero value indicates failure.";
  }

  typedef software-check-status {
    type enumeration {
      enum "pass" {
        description
          "The validation check passed.";
      }
      enum "fail" {
        description
          "The validation check failed.";
      }
    }
    description
      "The pass/fail result of a validation check performed in one of the
       software-check RPCs.";
  }

  typedef software-op-state {
    type enumeration {
      enum "unknown" {
        description
          "Software operational state is unknown.";
      }
      enum "normal" {
        description
          "Software operational state is normal.";
      }
      enum "upgrade-in-progress" {
        description
          "Software upgrade is in progress.";
      }
      enum "automatic-upgrade-in-progress" {
        description
          "Automatic software upgrade is in progress.";
      }
      enum "restart-in-progress" {
        description
          "System restart is in progress. WCS is initializing but not yet in
           'boot-complete' state.";
      }
      enum "module-restart-in-progress" {
        description
          "One or more modules is initializing and has not yet reached run-mode
           'run' state.";
      }
      enum "application-failed" {
        description
          "One or more required applications is not running.";
      }
    }
    description
      "Software operational state.";
  }

  typedef upgrade-op-state {
    type enumeration {
      enum "unknown" {
        description
          "Upgrade operational state is unknown.";
      }
      enum "idle" {
        description
          "Software upgrade is idle.";
      }
      enum "download-in-progress" {
        description
          "Software download is in progress.";
      }
      enum "download-complete" {
        description
          "Software download is complete.";
      }
      enum "download-failed" {
        description
          "Software download failed.";
      }
      enum "activation-in-progress" {
        description
          "Software activation is in progress.";
      }
      enum "activation-complete" {
        description
          "Software activation is complete.";
      }
      enum "activation-failed" {
        description
          "Software activation failed.";
      }
      enum "installation-in-progress" {
        description
          "Software installation is in progress.";
      }
      enum "installation-failed" {
        description
          "Software installation failed.";
      }
      enum "commit-in-progress" {
        description
          "Software commit is in progress.";
      }
      enum "commit-failed" {
        description
          "Software commit failed.";
      }
      enum "cancel-in-progress" {
        description
          "Software cancel operation is in progress.";
      }
      enum "cancel-failed" {
        description
          "Software cancel operation failed.";
      }
      enum "delete-in-progress" {
        description
          "Software delete operation is in progress.";
      }
      enum "delete-failed" {
        description
          "Software delete operation failed.";
      }
      enum "automatic-upgrade-in-progress" {
        description
          "Automatic software upgrade is in progress.";
      }
      enum "automatic-upgrade-failed" {
        description
          "Automatic software upgrade failed.";
      }
      enum "module-cold-restart-required" {
        description
          "A cold restart is required on one or more modules.";
      }
      enum "license-check-failed" {
        description
          "License check failed. Licensing alarms need to be cleared.";
      }
    }
    description
      "Software upgrade operational state.";
  }

  typedef boot-zone {
    type enumeration {
      enum "unknown" {
        description
          "Boot zone is unknown.";
      }
      enum "a" {
        description
          "Boot zone A.";
      }
      enum "b" {
        description
          "Boot zone B.";
      }
    }
    description
      "The boot zone type.";
  }

  grouping network-member-attribute-group {
    description
      "Common attributes of network member";
    leaf network-id {
      type uint8;
      description
        "The network-id.";
    }
    leaf site-id {
      type uint8;
      description
        "The site-id.";
    }
    leaf group-id {
      type uint8;
      description
        "The group-id.";
    }
    leaf member-name {
      type cienawstypes:string-maxl-64;
      description
        "The member-name.";
    }
    leaf member-id {
      type uint8;
      description
        "The member-id.";
    }
  }

  container waveserver-software {
    ui:ui-name "Software";
    description
      "Waveserver software upgrade and load management.";

    container status {
      ui:ui-name "Status";
      config false;
      description
        "Waveserver software status information.";
      leaf software-operational-state {
        ui:ui-name "Software Operational State";
        type software-op-state;
        description
          "The current software operational state.";
      }
      leaf upgrade-operational-state {
        ui:ui-name "Upgrade Operational State";
        type upgrade-op-state;
        description
          "The current upgrade operational state.";
      }
      leaf committed-version {
        ui:ui-name "Committed Version";
        type cienawstypes:string-maxl-64;
        description
          "The committed software release version.";
      }
      leaf active-version {
        type cienawstypes:string-maxl-64;
        description
          "The active software release version.";
      }
      leaf upgrade-to-version {
        type cienawstypes:string-maxl-64;
        description
          "The software release version currently being upgraded to, if
           applicable.";
      }
      leaf last-operation {
        type cienawstypes:string-maxl-128;
        description
          "The software upgrade last operation.";
      }
      leaf upgrade-log {
        type cienawstypes:string-maxl-128;
        description
          "The software upgrade log file URI on the Waveserver.";
      }
    }//end status

    container wcs-status {
      ui:ui-name "WCS Software Status";
      config false;
      description 
          "Software status information for the Waveserver Control Subsystem
           control module.";
      leaf boot-image-version {
        ui:ui-name "Boot Image Version";
        type cienawstypes:string-maxl-32;
        description
          "The current boot image version for the WCS.";
      }
      leaf fpga-id {
        ui:ui-name "FPGA Id";
        type cienawstypes:string-maxl-64;
        description
          "The current FPGA image identifier for the WCS.";
      }
      uses software-device-status-group;
    }//end wcs-status

    container module-status {
      ui:ui-name "Module Software Status";
      config false;
      description 
          "Module software status information.";
      list module {
        ui:ui-name "Module List";
        key "module-id";
        description 
          "List containing module-specific software status information.";
          leaf module-id {
            ui:ui-name "Module ID";
            type cienawstypes:name-string;
            mandatory true;
            description
              "Unique access identifier string of the Module, which may just be
               a slot number (e.g. '1'). Key value for the Module list.";
          }
          uses software-device-status-group;
      }
    }//end module-status

    container active {
      ui:ui-name "Active Software";
      config false;
      description
        "Waveserver active software information.";
      uses software-release-group;
    }//end active

    container installed {
      ui:ui-name "Installed Software";
      config false;
      description
        "Waveserver installed software release information.";
      list versions {
        key "index";
        description
          "A list of installed software releases on this Waveserver.";
        leaf index {
          ui:ui-name "Installed Index";
          type uint8;
          description
            "Unique id, read-only attribute.";
        }
        uses software-release-group;
      }
    }//end installed

    container network {
      description
        "Network upgrade status.";
      container upgrade {
        description
          "Network upgrade.";
        leaf auto-member-upgrade {
          type boolean;
          default "false";
          description
            "Auto-upgrade enabled for network.";
        }
        leaf upgrade-operational-state {
          type upgrade-op-state;
          config false;
          description
            "The current network upgrade operational state.";
        }
      }
      list member-status {
        key "network-id site-id group-id member-name";
        config false;
        description
          "Network member software status.";
        uses network-member-attribute-group;
        leaf software-operational-state {
          ui:ui-name "Software Operational State";
          type software-op-state;
          description
            "The current software operational state.";
        }
        leaf upgrade-operational-state {
          ui:ui-name "Upgrade Operational State";
          type upgrade-op-state;
          description
            "The current upgrade operational state.";
        }
        leaf committed-version {
          ui:ui-name "Committed Version";
          type cienawstypes:string-maxl-64;
          description
            "The committed software release version.";
        }
        leaf active-version {
          type cienawstypes:string-maxl-64;
          description
            "The active software release version.";
        }
        leaf upgrade-to-version {
          type cienawstypes:string-maxl-64;
          description
            "The software release version currently being upgraded to, if
             applicable.";
        }
        leaf last-operation {
          type cienawstypes:string-maxl-128;
          description
            "The software upgrade last operation.";
        }
      }
      list member-log {
        key "network-id site-id group-id member-name";
        config false;
        description
          "Network member log.";
        uses network-member-attribute-group;
        leaf upgrade-log-file {
          type cienawstypes:string-maxl-128;
          description
            "The software upgrade log file URI on the Waveserver.";
        }
      } //end list member-log
      list software-library {
        key "network-id site-id group-id member-name";
        config false;
        description
          "Network member software library.";
        uses network-member-attribute-group;
        container installed {
          description
            "Installed Version.";
          list versions {
            key "index";
            description
              "Network member installed version.";
            leaf index {
              ui:ui-name "Installed Index";
              type uint8;
              description
                "Unique id, read-only attribute.";
            }
            uses software-release-group;
          }
        }
      }
    }//end network
  }

  rpc waveserver-software-install {
    description
      "Perform one-step software upgrade (download, activate, and commit) via
       url string.";
    input {
      leaf url {
        type cienawstypes:string-maxl-254;
        mandatory true;
        description
          "The URL specifying the remote location and package name to be installed.
           Example format is 'scp://<uid>:<pwd>@<ip-address>/<path>/<filename>'.";
      }
      leaf group {
        type boolean;
        description
          "Indicates that this RPC op is for the whole network group or for 
           the local system only.";
      }
      leaf delete-from-load {
        type boolean;
        default "false";
        description
          "Optionally delete the 'from' load upon successful completion.";
      }
    }
    output {
      leaf return-code {
        type software-rtncode;
        description
          "return code: 0 is success; non-zero is failure";
      }
      leaf return-string {
        type cienawstypes:string-maxl-254;
        description
          "Return code description";
      }
    }
  }
  rpc waveserver-software-download {
    description
      "Download software load via url string.";
    input {
      leaf url {
        type cienawstypes:string-maxl-254;
        description
          "The URL specifying the remote location and package name to be installed.
           Example format is 'scp://<uid>:<pwd>@<ip-address>/<path>/<filename>'.
           Optional for group download.";
      }
      leaf group {
        type boolean;
        description
          "Indicates that this RPC op is for the whole network group or for 
           the local system only.";
      }
    }
    output {
      leaf return-code {
        type software-rtncode;
        description
          "return code: 0 is success; non-zero is failure";
      }
      leaf return-string {
        type cienawstypes:string-maxl-254;
        description
          "Return code description";
      }
    }
  }
  rpc waveserver-software-activate {
    description
      "Perform software activate via version string.";
    input {
      leaf version {
        type cienawstypes:string-maxl-32;
        mandatory true;
        description
          "The load version string including the build number and tag (Ex: waveserver-1.5.0.281-GA).";
      }
      leaf group {
        type boolean;
        description
          "Indicates that this RPC op is for the whole network group or for 
           the local system only.";
      }
      leaf auto-commit {
        type boolean;
        default "false";
        description
          "Optionally specify that the software load be automatically committed
           after activation.";
      }
      leaf delete-from-load {
        type boolean;
        default "false";
        description
          "Optionally delete the 'from' load upon successful completion.";
      }
    }
    output {
      leaf return-code {
        type software-rtncode;
        description
          "return code: 0 is success; non-zero is failure";
      }
      leaf return-string {
        type cienawstypes:string-maxl-254;
        description
          "Return code description";
      }
    }
  }
  rpc waveserver-software-delete {
    description
      "Perform software delete via version string.";
    input {
      leaf version {
        type cienawstypes:string-maxl-32;
        mandatory true;
        description
          "The load version string including the build number and tag (Ex: waveserver-1.5.0.281-GA).";
      }
      leaf group {
        type boolean;
        description
          "Indicates that this RPC op is for the whole network group or for 
           the local system only.";
      }
    }
    output {
      leaf return-code {
        type software-rtncode;
        description
          "return code: 0 is success; non-zero is failure";
      }
      leaf return-string {
        type cienawstypes:string-maxl-254;
        description
          "Return code description";
      }
    }
  }
  rpc waveserver-software-commit {
    description
      "Perform software commit operation in the current load has not been
       committed and it is in boot completion state.";
    input {
      leaf delete-from-load {
        type boolean;
        default "false";
        description
          "Optionally delete the 'from' load upon successful completion.";
      }
      leaf group {
        type boolean;
        description
          "Indicates that this RPC op is for the whole network group or for 
           the local system only.";
      }
    }
    output {
      leaf return-code {
        type software-rtncode;
        description
          "return code: 0 is success; non-zero is failure";
      }
      leaf return-string {
        type cienawstypes:string-maxl-254;
        description
          "Return code description";
      }
    }
  }
  rpc waveserver-software-cancel {
    description
      "Cancel an existing software upgrade operation that is in a failed state.";
    input {
      leaf group {
        type boolean;
        description
          "Indicates that this RPC op is for the whole network group or for 
           the local system only.";
      }
    }
    output {
      leaf return-code {
        type software-rtncode;
        description
          "return code: 0 is success; non-zero is failure";
      }
      leaf return-string {
        type cienawstypes:string-maxl-254;
        description
          "Return code description";
      }
    }
  }
  rpc waveserver-software-clear-log {
    description
      "Clear the contents of the local software upgrade log file.";
    output {
      leaf return-code {
        type software-rtncode;
        description
          "return code: 0 is success; non-zero is failure";
      }
      leaf return-string {
        type cienawstypes:string-maxl-254;
        description
          "Return code description";
      }
    }
  }
  rpc waveserver-software-check-local {
    description
      "Perform software check of a local load version.";
    input {
      leaf version {
        type cienawstypes:string-maxl-32;
        mandatory true;
        description
          "The load version string including the build number and tag (Ex: waveserver-1.5.0.281-GA).";
      }
    }
    output {
      leaf version {
        type cienawstypes:string-maxl-32;
        description
          "The software release version.";
      }
      leaf disk-space-check {
        type software-check-status;
        description
          "The pass/fail result of the disk space check.";
      }
      leaf rpm-checksum-verification {
        type software-check-status;
        description
          "The pass/fail result of the RPM checksum verification.";
      }
      leaf license-check {
        type software-check-status;
        description
          "The pass/fail result of the base software license check.";
      }
      leaf overall-status {
        type software-check-status;
        description
          "The the overall pass/fail result of the software check operation.";
      }
    }
  }
  rpc waveserver-software-check-remote {
    description
      "Perform software check of a remote candidate load url string.";
    input {
      leaf url {
        type cienawstypes:string-maxl-254;
        mandatory true;
        description
          "The URL specifying the remote location and package name to be checked.
           Example format is 'scp://<uid>:<pwd>@<ip-address>/<path>/<filename>'.";
      }
    }
    output {
      leaf version {
        type cienawstypes:string-maxl-32;
        description
          "The software release version.";
      }
      leaf disk-space-check {
        type software-check-status;
        description
          "The pass/fail result of the disk space check.";
      }
      leaf url-validation {
        type software-check-status;
        description
          "The pass/fail result of the input URL validation.";
      }
      leaf license-check {
        type software-check-status;
        description
          "The pass/fail result of the base software license check.";
      }
      leaf overall-status {
        type software-check-status;
        description
          "The the overall pass/fail result of the software check operation.";
      }
    }
  }
}
