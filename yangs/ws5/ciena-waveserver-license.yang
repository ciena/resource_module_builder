module ciena-waveserver-license {
  namespace "urn:ciena:params:xml:ns:yang:ciena-ws:ciena-waveserver-license";
  prefix license;

  import ciena-ui {
    prefix ui;
  }
  import ciena-waveserver-alarm {
    prefix alarm;
  }
  import ciena-waveserver-typedefs {
    prefix cienawstypes;
  }
  import ciena-swagger {
    prefix swagger;
  }
  swagger:support "true";

  organization "Ciena Corporation";
  contact
    "Web URL: http://www.ciena.com/
     Postal:  7035 Ridge Road
             Hanover, Maryland 21076
             U.S.A.
     Phone:   +1 800-921-1144
     Fax:     +1 410-694-5750";
  description
    "This module defines the software licensing state for Ciena's Waveserver, including installed licenses, and compliance to licensing requirements.";

  revision 2019-02-21 {
    description
      "Added license compliance state enum.";
    reference "Waveserver Ai R1.4 user's guide.";
  }

  revision 2018-06-20 {
      description
      "Waveserver Platform Data Model
       Migrated from Waveserver Classic R1.6 YANG model.";
    reference "Waveserver Ai R1.2 user's guide.";
  }

  typedef license-compliance-state {
    type enumeration {
      enum "not-compliant" {
        description 
          "The system is not compliant with all licensing requirements.";
      }
      enum "compliant" {
        description
          "The system complies with all licensing requirements.";
      }
      enum "not-initialized" {
        description
          "The  licensing system is not initialized yet as time is not set.";
      }
    }
    description
      "Whether the system complies with all licensing requirements.";
  }

  typedef license-type {
    type enumeration {
      enum "trial" {
        description
          "Trial License";
      }
      enum "served" {
        description
          "Served License";
      }
      enum "pre-authorized" {
        description
          "Pre-Authorized License";
      }
    }
    description
      "License type.";
  }

  typedef license-status {
    type enumeration {
      enum "valid" {
        description
          "Valid License";
      }
      enum "invalid" {
        description
          "Invalid License";
      }
      enum "expired" {
        description
          "Expired License";
      }
    }
    description
      "Validity of the license.";
  }

  typedef license-source {
    type enumeration {
      enum "pre-install" {
        description
          "Pre-Installed License";
      }
      enum "local" {
        description
          "Locally Held License";
      }
      enum "pre-authorized" {
        description
          "Pre-Authorized License";
      }
    }
    description
      "The source of the license.";
  }

  container waveserver-license {
    ui:ui-name "License";
    description
      "Waveserver license information parameters.";
    container client {
      ui:ui-name "License Client";
      description
        "License client information.";
      container id {
        ui:ui-name "License Client Identification";
        description
          "License client identification information.";
        leaf registration-id {
          ui:ui-name "Registration Id";
          type cienawstypes:string-maxl-64;
          description
            "License client registration id";
        }
      }
      container state {
        ui:ui-name "License Client State";
        description
          "License client state information.";
        leaf admin-state {
          type cienawstypes:enabled-disabled-enum;
          description
            "Administrative state of the license service. Always enabled.";
        }
        leaf operational-state {
          type cienawstypes:up-down-enum;
          config false;
          description
            "Operational state of the license service.";
        }
        leaf compliance-state {
          ui:ui-name "Compliance State";
          type license-compliance-state;
          config false;
          description
            "Whether the license client is compliant.";
        }
      }
      list alarm-instances {
        ui:ui-name "License Alarm Instances";
        key "instance";
        config false;
        description
          "A reference table of the defined alarm instances associated with
           the license client. Each alarm instance is associated with a
           specific software feature that may be supported on the system.";
        leaf instance {
          ui:ui-name "Alarm Instance";
          type alarm:alarm-instance-string;
          description
            "The object instance the license alarm may be raised against.";
        }
        leaf feature {
          ui:ui-name "Feature Name";
          type cienawstypes:string-maxl-128;
          description
            "The name of the feature associated with the license instance.";
        }
        leaf description {
          ui:ui-name "Description";
          type cienawstypes:string-maxl-128;
          description
            "Description of the feature associated with the license instance.";
        }
      }
    }
    container licenses {
      ui:ui-name "Licenses";
      config false;
      description
        "Waveserver licenses.";
      list licenses-list {
        ui:ui-name "Licenses List";
        key "license-index";
        description
          "List of waveserver licenses.";
        leaf license-index {
          ui:ui-name "License Index";
          type uint32;
          mandatory true;
          description
            "License index, unique, key value for the License List.";
        }
        leaf name {
          ui:ui-name "License Name";
          type cienawstypes:string-maxl-128;
          description
            "Name of the License.";
        }
        leaf description {
          ui:ui-name "License Description";
          type cienawstypes:string-maxl-128;
          description
            "Description of the License.";
        }
        leaf version {
          ui:ui-name "Version";
          type cienawstypes:string-maxl-16;
          description
            "Version of the License.";
        }
        leaf status {
          ui:ui-name "Status";
          type license-status;
          description
            "Status of the License.";
        }
        leaf source {
          ui:ui-name "Source";
          type license-source;
          description
            "Source of the License.";
        }
        leaf issuer-name {
          ui:ui-name "Issuer Name";
          type cienawstypes:string-maxl-128;
          description
            "Name of the Issuer of the License.";
        }
        leaf issued-date {
          ui:ui-name "Issued Date";
          type cienawstypes:string-maxl-128;
          description
            "Date the License was issued.";
        }
        leaf type {
          ui:ui-name "Type";
          type license-type;
          description
            "Type of the License.";
        }
        leaf host-id {
          ui:ui-name "Host Id";
          type cienawstypes:string-maxl-128;
          description
            "Host Id of the License.";
        }
        leaf count {
          ui:ui-name "Count";
          type cienawstypes:string-maxl-16;
          description
            "Number of License instances available.";
        }
        leaf checked-out-count {
          ui:ui-name "Checked out Count";
          type cienawstypes:string-maxl-16;
          description
            "Number of License instances checked out.";
        }
        leaf expiry-date {
          ui:ui-name "Expiry Date";
          type cienawstypes:string-maxl-32;
          description
            "Date the License expires.";
        }
        leaf notice {
          ui:ui-name "Notice";
          type cienawstypes:string-maxl-128;
          description
            "Notice of the License.";
        }
      }
    }
    container server {
      ui:ui-name "License Server";
      description
        "License server information.";
      leaf host-address {
        ui:ui-name "Host Address";
        type string {
          length "0..256";
          pattern '.+:[0-9]+';
        }
        description
          "The license server host name and port number, separated by a colon.";
      }
      leaf num-license-servers {
        ui:ui-name "Number of License Servers";
        type uint32;
        config false;
        description
          "The number of license servers.";
      }
    }  
  }
  rpc waveserver-license-file-delete {
    description
      "Perform a license file delete.";
    input {
      leaf filename {
        ui:ui-name "Filename";
        type cienawstypes:string-maxl-254;
        description
          "Filename of the license file.";
      }
    }
    output {
      leaf license-return-code {
        type uint32;
        description
          "License return code: 0 is successful; non-zero is failure";
      }
      leaf license-return-string {
        type cienawstypes:string-maxl-254;
        description
          "License return code description";
      }
    }
  }
  rpc waveserver-license-file-generate-request {
    description
      "Generate a license capability file.";
    output {
      leaf license-return-code {
        type uint32;
        description
          "License return code: 0 is successful; non-zero is failure";
      }
      leaf license-return-string {
        type cienawstypes:string-maxl-254;
        description
          "License return code description";
      }
    }
  }
  rpc waveserver-license-file-activate {
    description
      "Activate a downloaded license file.";
    input {
      leaf filename {
        ui:ui-name "Filename";
        type cienawstypes:string-maxl-254;
        description
          "Filename of the license file.";
      }
    }
    output {
      leaf license-return-code {
        type uint32;
        description
          "License return code: 0 is successful; non-zero is failure";
      }
      leaf license-return-string {
        type cienawstypes:string-maxl-254;
        description
          "License return code description";
      }
    }
  }
  rpc waveserver-license-server-clear {
    description
      "Clear the license server information.";
    output {
      leaf license-return-code {
        type uint32;
        description
          "License return code: 0 is successful; non-zero is failure";
      }
      leaf license-return-string {
        type cienawstypes:string-maxl-254;
        description
          "License return code description";
      }
    }
  }
  rpc waveserver-license-file-download {
    description
      "Download a license file.";
    input {
      leaf mode {
        ui:ui-name "Mode";
        type enumeration {
          enum "none" {
            value 0;
            description
              "No FTP mode is specified.";
          }
          enum "tftp" {
            value 1;
            description
              "Trivial File Transfer Protocol (TFTP) mode.";
          }
          enum "ftp" {
            value 2;
            description
              "File Transfer Protocol (FTP) mode.";
          }
          enum "sftp" {
            value 3;
            description
              "Secure File Transfer Protocol (SFTP) mode.";
          }
          enum "scp" {
            value 4;
            description
              "Secure Copy Protocol (SCP) mode.";
          }
        }
        mandatory true;
        description
          "XFP mode: TFTP, FTP, SFTP, or SCP.";
      }
      leaf server {
        ui:ui-name "Server";
        type cienawstypes:string-maxl-64;
        mandatory true;
        description
          "Server IP Address.";
      }
      leaf login-id {
        ui:ui-name "Login ID";
        type cienawstypes:string-maxl-32;
        description
          "Login ID.";
      }
      leaf password {
        ui:ui-name "Password";
        type cienawstypes:string-maxl-128;
        description
          "Password in clear text.";
      }
      leaf filename {
        ui:ui-name "Filename";
        type cienawstypes:string-maxl-254;
        mandatory true;
        description
          "Filename of the license file.";
      }
    }
    output {
      leaf license-return-code {
        type uint32;
        description
          "License return code: 0 is successful; non-zero is failure";
      }
      leaf license-return-string {
        type cienawstypes:string-maxl-254;
        description
          "License return code description";
      }
    }
  }
}
