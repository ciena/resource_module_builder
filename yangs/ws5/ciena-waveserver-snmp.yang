module ciena-waveserver-snmp {
  namespace "urn:ciena:params:xml:ns:yang:ciena-ws:ciena-waveserver-snmp";
  prefix snmp-if;

  import yuma-ncx {
    prefix ncx;
  }
  import ciena-waveserver-typedefs {
    prefix cienawstypes;
  }
  import ciena-waveserver-port {
    prefix port;
  }
  import ciena-ddf {
    prefix ddf;
  }
  import ciena-ui {
    prefix ui;
  }
  import ciena-swagger {
    prefix swagger;
  }
  swagger:support "true";

  organization "Ciena Corporation";
  contact
    "Web URL: http://www.ciena.com/
     Postal:  7035 Ridge Road
              Hanover, Maryland 21076
              U.S.A.
     Phone:   +1 800-921-1144
     Fax:     +1 410-694-5750";
  description
    "This module defines the configuration and operational data for the Simple
     Network Management Protocol (SNMP) server on Ciena's Waveserver platform.";

  revision 2019-02-19 {
    description
      "Added lists: 'snmp/user','snmp/viewtree','snmp/security-to-group',
                    'snmp/access','snmp/notify', and related typedefs.";
    reference "Waveserver Ai R1.4 user's guide.";
  }

  revision 2018-09-19 {
    description
      "Waveserver Platform Data Model
       The initial definition of the SNMP external data model.";
    reference "Waveserver Ai R1.3 user's guide.";
  }

  typedef priv-protocol {
    type enumeration {
      enum noPriv {
        value 1;
        description
          "Uses Uses no privacy protocol.";
      }
      enum des {
        value 2;
        description
          "Uses privacy protocol des.";
      }
      enum 3des {
        value 3;
        description
          "Uses privacy protocol 3des.";
      }
      enum aes-128 {
        value 4;
        description
          "Uses privacy protocol aes-128.";
      }
    }
    description
      "Defines the supported SNMP privacy protocols.";
    reference
      "RFC 3414: User-based Security Model (USM) for version 3 of the Simple
       Network Management Protocol (SNMPv3).";
  }

  typedef auth-protocol {
    type enumeration {
      enum noAuth {
        value 1;
        description
          "Uses no authentication protocol.";
      }
      enum md5 {
        value 2;
        description
          "Uses authentication protocol md5.";
      }
      enum sha {
        value 3;
        description
          "Uses authentication protocol sha.";
      }
    }
    description
      "Defines the supported SNMP authentication protocols.";
    reference
      "RFC 3414: User-based Security Model (USM) for version 3 of the Simple
       Network Management Protocol (SNMPv3).";
  }

  typedef security-model {
    type enumeration {
      enum v1  {
        value 1;
        description
          "Uses SNMPv1 community-based security model.";
      }
      enum v2c {
        value 2;
        description
          "Uses SNMPv2c community-based security model.";
      }
      enum usm {
        value 3;
        description
          "Uses SNMPv3 User-based Security Model (USM).";
      }
    }
    description
      "Defines the supported SNMP security model types.";
    reference
      "RFC 3411: An Architecture for Describing Simple Network Management
       Protocol (SNMP) Management Frameworks.";
  }

  typedef security-level {
    type enumeration {
      enum no-auth-no-priv {
        value 1;
        description
          "No authentication and no encrpytion.";
      }
      enum auth-no-priv {
        value 2;
        description
          "Messages are authenticated but not encrypted (i.e., no privacy).";
      }
      enum auth-priv {
        value 3;
        description
          "Messages are authenticated and encrypted (i.e., with privacy).";
      }
    }
    description
      "SNMP security level.";
    reference
      "RFC 3411: An Architecture for Describing Simple Network
       Management Protocol (SNMP) Management Frameworks";
  }

  typedef mp-model {
    type uint32;
    description
      "The Message Processing Model type identifies the format of a particular
       version of an SNMP message. Values between 0 and 255 are managed by IANA
       with the following reserved values:
         0     - Reserved for SNMPv1
         1     - Reserved for SNMPv2c
         2     - Reserved for SNMPv2u and SNMPv2
         3     - Reserved for SNMPv3
         4-255 - Unassigned";
    reference
      "RFC 3411: An Architecture for Describing Simple Network Management
       Protocol (SNMP) Management Frameworks.";
  }

  typedef snmp-name-string {
    type string {
      length "1..32";
    }
    description
      "A string that uniquely identifies an SNMP object instance in a list,
       including target, target-params, and community object types.";
    reference
      "RFC 3413: Simple Network Management Protocol (SNMP) Applications.";
  }

  typedef tag-value {
    type string {
      length "0..32";
    }
    description
      "Represents SnmpTagValue as defined in RFC 3413. A zero length string
       indicates an empty list.";
    reference
      "RFC 3413: Simple Network Management Protocol (SNMP) Applications.
       SNMP-TARGET-MIB.SnmpTagValue";
  }

  container waveserver-snmp {
    ui:ui-name "SNMP";
    description
      "Waveserver SNMP configuration and operational data.";

    container global-config {
      ui:ui-name "Global Config";
      description
        "Global configuration attributes for the SNMP engine.";

      leaf admin-state {
        ui:ui-name "Admin State";
        type cienawstypes:enabled-disabled-enum;
        description
          "SNMP engine administrative state.";
      }
      leaf operational-state {
        ui:ui-name "Operational State";
        type cienawstypes:up-down-enum;
        config false;
        description
          "SNMP engine operational state.";
      }
      leaf standard-link-traps-admin-state {
        ui:ui-name "Standard Link Traps";
        type cienawstypes:enabled-disabled-enum;
        description
          "Specifies whether standard link up/down trap notifications are
           enabled or disabled.";
      }
      leaf contact {
        ui:ui-name "Contact";
        type string {
          length "0..255";
        }
        description
          "SNMP system contact string.";
      }
      leaf location {
        ui:ui-name "Location";
        type string {
          length "0..255";
        }
        description
          "SNMP system location string.";
      }
      leaf engine-id {
        ui:ui-name "Engine ID";
        type string {
          pattern '([0-9a-fA-F]){2}(:([0-9a-fA-F]){2}){4,31}';
        }
        config false;
        description
          "The local SNMP engine's system-assigned unique identifier, expressed
           as a series of colon-separated hexadecimal octets.";
        reference
          "RFC 3411: An Architecture for Describing Simple Network Management
           Protocol (SNMP) Management Frameworks";
      }
      leaf engine-boots {
        ui:ui-name "Engine Boots";
        type uint32;
        config false;
        description
          "The number of times that the SNMP engine has (re-)initialized itself
           since the engine-id was last configured, or assigned at system boot.";
        reference
          "RFC 3411: An Architecture for Describing Simple Network Management
           Protocol (SNMP) Management Frameworks";
      }
      leaf engine-time {
        ui:ui-name "Engine Time";
        type uint32;
        units "seconds";
        config false;
        description
          "The number of seconds since the engine-boots counter was last
           incremented (i.e. since the SNMP engine was last booted).";
        reference
          "RFC 3411: An Architecture for Describing Simple Network Management
           Protocol (SNMP) Management Frameworks";
      }
      leaf engine-max-message-size {
        ui:ui-name "Max Message Size";
        type uint32;
        config false;
        description
          "The maximum length in octets of an SNMP message which this SNMP
           engine can send or receive and process, determined as the minimum
           of the maximum message size value supported among all of the
           transports available to and supported by the engine.";
        reference
          "RFC 3411: An Architecture for Describing Simple Network Management
           Protocol (SNMP) Management Frameworks";
      }
    }//end global-config

    container statistics {
      ui:ui-name "Statistics";
      config false;
      description
        "Statistics associated with the SNMP engine, including a collection
         of counters associated with the SNMP User-based Security Model (USM).";
      reference
        "RFC 2574: User-based Security Model (USM) for version 3 of the Simple
         Network Management Protocol (SNMPv3)";

      leaf unknown-security-models {
        ui:ui-name "Unknown Security Models";
        type uint32;
        description
          "The total number of packets received by the SNMP engine which were
           dropped because the packets referenced a security model that the
           SNMP agent does not support or recognize.";
      }
      leaf invalid-messages {
        ui:ui-name "Invalid Messages";
        type uint32;
        description
          "The total number of packets received by the SNMP engine which were
           dropped because the packets contained invalid or inconsistent
           components.";
      }
      leaf unknown-pdu-handlers {
        ui:ui-name "Unknown PDU Handlers";
        type uint32;
        description
          "The total number of packets received by the SNMP engine which were
           dropped because the agent had no handler registered for the
           Protocol Data Unit (PDU) type of the packet.";
      }
      leaf unsupported-security-levels {
        ui:ui-name "Unsupported Security Levels";
        type uint32;
        description
          "The total number of packets received by the SNMP engine which were
           dropped because they requested a security level that was unknown
           to the SNMP engine or otherwise unavailable.";
      }
      leaf not-in-time-windows {
        ui:ui-name "Not In Time Windows";
        type uint32;
        description
          "The total number of packets received by the SNMP engine which were
           dropped because they appeared outside of the authoritative SNMP
           engine's window.";
      }
      leaf unknown-user-names {
        ui:ui-name "Unknown User Names";
        type uint32;
        description
          "The total number of packets received by the SNMP engine which were
           dropped because they referenced a user that was not known to the
           SNMP engine.";
      }
      leaf unknown-engine-ids {
        ui:ui-name "Unknown Engine IDs";
        type uint32;
        description
          "The total number of packets received by the SNMP engine which were
           dropped because they referenced an engine-id that was not known to
           the SNMP engine.";
      }
    }//end statistics

    list target {
      ui:ui-name "Target";
      key name;
      //ncx:user-write "create delete";
      description
        "List of target transport addresses (e.g. trap destinations) to be used
         in the generation of SNMP messages.";
      reference
        "RFC 3413: Simple Network Management Protocol (SNMP) Applications.";

      leaf name {
        ui:ui-name "Target Name";
        type snmp-name-string;
        description
          "SNMP trap target name. Uniquely identifies the target entry in the
           list.";
      }
      leaf address {
        ui:ui-name "Target Address";
        type cienawstypes:ipaddr-or-hostname;
        mandatory true;
        description
          "The SNMP target transport address, as an IPv4 address with optional
           prefix length, or hostname format.";
      }
      leaf target-params {
        ui:ui-name "Target Params";
        type snmp-name-string;
        mandatory true;
        description
          "Identifies an entry in the target-params list. The identified entry
           contains SNMP parameters to be used when generating messages to be
           sent to this target transport address. If the selected entry in the
           target-params list does not exist, the management target will not be
           used to generate notifications.";
      }
      leaf tag {
        ui:ui-name "Target Tag";
        type tag-value;
        description
          "Tag value used to select one or more target address entries for a
           particular operation.";
      }
      leaf port {
        ui:ui-name "Target Port";
        type uint16;
        description
          "UDP port number associated with the target entry. Default is 162.";
      }
      leaf transport-domain {
        ui:ui-name "Target Transport Domain";
        type enumeration {
          enum snmp-udp {
            description
              "SNMP over UDP. This is the default domain value.";
          }
          enum v4-udp {
            description
              "SNMP over UDP over Ipv4.";
          }
          enum v6-udp {
            description
              "SNMP over UDP over Ipv6.";
          }
        }
        description
          "Indicates the transport type of the address contained in this SNMP
           target entry. Default is 'snmp-udp'.";
         reference
           "RFC 3417: Transport Mappings for the Simple Network Management
            Protocol (SNMP).";
      }
      leaf timeout {
        ui:ui-name "Target Timeout";
        type uint32;
        units "0.01 seconds";
        description
          "The expected maximum round trip time for communicating with this
           target transport address, expressed in hundredths of a second.";
      }
      leaf retry-count {
        ui:ui-name "Target Retry Count";
        type uint32;
        description
          "The default number of retries to be attempted when a response is not
           received for a generate message to this target transport address.";
      }
    }//end target

    list target-params {
      ui:ui-name "Target Params";
      //ncx:user-write "create delete";
      key name;
      description
        "List of objects containing one ore more SNMP parameters which can be
         associated with an SNMP transport target.";
      reference
        "RFC 3413: Simple Network Management Protocol (SNMP) Applications.";

      leaf name {
        ui:ui-name "Target Params Name";
        type snmp-name-string;
        description
          "An arbitrary name which uniquely identifies this target-params entry
           in the list.";
      }
      leaf security-name {
        ui:ui-name "Security Name";
        type snmp-name-string;
        mandatory true;
        description
          "SNMP security name, represented as a string.";
      }
      leaf security-model {
        ui:ui-name "Security Model";
        type security-model;
        description
          "The security model associated with this target-params entry. Default
          is v1.";
      }
      leaf security-level {
        ui:ui-name "Security Level";
        type security-level;
        description
          "The security level associated with this target-params entry. Default
           is no-auth-no-priv.";
      }
      leaf message-processing-model {
        ui:ui-name "MP Model";
        type mp-model;
        config false;
        description
          "The Message Processing Model associated with this target-params entry.
           Derived from the security-model.";
      }
    }//end target-params

    list community {
      ui:ui-name "Community";
      //ncx:user-write "create delete";
      key index;
      description
        "List of community entries for SNMP v1 and v2c security.";

      leaf index {
        ui:ui-name "Index";
        type snmp-name-string;
        description
          "Index into the community list.";
      }
      leaf community-name {
        ui:ui-name "Community Name";
        type string {
          length "1..64";
        }
        mandatory true;
        description
          "SNMP community name, represented as a string.";
      }
      leaf security-name {
        ui:ui-name "Security Name";
        type snmp-name-string;
        mandatory true;
        description
          "SNMP security name, represented as a string.";
      }
      leaf transport-tag {
        ui:ui-name "Transport Tag";
        type tag-value;
        description
          "Used to limit access for this community to the specified target(s).";
      }
      leaf context-name {
        ui:ui-name "Context Name";
        type string {
          length "0..32";
        }
        description
          "The context in which management information is accessed when using
           the community string specified by this entry.";
      }
    }//end community

    list user {
      ui:ui-name "User";
      key "name engine-id";
      description
        "List of SNMPv3 user profiles. A double-keyed list that consists of a
         user name and an Engine Id value. The combination of user name and
         Engine Id make up SNMP MIB user profile.";
      reference
        "RFC 3414: User-based Security Model (USM) for version 3 of the Simple
         Network Management Protocol (SNMPv3).";

      leaf name {
        ui:ui-name "User Name";
        type snmp-name-string;
        description
          "SNMP user name. Uniquely identifies the user entry in the
           list.";
      }
      leaf engine-id {
        ui:ui-name "User Engine Id";
        type string {
          pattern '([0-9a-fA-F]){2}(:([0-9a-fA-F]){2}){4,31}';
        }
        description
          "The SNMP user engine id, unique identifier, expressed
           as a series of colon-separated hexadecimal octets.";
        reference
          "RFC 3411: An Architecture for Describing Simple Network Management
           Protocol (SNMP) Management Frameworks";
      }
      leaf auth-protocol {
        ui:ui-name "User Auth Protocol";
        type auth-protocol;
        mandatory true;
        description
          "The SNMP user authentication protocol.";
        reference
          "RFC 3414: User-based Security Model (USM) for version 3 of the Simple
           Network Management Protocol (SNMPv3).";
      }
      leaf auth-password {
        ui:ui-name "User Auth Password";
        type cienawstypes:string-maxl-128;
        description
          "The user authentication protocol password, supplied as cleartext.
           This is a write-only attribute that should not be stored nor returned
           on user retrieval. The password will be encrypted via one-way hash
           function and stored only in its encrypted format.";
        ncx:password;
      }
      leaf auth-secret {
        ui:ui-name "Password Auth Secret";
        type cienawstypes:string-maxl-256;
        description
          "The encrypted user authentication protocol password string, supplied
           as a hashed value. This should only be configured at user creation
           time, and will be ignored if the user account already exists.";
      }
      leaf priv-protocol {
        ui:ui-name "User Priv Protocol";
        type priv-protocol;
        description
          "The SNMP user privacy protocol.";
        reference
          "RFC 3414: User-based Security Model (USM) for version 3 of the Simple
           Network Management Protocol (SNMPv3).";
      }
      leaf priv-password {
        ui:ui-name "User Priv Password";
        type cienawstypes:string-maxl-128;
        description
          "The user privacy protocol password, supplied as cleartext. This is a
           write-only attribute that should not be stored nor returned on user
           retrieval. The password will be encrypted via one-way hash function
           and stored only in its encrypted format.";
        ncx:password;
      }
      leaf priv-secret {
        ui:ui-name "Password Priv Secret";
        type cienawstypes:string-maxl-256;
        description
          "The encrypted user privacy protocol password string, supplied as a
           hashed value. This should only be configured at user creation time,
           and will be ignored if the user account already exists.";
      }
    }//end user

    list viewtree {
      ui:ui-name "Viewtree";
      //ncx:user-write "create delete";
      key "name sub-tree";
      description
        "List of view tree definitions. A double-keyed list that consists of a
         view tree name and sub-tree OID string value. The combination of
         sub-tree entries with the same viewtree name make up an SNMP MIB
         Viewtree or View Tree Family.";
      reference
        "RFC 3415: View-based Access Control Model (VACM) for the Simple Network
         Management Protocol (SNMP).";

      leaf name {
        ui:ui-name "Viewtree Name";
        type snmp-name-string;
        description
          "SNMP viewtree name. Identifies the viewtree entries in the list that
           belong to the same viewtree family.";
      }
      leaf sub-tree {
        ui:ui-name "Sub-tree Definition";
        type snmp-name-string;
        description
          "SNMP Sub-tree definition, OID format, Ex:1.3.6.1.4.1.1271.35,
           and predefined system defaults snmpResearch and iso.";
      }
      leaf type {
        ui:ui-name "Sub-tree Type";
        type enumeration {
          enum "include" {
            description
              "Sub-tree include type.";
          }
          enum "exclude" {
            description
              "Sub-tree exclude type.";
          }
        }
        mandatory true;
        description
          "The SNMP Sub-tree type.";
      }
      leaf mask {
        ui:ui-name "Sub-tree Mask";
        type string {
          pattern '([0-9a-fA-F]){2}(:([0-9a-fA-F]){2}){1,32}';
        }
        description
          "Sub-tree mask or family mask, a colon-separated octet string.";
      }
    }//end viewtree

    list security-to-group {
      ui:ui-name "Security To Group";
      //ncx:user-write "create delete";
      key "user sec-model";
      description
        "List of security-to-group entries. A double-keyed list of entries
         identified by security criteria (name and model) which can be assigned
         to an access group name. Security groups can be created to identify
         sets of users with similar read/write access control permissions or
         notification view filtering.";
      reference
        "RFC 3415: View-based Access Control Model (VACM) for the Simple Network
         Management Protocol (SNMP).";

      leaf user {
        ui:ui-name "User Name";
        type snmp-name-string;
        description
          "User name string (SNMPv3) or community string (SNMPv1, SNMPv2)
           associated with the security group.";
      }
      leaf sec-model {
        ui:ui-name "Security Model";
        type security-model;
        description
          "The security model associated with this security-to-group entry.";
      }
      leaf group {
        ui:ui-name "Group Name";
        type snmp-name-string;
        mandatory true;
        description
          "A user-assigned access entry group name identifying a group of users
           with similar access control permissions, notification view, etc.
           This group name is used as an index into the access list to select
           an access control policy, however it does not imply or guarantee that
           an instance with this name actually exists in the access table.";
      }
    }//end security-to-group

    list access {
      ui:ui-name "Access Entry";
      //ncx:user-write "create delete";
      key "entry sec-model sec-level";
      description
        "List of access entry profiles, defining access privileges and MIB
         read/write and notification view filters for a particular user class
         group of users.";
      reference
        "RFC 3415: View-based Access Control Model (VACM) for the Simple Network
         Management Protocol (SNMP).";

      leaf entry {
        ui:ui-name "Entry Name";
        type snmp-name-string;
        description
          "Entry name. Uniquely identifies the access entry/group in the list.";
      }
      leaf sec-model {
        ui:ui-name "Security Model";
        type security-model;
        mandatory true;
        description
          "The security model associated with this access entry.";
      }
      leaf sec-level {
        ui:ui-name "Security Level";
        type security-level;
        mandatory true;
        description
          "The security level associated with this access entry.";
      }
      leaf read-view {
        ui:ui-name "Read View";
        type string {
          length "0..33";
        }
        mandatory true;
        description
          "Read view type. Each access entry profile must have a read view
           assigned to it.";
      }
      leaf write-view {
        ui:ui-name "Write View";
        type string {
          length "0..33";
        }
        description
          "Write view type, optional.";
      }
      leaf notify-view {
        ui:ui-name "Notify View";
        type string {
          length "0..33";
        }
        description
          "Notify view type, optional.";
      }
    }//end access

    list notify {
      ui:ui-name "Notify";
      key name;
      description
        "List of notification target entries. Used to select management targets
         which should receive notifications, as well as the type of notification
         which should be sent to each selected management target.";
      reference
        "RFC 3413: Simple Network Management Protocol (SNMP) Applications.";

      leaf name {
        type snmp-name-string;
        description
          "Notify name. Uniquely identifies the notify entry in the list.";
      }
      leaf notify-tag {
        type snmp-name-string;
        mandatory true;
        description
          "Notify tag name. Contains a single tag value which is used to select
           entries in the target list (target address table). Any entry in the
           target list which contains this tag value will be selected for this
           notify target. If the tag value is an empty string, then no entries
           will be selected.";
      }
      leaf notify-type {
        type enumeration {
          enum "trap" {
          value 1;
            description
              "Create trap notification. Notification messages generated will
               contain Unconfirmed-Class PDUs. This is the default value.";
          }
          enum "inform" {
          value 2;
            description
              "Create inform notification. Notification messages generated will
               contain Confirmed-Class PDUs.";
          }
        }
        description
          "The type of notification to be generated for entries in the target
           list selected by the notify-tag value. Default is trap.";
      }
    }//end notify
  }//end waveserver-snmp

  augment "/port:waveserver-ports/port:ports/port:properties" {
    description
      "SNMP related port properties.";
    ddf:ddf-struct-version "SnmpPortProps";
    leaf snmp-standard-link-traps {
      ui:ui-name "Trap State";
      type cienawstypes:enabled-disabled-enum;
      description
        "Indicates whether standard SNMP traps are enabled or disabled on the
         port object. Applies to all line and client port types.";
      reference
        "RFC 3413: Simple Network Management Protocol (SNMP) Applications.";
    }
  }//end augment to ports/properties

}
