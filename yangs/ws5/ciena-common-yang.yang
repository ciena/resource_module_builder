module ciena-common-yang {
  namespace "urn:ciena:params:xml:ns:yang:ciena-common-yang";
  prefix yang;

  organization "Ciena";
  contact
    "";
  description
    "holds definitions that are commonly used across the system.";

  revision 2015-04-07 {
    description
      "";
    reference
      "";
  }

  extension handler {
    argument value;
    description
      "Handler for this YANG data type";
  }

  extension alias {
    argument value;
    description
      "Alias for generated bindings for a container, list element, or
       augment.";
  }

  extension mount-depth {
    argument value;
    description
      "Maximum depth a module can include itself to in this mount";
  }

  extension mount {
    argument module;
    description
      "Mount the specified module under this anyxml node.";
  }

  extension create-supported {
    argument value;
    description
      "Denotes whether a node may be created.";
  }

  extension edit-supported {
    argument value;
    description
      "Denotes whether a node may be modified/edited.";
  }

  extension get-supported {
    argument value;
    description
      "Denotes whether a node may be retrieved.";
  }

  extension delete-supported {
    argument value;
    description
      "Denotes whether a node may be deleted.";
  }

  typedef yang-action {
    type enumeration {
      enum create;
      enum edit;
      enum update;
      enum replace;
      enum delete;
    }
  }

  typedef yang-phase {
    type enumeration {
      enum commit;
    }
    description "Optional flag that specifies if the data should persist." ;
  }

  typedef yang-status {
    type enumeration {
      enum failed;
      enum ok;
    }
    description "Summary yang action status." ;
  }

  typedef service {
    type string { length "1..32" ; }
    description "Specifies the name of the Service being requested. Allows the
                 routing of messages and requests to the appropriate
                 destination." ;
  }

  grouping yang-set-obj-input {
      leaf path {
        type string;
        description "path of object the set is to be applied to";
      }
      leaf action {
        type yang-action;
      }
      leaf phase {
        type yang-phase;
        description "Phase of the edit operation.";
      }
      anyxml config{
        mandatory true;
        description "Anyxml data for set-object operation.";
      }
  }

  identity error-code {
    description
      "The base identity to represent error codes";
  }

  identity error-unknown {
    base error-code;
    description
      "Error was generated for unknown reason.";
  }

  identity success {
    base error-code;
    description
      "Success.";
  }

  identity error-internal {
    base error-code;
    description
      "Error was generated by an internal failure.";
  }

  identity error-does-not-exist {
    base error-code;
    description
      "Error was generated because the instance does not exist.";
  }

  identity error-already-exist {
    base error-code;
    description
      "Error was generated because the instance already exists.";
  }

  identity error-already-locked {
    base error-code;
    description
      "Error was generated because the instance is already locked.";
  }

  identity state-name {
   description   "Base identity to represent FSM(Finite State Machine) state";
  }

  grouping rpc-result-common {
    description
      "Common RPC output data (return codes) that should be shared across all
       RPCs.";
    list return-code-list {
      yang:alias "yang-return-code-list";
      uses return-code;
    }
    leaf status {
      type yang-status;
    }
  }

  grouping return-code {
    leaf instance {
      type instance-identifier;
      mandatory false;
      description "The instance to which the return code applies.";
    }
    leaf error {
      type identityref {
        base error-code;
      }
    }
    leaf action {
      type yang-action;
      mandatory false;
      description "The action performed for which the return code applies.";
    }
    leaf error-str {
      type string;
      mandatory false;
      description
        "A string description of the return code.";
    }
  }

  rpc yang-del-object {
    input {
      leaf path {
        type string;
        description "path of object the delete is to be applied to";
      }
    }
    output {
      uses rpc-result-common;
    }
  }

  rpc yang-set-object {
    input {
      uses yang-set-obj-input;
    }
    output {
      uses rpc-result-common;
    }
  }

  rpc yang-stage-object {
    input {
      leaf path {
        type string;
        description "path of object to be staged";
      }
      leaf action {
        type yang-action;
        default edit;
      }
      anyxml in;
    }
    output {
      uses rpc-result-common;
      anyxml out;
    }
  }

  rpc yang-val-object {
    input {
      leaf path {
        type string;
        description "path of object to be validated";
      }
      leaf action {
        type yang-action;
        default edit;
      }
      anyxml config;
    }
    output {
      uses rpc-result-common;
    }
  }

  rpc yang-compare-objects {
    input {
      anyxml old;
      anyxml new;
      leaf path {
        type string;
        description "path of the object we are comparing";
      }
    }
    output {
      list actions {
        yang:alias yang-patch;
        key action;
        uses yang-set-obj-input;
      }
      uses rpc-result-common;
    }
  }

  rpc yang-get-object {
    input {
      leaf path {
        type string;
        description "path to get object from";
      }
      container options {
        leaf content {
          type enumeration {
            enum "config";
            enum "nonconfig";
            enum "all";
          }
          default "all";
          description "specify the type of content to return (config/non-config/all)";
        }
        leaf fields {
          type string { 
            length 20000;
          }
          description "restconf style fields filter";
        }
      }
    }
    output {
      uses rpc-result-common;
      anyxml data;
    }
  }

  rpc yang-request-object {
    input {
      leaf path {
        type string;
        description "path to request object from";
      }
      leaf subscriber {
        type string;
        description "name of the subscriber.  This is used in the "+
                    "notification to route the data to the correct destination";
      }
      container options {
        yang:alias yang-request-object-options;
        leaf config {
          type boolean;
          default false;
          description "set to true if only config data to be returned.";
        }
        leaf get-initial {
          type boolean;
          description "set to true if the request should report the data initially.";
        }
        leaf get-on-change {
          type boolean;
          description "set to true if changes to the data should be reported.";
        }
        leaf frequency {
          type uint32;
          units "ms";
          description "frequency of subscription";
        }
        leaf fields {
          type string { 
            length 20000;
          }
          description "restconf style fields filter";
        }
      }
    }
    output {
      uses rpc-result-common;
      leaf request-id {
        type uint64;
        description "number used to reference the request in the future";
      }
    }
  }

  rpc yang-unsubscribe {
    input {
      leaf subscriber {
        type string;
        description "name of the subscriber.  This was supplied in the "+
                    "request";
      }
      leaf request-id {
        type uint64;
        description "number used to reference the request";
      }
    }
    output {
      uses rpc-result-common;
    }
  }

  rpc yang-rpc-action {
    input {
      leaf tag {
        type uint64;
        description "tag to return in a response";
      }
      leaf action {
        type string;
        description "action to perform";
      }
      leaf path {
        type string;
        description "rpc or path to execute action on";
      }
      leaf msg-trace {
        type string;
        description "Message tracing tag list";
      }
      anyxml data;
    }
    output {
      uses rpc-result-common;
      leaf tag {
        type uint64;
        description "tag provided in the request";
      }
      leaf path {
        type string;
        description "rpc or path to execute action on";
      }
      anyxml data;
    }
  }

  notification yang-delivery {
    leaf timestamp {
      type uint64;
    }
    leaf path {
      type instance-identifier;
      description "path of object the delivery applies to";
    }
    leaf subscriber {
      type string;
      description "name of the subscriber.  This was supplied in the "+
                  "request";
    }
    leaf request-id {
      type uint64;
      description "number used to reference the request";
    }
    leaf action {
      type yang-action;
    }
    anyxml data;
  }
}
