module ciena-ddm-zmq {
  namespace "urn:ciena:params:xml:ns:yang:ciena-ddm-zmq";
  prefix ddm-zmq;

  import ciena-ddy-msg {
    prefix ciena-ddy-msg;
  }

  organization "Ciena";
  contact
    "";
  description
    "";

  revision 2015-04-07 {
    description
      "";
  }

  identity zmq {
    base ciena-ddy-msg:ddm-protocols;
    description
      "Zero-MQ Client/Server";
  }

  augment "/ciena-ddy-msg:domains/ciena-ddy-msg:protocols" {
    when "ciena-ddy-msg:type = 'ciena-ddy-msg:zmq'";
    container zmq-options 
    {
      leaf ipport {
        type string;
        description "IP and Port in the URL of the destination.";
      }
      leaf pubipport {
        type string;
        description "IP and Port of the publisher to connect to";
      }
      leaf format {
        type identityref {
          base ciena-ddy-msg:ddm-format;
        }
        description "Serialization format for the data.";
      }
    }
  }
}
