module ciena-pon-ctrl-deviation {
  namespace "http://www.ciena.com/ns/yang/ciena-pon-ctrl-dev";
  prefix "pon-ctrl-dev";

  import ciena-pon-ctrl {
    prefix pon-ctrl;
  }

  import ciena-types {
    prefix ciena;
  }

  import ietf-yang-types {
    prefix yang;
  }

  revision "2023-10-11" {
    description
      "Add deviations for rogue ONU configurations.";
  }

  revision "2022-03-10" {
    description
      "Initial revision.";
  }

  deviation /pon-ctrl:pon-ctrl/pon-ctrl:global/pon-ctrl:rogue-onu-action-repeat-threshold {
    deviate not-supported;
  }

  deviation /pon-ctrl:pon-ctrl/pon-ctrl:global/pon-ctrl:rogue-onu-isolate-enable {
    deviate not-supported;
  }

  deviation /pon-ctrl:pon-ctrl/pon-ctrl:global/pon-ctrl:rogue-onu-action-reset-olt {
    deviate not-supported;
  }

  deviation /pon-ctrl:pon-ctrl/pon-ctrl:global/pon-ctrl:rogue-onu-mass-onu-deregistration-event {
    deviate not-supported;
  }

  deviation /pon-ctrl:pon-ctrl/pon-ctrl:global/pon-ctrl:rogue-onu-action-reset-onu {
    deviate not-supported;
  }

  deviation /pon-ctrl:pon-ctrl/pon-ctrl:global/pon-ctrl:rogue-onu-negative-rx-threshold {
    deviate not-supported;
  }

  deviation /pon-ctrl:pon-ctrl/pon-ctrl:global/pon-ctrl:rogue-onu-action-sample-size {
    deviate not-supported;
  }

  deviation /pon-ctrl:pon-ctrl/pon-ctrl:global/pon-ctrl:rogue-onu-olt-action-disable-all-serial-numbers {
    deviate not-supported;
  }

  deviation /pon-ctrl:pon-ctrl/pon-ctrl:global/pon-ctrl:onu-serial-number-config-change-enable {
    deviate not-supported;
  }

  deviation /pon-ctrl:pon-ctrl/pon-ctrl:global/pon-ctrl:rogue-onu-bip-error-threshold {
    deviate not-supported;
  }

  deviation /pon-ctrl:pon-ctrl/pon-ctrl:global/pon-ctrl:rogue-onu-olt-action-disable-serial-number {
    deviate not-supported;
  }

  deviation /pon-ctrl:pon-ctrl/pon-ctrl:global/pon-ctrl:rogue-onu-crc32-error-threshold {
    deviate not-supported;
  }

  deviation /pon-ctrl:pon-ctrl/pon-ctrl:global/pon-ctrl:rogue-onu-olt-action-reset-all-onus {
    deviate not-supported;
  }

  deviation /pon-ctrl:pon-ctrl/pon-ctrl:global/pon-ctrl:rogue-onu-olt-action-reset-olt {
    deviate not-supported;
  }

  deviation /pon-ctrl:pon-ctrl/pon-ctrl:global/pon-ctrl:rogue-onu-action-disable-serial-number {
    deviate not-supported;
  }

  deviation /pon-ctrl:pon-ctrl/pon-ctrl:global/pon-ctrl:rogue-onu-enable {
    deviate not-supported;
  }

  deviation /pon-ctrl:pon-ctrl/pon-ctrl:global/pon-ctrl:rogue-onu-positive-rx-threshold {
    deviate not-supported;
  }

  deviation /pon-ctrl:pon-ctrl/pon-ctrl:global/pon-ctrl:rogue-onu-action-history-size {
    deviate not-supported;
  }

  deviation /pon-ctrl:pon-ctrl/pon-ctrl:global/pon-ctrl:rogue-onu-fast-recovery-enable {
    deviate not-supported;
  }

  deviation /pon-ctrl:pon-ctrl/pon-ctrl:global/pon-ctrl:rogue-onu-action-min-idle-receive-power-threshold {
    deviate not-supported;
  }

  deviation /pon-ctrl:pon-ctrl/pon-ctrl:global/pon-ctrl:rogue-onu-hec-error-threshold {
    deviate not-supported;
  }

  deviation /pon-ctrl:pon-ctrl/pon-ctrl:global/pon-ctrl:rogue-onu-remediate-enable {
    deviate not-supported;
  }

}
