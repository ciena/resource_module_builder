module ciena-openconfig-system {
  namespace "http://www.ciena.com/ns/yang/ciena-openconfig-system";
  prefix "ciena-oc-sys";

  import openconfig-system { prefix oc-sys; }
  import yuma-ncx { prefix ncx; }
  import ietf-yang-types { prefix yang; }
  import ciena-ssh-types { prefix sshtypes; }
  import ciena-file-transfer-types { prefix ciena-ftt; }
  import ciena-types { prefix cn-type; }

  organization
    "Ciena Corporation";
  
  contact
    "Web URL: http://www.ciena.com/
     E-mail:  yang@ciena.com
     Postal:  7035 Ridge Road
              Hanover, Maryland 21076
              U.S.A.
     Phone:   +1 800-921-1144
     Fax:     +1 410-694-5750";
      
  description
    "This YANG module defines Ciena's augmentations to openconfig-system.

      Copyright (c) 2018 Ciena Corporation.  All rights 
      reserved.

      All information contained herein is, and remains
      the property of Ciena Corporation. Dissemination of this 
      information or reproduction of this material is strictly 
      forbidden unless prior written permission is obtained from 
      Ciena Corporation.";

  revision 2023-09-13 {
    description
      "Added length restriction for local user's password.
       Added support to install Public Key via CLI string.
       Added support for host key algorithms in ssh-server configuration.";
    reference
      "No specific reference or standard available.";
  }

  revision 2022-12-06 {
    description
      "Added supported objects for local account password expiration.
       Added password expiry warning and period as part of the user state.
       Added password expiry status as part of the user state.";
    reference
      "No specific reference or standard available.";
  }

  revision 2021-07-30 {
    description
      "Added leaf data node to display MD5 and SHA1 fingerprint of
      installed SSH User Public Keys";
    reference
      "No specific reference or standard available.";
  }

  revision 2020-10-29 {
    description
      "User generated keys are not part of SSH server configurations,
       hence moving their state out of SSH server state hierarchy";
    reference
      "No specific reference or standard available.";
  }

  revision 2020-09-29 {
    description
      "Added supported objects for SSH server configurations";
    reference
      "RFC 4253: The Secure Shell (SSH) Transport Layer Protocol.";
  }
  
  revision 2018-01-29 {
    description 
      "Initial version";
    reference
      "RFC 6020: YANG - A Data Modeling Language for
       the Network Configuration Protocol (NETCONF).
       No specific reference; standard not available.";
  }

  grouping password-expiry {
    leaf password-expiry-period {
      type int32 {
        range "0 | 14..365";
      }
      units "days";
      default 0;
      description
        "This attribute represents the maximum number of days that can
         elapse before a password must be changed. This is the password expiration period.
         Default value is 0, meaning password will not expire.";
    }
    leaf password-expiry-warning {
      type int32 {
        range "0..90";
      }
      units "days";
      default 0;
      description
        "This attribute represents the number of days prior to password expiration that a
         warning about password expiration is displayed upon successful login.
         Default value is 0, meaning no expiry warning will be displayed.";
    }
  }
  augment "/oc-sys:system/oc-sys:aaa/oc-sys:authentication/oc-sys:users/oc-sys:user/oc-sys:config" {
    leaf password {
      type string {
        length "1..128";
      }
      ncx:password;
      description
        "The user password in cleartext, only the hashed
        value will be stored";
    }
    uses password-expiry;
  }

  augment "/oc-sys:system/oc-sys:aaa/oc-sys:authentication/oc-sys:users/oc-sys:user/oc-sys:state" {
    leaf lockout-time {
      type uint16;
      description
        "Amount of time left before the lockout ends";
    }
    leaf last-failure {
       type yang:date-and-time;
       description
          "Last timestamp of user login failure";
    }
    uses password-expiry;
    leaf last-password-change {
       type cn-type:date;
       description
          "This attribute represents date of the last password change";
    }
    leaf password-expired {
       type boolean;
       description
          "Indicates the password expiry status for the user.
           Set to true if the password has expired.";
    }
  }

  augment "/oc-sys:system/oc-sys:ssh-server/oc-sys:config" {
     description
        "Augmenting SSH server attributes to SSH server config";

     leaf public-key-authentication {
        type cn-type:admin-state;
        default "enabled";
        description 
           "Admin state of public key authentication on SSH server";
     }

     leaf-list encryption-algorithm {
        type identityref {
          base sshtypes:encryption-algo;
        }
       description
         "Encryption algorithm configuration on  SSH server";
     }

     leaf-list kex-algorithm {
        type identityref {
          base sshtypes:kex-algo; 
        }
       description
         "Key exchange algorithm configuration on  SSH server";
     }

     leaf-list mac-algorithm {
        type identityref {
          base sshtypes:mac-algo; 
        }
       description
         "Mac algorithm configuration on  SSH server";
     }

     leaf-list pka-algorithm {
        type identityref {
          base sshtypes:pka-algo; 
        }
       description
         "Public key algorithm configuration on SSH server";
     }

     leaf-list host-key-algorithm {
        type identityref {
          base sshtypes:pka-algo;
        }
       description
         "Host key algorithm configuration on SSH server";
     }

     leaf rekey-limit {
        type enumeration {
           enum 1G {
              description
                 "Rekey after transmitting 1G bytes.";
           }
           enum 500M {
              description
                 "Rekey after transmitting 500M bytes.";
           }
           enum default {
              description
                 "default value of rekey limit as per OpenSSH default configuration.";
           }
        }
        description
           "Max number of bytes that are transmitted before the 
           session key is renegotiated.";
     }

     leaf rekey-time {
        type uint32 {
           range "0..3600";
        }
        units seconds;
        description
           "Max time in seconds after which SSH key is renegotiated.
           0 represents default value of rekey-time as per OpenSSH default configuration.";
     }
  }

  augment "/oc-sys:system/oc-sys:state" {
     description
        "State of User generated keys either host key or client public key";

     container user-public-keys {
        description
           "SSH client public key information.";

        list user {
           key "user";
           description
              "User list.";
           leaf user {
              type string;
              description
                 "The user for which public key has been installed.";
           }
           leaf fingerprint-md5 {
              type string;
              description
                 "This leaf displays the MD5 fingerprint of user public key.";
           }
           leaf fingerprint-sha1 {
              type string;
              description
                 "This leaf displays the SHA1 fingerprint of user public key.";
           }
        }
     }
  }

  //RPCs
  rpc ssh-user-pubkey-install {
    description
      "Install SSH client's public key.";
    input {
      leaf user {
        type string;
        mandatory true;
        description
          "The user to which this public key belongs.";
      }

      uses ciena-ftt:file-transfer-parameters {
        augment file-transfer-syntax {
          case cli-string {
            leaf key-string {
               type string {
                 length "1..3000";
               }
               description
                 "String representing the public key.";
            }
          }
        }
      }
    }
    output {
      leaf status {
        type cn-type:status;
        description
          "Status indicating if the operation has succeeded or not.";
      }
    }
  }

  rpc ssh-user-pubkey-delete {
    description
      "delete user's public key";
    input {
      leaf user {
        type string;
        mandatory true;
        description
          "The user for which public key needs to be deleted.";
      }
    }
    output {
      leaf status {
        type cn-type:status;
        description
          "Status indicating if the operation has succeeded or not.";
      }
    }
  }
}
