module ciena-openconfig-platform-deviation {
   namespace "http://www.ciena.com/ns/yang/cn-oc-platform-dev";
   prefix "cn-oc-platform-dev";

   import openconfig-platform {
      prefix "oc-platform";
   }

   import ciena-types {
      prefix "ciena-types";
   }

   organization
      "Ciena Corporation";

   contact
      "Web URL: http://www.ciena.com/
      E-mail: yang@ciena.com
      Postal: 7035 Ridge Road
              Hanover, Maryland 21076
              U.S.A.
      Phone: +1 800-921-1144
      Fax:   +1 410-694-5750";

   description
      "This YANG module defines Ciena's deviations from the openconfig-platform model.

      Copyright (c) 2018 Ciena Corporation. All rights reserved.

      All information contained herein is, and remains
      the property of Ciena Corporation. Dissemination of this
      information or reproduction of this material is strictly
      forbidden unless prior written permission is obtained from
      Ciena Corporation.";

   revision 2023-07-18 {
      description
         "Added 1x200G-QSFPDD-MACSEC to fru-type typedef";
      reference
         "";
   }

   revision 2023-05-19 {
      description
         "Added 2x100G-QSFPDD-MACSEC to fru-type typedef";
      reference
         "";
   }

   revision 2022-09-15 {
      description
         "Added 12xsfp28 and 2xqsfpdd Macsec to fru-type typedef";
      reference
         "";
   }

   revision 2022-03-07 {
      description
         "Added server-module to fru-type typedef";
      reference
         "";
   }

   revision 2021-10-13 {
      description
         "Added 2x400GCFP2-DCO enumerations to fru-type typedef";
      reference
         "";
   }

   revision 2021-07-19 {
     description
       "Added filler-mismatch-alarm of the type state.
        Added 16x1G to fru-type typdef.";
     reference
       "";
   }

   revision 2021-07-13 {
      description
         "Added 2x10G-SFP+ to fru-type typedef";
      reference
         "";
   }

   revision 2020-09-25 {
      description
         "Added 8xQSFP28, 2xQSFPDD, and OC48-TDM  to fru-type typdef";
      reference
         "";
   }

   revision 2020-03-03 {
      description
         "Added 4x10G to fru-type typedef";
      reference
         "";
   }

   revision 2020-01-10 {
      description
         "Added 4xCFP2-DCO, CFP2-DCO, CFP2-QSFP28 and 2xCFP2-DCO enumerations to fru-type typedef";
      reference
         "";
   }

   revision 2019-08-19 {
      description
         "Added qsfp28 enum to fru-type typedef";
      reference
         "";
   }

   revision 2018-12-14 {
      description
         "Replace properties/property/config/value union.
          Added none enum to fru-type typedef.";
      reference
         "";
   }

   typedef fru-type {
      type enumeration {
         enum none {
            description
               "Fru Type not configured.";
            value 2;
         }
         enum 1xWLAi {
            description
               "1 WaveLogic Ai line port and 4 100G capable line ports.";
         }
         enum qsfp28 {
            description
               "Qsfp28 card with 2 100G capable ports";
         }
         enum 4xCFP2-DCO {
            description
               "CFP2-DCO card with 4 100/200G capable ports";
         }
         enum CFP2-QSFP28 {
            description
               "CFP2-QSFP28 card with 1 100G capable CFP2 port and 1 100G capable QSFP28 port";
         }
         enum CFP2-DCO {
            description
               "CFP2-DCO card with 1 100/200G capable port";
         }
         enum 2xCFP2-DCO {
            description
               "CFP2-DCO card with 2 100G capable ports";
         }
         enum 4x10G {
            description
               "PCIE NIC with 4 10G capable ports";
         }
         enum OC48-TDM {
            description
               "Combo CEM FRU module with 2 Ethernet, 4 Smart and 10 TDM capable ports";
         }
         enum 8xQSFP28 {
            description
            "QSFP28 card with 8 100G capable ports";
         }
         enum 2xQSFPDD {
            description
            "QSFPDD card with 2 400G capable ports";
         }
         enum 2x10G-SFP+ {
            description
               "PCIe NIC with 2 10G SFP+ capable ports";
         }
         enum 16x1G {
            description
               "GIGE FRU module with 16 1G capable ports";
         }
         enum 2x400G-CFP2-DCO {
            description
               "CFP2-DCO card with 2 400G capable ports";
         }
         enum server-module {
            description
               "Server-Module FRU";
         }
         enum 12xSFP28-MACSEC {
            description
               "macSec card with 12 25G capable ports";
         }
         enum 2xQSFPDD-MACSEC {
            description
               "macSec card with 2 400G capable ports";
         }
         enum 2x100G-QSFPDD-MACSEC {
            description
               "macSec card with 2 100G capable ports";
         }
         enum 1x200G-QSFPDD-MACSEC {
            description
               "macSec card with 1 200G capable port";
         }
      }
      description
         "The service module type.";
   }

   deviation /oc-platform:components/oc-platform:component/oc-platform:properties/oc-platform:property/oc-platform:config/oc-platform:value {
      deviate replace {
         type union {
            type int64;
            type uint64;
            type decimal64 {
               fraction-digits 2;
            }
            type fru-type;
            type ciena-types:admin-state;
            type ciena-types:filler-mismatch-alarm;
            type boolean;
            type string;
         }
      }
   }
}
