module ciena-software-mgmt-deviation {
  namespace "http://www.ciena.com/ns/yang/ciena-software-mgmt-dev";
  prefix "ciena-software-management-dev";

  import ciena-software-mgmt { prefix software-mgmt; }

  revision 2023-06-07 {
     description "Removed default value deviation from software-install rpc defer-activation attribute.";
  }

  revision 2021-08-23 {
     description "Added not-supported deviation for rolling-upgrade.";
  }

  revision 2020-12-22 {
     description "Removed the not-supported deviation from software-state/user-revert-timer.
                  Removed the not-supported deviation from software-activate/input/revert-timeout.
                  Replaced software-activate/input/revert-timeout uint32 type with uint32 range.
                  Removed the not-supported deviation from software-cancel.";
  }

  revision 2020-02-17 {
     description "Added default value false to software-install rpc defer-activation attribute.";
  }

  revision 2019-09-19 {
     description "Adding not-supported deviation for unsupported capabilities.
                  Adding not-supported deviation for software-state/running-package/standby-bootchain.";
  }

  revision 2019-04-05 {
     description "Initial revision.";
  }

  deviation /software-mgmt:software/software-mgmt:rolling-upgrade {
     deviate not-supported;
  }

  deviation /software-mgmt:software-state/software-mgmt:auto-revert-timer {
     deviate not-supported;
  }

  deviation /software-mgmt:software-state/software-mgmt:running-package/software-mgmt:package-status {
     deviate not-supported;
  }

  deviation /software-mgmt:software-state/software-mgmt:running-package/software-mgmt:release-status {
     deviate not-supported;
  }

  deviation /software-mgmt:software-state/software-mgmt:running-package/software-mgmt:active-bootchain/software-mgmt:status {
     deviate not-supported;
  }

  deviation /software-mgmt:software-state/software-mgmt:running-package/software-mgmt:standby-bootchain {
     deviate not-supported;
  }

  deviation /software-mgmt:software-state/software-mgmt:running-package/software-mgmt:release-package {
     deviate not-supported;
  }

  deviation /software-mgmt:software-state/software-mgmt:running-package/software-mgmt:kernel {
     deviate not-supported;
  }

  deviation /software-mgmt:software-state/software-mgmt:running-package/software-mgmt:uboot {
     deviate not-supported;
  }

  deviation /software-mgmt:software-state/software-mgmt:package/software-mgmt:active-bootchain {
     deviate not-supported;
  }

  deviation /software-mgmt:software-state/software-mgmt:package/software-mgmt:standby-bootchain {
     deviate not-supported;
  }

  deviation /software-mgmt:software-state/software-mgmt:package/software-mgmt:release-package {
     deviate not-supported;
  }

  deviation /software-mgmt:software-state/software-mgmt:package/software-mgmt:kernel {
     deviate not-supported;
  }

  deviation /software-mgmt:software-state/software-mgmt:package/software-mgmt:uboot {
     deviate not-supported;
  }

  deviation /software-mgmt:software-activate/software-mgmt:input/software-mgmt:allow-service-disruption {
     deviate not-supported;
  }

  deviation /software-mgmt:software-activate/software-mgmt:input/software-mgmt:force-standby {
     deviate not-supported;
  }

  deviation /software-mgmt:software-activate/software-mgmt:input/software-mgmt:revert-timeout {
     deviate replace {
         type uint32 {
             range "60..65535";
         }
     }
  }

  deviation /software-mgmt:software-download/software-mgmt:input/software-mgmt:file-transfer-syntax/software-mgmt:component/software-mgmt:filename {
     deviate not-supported;
  }

  deviation /software-mgmt:software-download/software-mgmt:input/software-mgmt:file-transfer-syntax/software-mgmt:component/software-mgmt:server-type {
     deviate not-supported;
  }

  deviation /software-mgmt:software-download/software-mgmt:input/software-mgmt:file-transfer-syntax/software-mgmt:component/software-mgmt:address {
     deviate not-supported;
  }

  deviation /software-mgmt:software-download/software-mgmt:input/software-mgmt:file-transfer-syntax/software-mgmt:component/software-mgmt:login-id {
     deviate not-supported;
  }

  deviation /software-mgmt:software-download/software-mgmt:input/software-mgmt:file-transfer-syntax/software-mgmt:component/software-mgmt:password {
     deviate not-supported;
  }

  deviation /software-mgmt:software-download/software-mgmt:input/software-mgmt:file-transfer-syntax/software-mgmt:component {
     deviate not-supported;
  }

  deviation /software-mgmt:software-download/software-mgmt:input/software-mgmt:destination-path {
     deviate not-supported;
  }

  deviation /software-mgmt:software-install/software-mgmt:input/software-mgmt:package-path {
     deviate not-supported;
  }

  deviation /software-mgmt:software-install/software-mgmt:input/software-mgmt:file-transfer-syntax/software-mgmt:component/software-mgmt:filename {
     deviate not-supported;
  }

  deviation /software-mgmt:software-install/software-mgmt:input/software-mgmt:file-transfer-syntax/software-mgmt:component/software-mgmt:server-type {
     deviate not-supported;
  }

  deviation /software-mgmt:software-install/software-mgmt:input/software-mgmt:file-transfer-syntax/software-mgmt:component/software-mgmt:address {
     deviate not-supported;
  }

  deviation /software-mgmt:software-install/software-mgmt:input/software-mgmt:file-transfer-syntax/software-mgmt:component/software-mgmt:login-id {
     deviate not-supported;
  }

  deviation /software-mgmt:software-install/software-mgmt:input/software-mgmt:file-transfer-syntax/software-mgmt:component/software-mgmt:password {
     deviate not-supported;
  }

  deviation /software-mgmt:software-install/software-mgmt:input/software-mgmt:file-transfer-syntax/software-mgmt:component {
     deviate not-supported;
  }

  deviation /software-mgmt:software-protect {
     deviate not-supported;
  }

  deviation /software-mgmt:software-validate {
     deviate not-supported;
  }

}
