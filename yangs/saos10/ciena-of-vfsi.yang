module ciena-of-vfsi {
   namespace "http://www.ciena.com/ns/yang/ciena-pn/ciena-of-vfsi";
   prefix "of-vfsi";

   import ciena-of-types {
      prefix "of-types";
   }

   organization
      "Ciena Corporation";
    
   contact
      "Web URL: http://www.ciena.com/
       E-mail:  yang@ciena.com
       Postal:  7035 Ridge Road
                Hanover, Maryland 21076
                    U.S.A.
       Phone:   +1 800-921-1144
       Fax:     +1 410-694-5750";
    
   description
      "This YANG module defines Ciena's management data definition for the definition of 
       Virtual FlowSwitch Instances (vfsi).";
    
   revision "2018-09-14" {
      description
         "Initial Version.";
   }

/*
 * typedefs
 */

   typedef vfsi-id-ref {
      type leafref {
         path "/of-vfsi:of-vfsis/of-vfsi:of-vfsi/of-vfsi:vfsi-id";
      }
      description
         "This type is used by data models that need to reference
          configured vfsis.";
   }

/*
 * features
 */

/*
 * Configuration model.
 */

   container of-vfsis {

      description
         "The configuration model for vfsis (Virtual Flow Switch Instances) include a list of logical ports
          which are contained within the vfsi. The port list may be present at the time of vfsi creation
          or added/remapped afterwards.";

      list of-vfsi {

         description
            "This is the list of Virtual Flow Switch Instances.  These are automatically
             created and configured by the switch, and should not be created by the
             controller.
             Only the table-description should be configured by the controller.";

         key "vfsi-id";
            
         leaf vfsi-id {
            type of-types:vfsi-id;
            description
               "An identifier of the Virtual FlowSwitch Instance. Unique string values are chosen to 
                uniquely identify the Virtual Flow Switch Instance.
                This element cannot be modified by the controller.";
         }

         leaf instance-description {
            type string;
            description
               "A more detailed description that an operator can use to describe 
                the Virtual FlowSwitch Instance.";
         }

         leaf-list port-list {
            type of-types:logical-port;
            description
               "List of Logical Ports within this Virtual Flow Switch Instance.";
         }

         leaf default-instance {
            config false;
            type empty;
            description
               "Table is a default Instance. (e.g. autogenerated by a flowswitch)";
         }
      }
   }

   container of-vfsis-state {
      config false;

      list of-vfsi {

         description
            "The state and statistics associated with a vfsi.";

         key "vfsi-id";

         leaf vfsi-id {
            type of-types:vfsi-id;
            description
               "This object indicates the identifier and is a text string that is 
                used to identify a Virtual Flow Switch Instance.";
         }

         leaf-list port-list {
            type of-types:logical-port;
            description
               "List of Logical Ports within this Virtual Flow Switch Instance.";
         }
      }
   }
}
