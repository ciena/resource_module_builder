module ciena-ospfv3 {
   namespace   "http://ciena.com/ns/yang/ciena-ospfv3";
   prefix "ospfv3";

   import ietf-inet-types {
      prefix "inet";
   }

   import openconfig-interfaces {
      prefix "oc-if";
   }

   import ietf-routing-types {
      prefix "rt-types";
   }

   import ciena-l3-types {
      prefix cn-l3-types;
   }

   import ietf-yang-types {
      prefix yang;
   }

  import ciena-routing-policy {
      prefix "rt-pol";
   }

   import ciena-types {
       prefix ciena-types;
   }

   import ciena-isis {
      prefix "isis";
   }

   import ciena-bfd-types {
      prefix "bfd-types";
   }

   organization
      "Ciena Corporation";

   contact
      "Web URL: http://www.ciena.com/
      E-mail:  yang@ciena.com
      Postal:  7035 Ridge Road
      Hanover, Maryland 21076
      U.S.A.
      Phone:   +1 800-921-1144
      Fax:     +1 410-694-5750";

   description
      "This YANG module defines Ciena's IPv6 Open Shortest Path First (ospfv3) protocol

      Copyright (c) 2022  Ciena Corporation.  All rights
      reserved.

      All information and intellectual property contained in this
      YANG module (Specification) is, and remains the property
      of Ciena Corporation. Ciena retains all title and ownership
      in the Specification, including any revisions.

      Ciena grants all interested parties that access the
      Specification with the intent to use or distribute (you) a
      non-exclusive, no-cost license to use and distribute
      unmodified copies of the Specification solely in connection
      with the management of Ciena products sold by or on
      behalf of Ciena, provided this copyright notice and license
      appear on all copies. Ciena may rescind or modify this
      license at any time.

      This Specification is supplied 'as is', and Ciena makes no
      warranty, either express or implied, as to the use, operation,
      condition, or performance of the Specification. You agree
      that Ciena has no liability for your use of the Specification.";
   

   revision "2022-08-21" {
      description
         "Initial version of ciena-ospfv3 config, state and rpc yang model.
          Removed the leafref path for area-id due to yuma warnings.
          Added default value of mtu-ignore field.";
   }

   feature bfd {
      description
         "Support for BFD detection of OSPF neighbor reachability.";
         reference "RFC 5880: Bidirectional Forwarding Detection (BFD)
         RFC 5881: Bidirectional Forwarding Detection
         (BFD) for IPv6 (Single Hop)";
   }

   feature router-id {
      description
         "Set Router-ID per instance explicitly.";
   }

   identity area-type {
      description
         "Base identity for OSPFV3 area type.";
   }

   identity normal-area {
      base area-type;
      description
         "OSPFV3 normal area.";
   }

   typedef ospfv3-metric {
      type uint32 {
         range "0 .. 16777214";
      }
      description
         "OSPFV3 Metric - 24-bit unsigned integer.";
   }

   grouping redistribute-config {
      description
         "OSPFV3 instance redistribute config.";

      list redistribute {
         key "protocol";
         description
            "Redistribute routes to external process";

         leaf protocol {
            type cn-l3-types:ospfv3-route-source;
            description
               "Redistribute protocol name";
         }

         leaf metric-type {
            type cn-l3-types:ospfv3-metric-type;
            description
               "Metric type";
         }

         leaf metric {
            type  ospfv3-metric;
            default "20";
            description
               "Metric value";
         }

         leaf policy {
            type leafref {
               path "/rt-pol:routing-policy/rt-pol:policies/rt-pol:policy/rt-pol:name";
            }
            description
               "Name of the routemap to apply the filter to.";
         }

         list instance {
            when "../protocol= 'isis'";
            key "tag";
            description
               "Redistribute the routes from a specific ISIS instance";

            leaf tag {
               type leafref {
                  path "/isis:isis/isis:instance/isis:tag";
               }
               description
                  "Tag should be instance of ISIS";
            }

            leaf metric-type {
               type cn-l3-types:ospfv3-metric-type;
               description
                  "Metric type";
             }

            leaf metric {
               type  uint32 {
                  range "0..16777214";
               }
               default "20";
               description
                  "Metric value";
            }

            leaf policy {
               type leafref {
                  path "/rt-pol:routing-policy/rt-pol:policies/rt-pol:policy/rt-pol:name";
               }
               description
                  "Name of the routemap to apply the filter to.";
            }
         }
      }
   }

   grouping area-range-config {
      description
         "OSPFV3 area range config.";

      container areas {
         description
            "All areas.";
         list area {
            key "id";
            max-elements 16;
            description
               "List of OSPFV3 areas";
            leaf id {
               type yang:dotted-quad;
               description
                  "Area ID";
            }

            list range {
               key "prefix";
               description
                  "Summarize routes matching address/mask
                  (Area Border Routers (ABRs) only)";
               leaf prefix  {
                  type  inet:ipv4-prefix;
                  description
                     "the network prefix";
               }
               leaf range-advertise  {
                  type  cn-l3-types:ospfv3-range-advertise;
                  default "advertise";
                  description
                     "Advertise or not-advertise";
               }
            }
         }
      }
   }

   grouping instance-config {
      description
         "OSPFV3 instance config state.";

      leaf router-id {
         if-feature router-id;
         type rt-types:router-id;
         description
            "Defined in RFC 2328. A 32-bit number
            that uniquely identifies the router.";
      }

      leaf spf-min-delay  {
         type  uint32 {
            range "1..600000";
         }
         default "500";
         units milliseconds;
         description
            "The minimum SPF delay time in milliseconds: 500 milliseconds.";
      }

      leaf spf-max-delay  {
         type  uint32 {
            range "1..600000";
         }
         default "5000";
         units milliseconds;
         description
            "The maximum SPF hold delay time in milliseconds: 50000
            milliseconds (50 seconds)";
      }

      leaf admin-distance  {
         type  uint32 {
            range "1..255";
         }
         description
            "OSPFV3 administrative distance";
      }

      uses redistribute-config;
   }

   grouping interface-common-config {
      description
         "Common configuration for all types of interfaces,
         including virtual links and sham links.";

      leaf hello-interval {
         type uint16 {
            range "1..65535";
         }
         units seconds;
         default "10";
         description
            "Interval between hello packets (seconds). It must
            be the same for all routers on the same network.
            Different networks, implementations, and deployments
            will use different hello-intervals. A sample value
            for a LAN network would be 10 seconds.";
      }

      leaf dead-interval {
         type uint16 {
            range "1..65535";
         }
         units seconds;
         must ". > ../hello-interval" {
            error-message "The dead interval must be "
               + "larger than the hello interval";
            description
               "The value must be greater than the 'hello-interval'.";
         }
         default "40";
         description
            "Interval after which a neighbor is declared down
            (seconds) if hello packets are not received. It is

            typically 3 or 4 times the hello-interval. A typical
            value for LAN networks is 40 seconds.";
      }

      leaf retransmit-interval {
         type uint16 {
            range "1..1800";
         }
         units seconds;
         default "5";
         description
            "Interval between retransmitting unacknowledged Link
            State Advertisements (LSAs) (seconds). This should
            be well over the round-trip transmit delay for
            any two routers on the network. A sample value
            would be 5 seconds.";

      }

      leaf transmit-delay {
         type uint16 {
            range "1..3600";
         }
         units seconds;
         default "1";
         description
            "Estimated time needed to transmit Link State Update
            (LSU) packets on the interface (seconds). LSAs have
            their age incremented by this amount when advertised
            on the interface. A sample value would be 1 second.";
      }

      leaf disable {
         type boolean;
         default false;
         description
            "Disable OSPFV3 protocol on the interface.";
      }

      leaf metric {
         type cn-l3-types:ospfv3-link-metric;
         description
            "Interface cost.";
      }

      leaf link-lsa-suppression {
         type boolean;
         description
            "Enable/disable link LSA (type 8) suppression";
         default "false";
      }
   }

   grouping interface-config {
      description 
         "Configuration for real interfaces.";

      leaf ospfv3-intf-type {
         type enumeration {
            enum "broadcast" {
               description
                  "Specify OSPFV3 broadcast multi-access network.";
            }
            enum "non-broadcast" {
               description
                  "Specify OSPFV3 non-broadcast multi-access network.";
            }
            enum "point-to-point" {
               description
                  "Specify OSPFV3 point-to-point network.";
            }
            enum "point-to-multipoint" {
               description
                  "Specify OSPFV3 point-to-multipoint network.";
            }
         }
         default "broadcast";
         description
            "Interface type.";
      }

      leaf passive {
         type boolean;
         default "false";
         description
            "Enable/Disable passive interface - a passive interface's
            prefix will be advertised but no neighbor adjacencies
            will be formed on the interface.";
      }

      leaf priority {
         type uint8 {
            range "0..255";
         }
         default "1";
         description
            "Configure OSPFV3 router priority. On multi-access network
            this value is for Designated Router (DR) election. The
            priority is ignored on other interface types. A router
            with a higher priority will be preferred in the election
            and a value of 0 indicates the router is not eligible to
            become Designated Router or Backup Designated Router
            (BDR).";
      }

      container bfd {
         if-feature bfd;
         description
            "BFD Client Configuration.";
         uses bfd-types:client-cfg-parms;
         reference "RFC YYYY: YANG Data Model for Bidirectional
            Forwarding Detection (BFD). Please replace YYYY with
            published RFC number for draft-ietf-bfd-yang.";
      }

      leaf mtu-ignore  {
         type boolean;
         default "false";
         description
            "Ignore OSPFV3 DD packet having MTU mismatch.";
      }

      container area-id {
         description
            "OSPFV3 area";
         leaf id {
            type yang:dotted-quad;
            description
               "OSPFV3 area-id";
         }
      }

      uses interface-common-config;

   }

   container ospfv3 {
      description
         "OSPFV3 protocol Instance";
      list instance {
         key "tag instance-id";
         max-elements 64;
         description
            "OSPFV3 structure";
         leaf tag {
            type cn-l3-types:string-max-256 {
               pattern '[\S]*';
            }
            description
               "OSPFV3 instance tag";
         }

         leaf instance-id {
             type uint8 {
                 range "0 .. 31|64 .. 95";
             }
             mandatory true;
             description
                 "OSPFV3 instance id 0 to 31 for IPv6 Unicast and 64 to 95 for IPv4 unicast.";
         }

         uses instance-config;

         container areas {
            description
               "All areas.";
            list area {
               key "id";
               max-elements 16;
               description
                  "List of OSPFV3 areas";
               leaf id {
                  type yang:dotted-quad;
                  description
                     "Area ID";
               }

               list range {
                  key "prefix";
                  description
                     "Summarize routes matching address/mask
                     (Area Border Routers (ABRs) only)";
                  leaf prefix  {
                     type  inet:ipv6-prefix;
                     description
                        "The network prefix";
                  }
                  leaf range-advertise  {
                     type  cn-l3-types:ospfv3-range-advertise;
                     default "advertise";
                     description
                        "Advertise or not-advertise";
                  }
               }
               list virtual-link {
                  key "peer-id";
                  description
                     "Virtual link ID(IP addr) associated with neighbor";

                  leaf peer-id {
                     type rt-types:router-id;
                     description
                        "The Virtual Link ID associated with neighbor";
                  }
                  leaf vlink-dead-interval  {
                     type uint32 {
                        range "1..65535";
                     }
                     units seconds;
                     default "40";
                     description
                        "Virtual link Dead interval (in seconds) for router detection time";
                  }
                  leaf vlink-hello-interval {
                     type uint32 {
                        range "1..65535";
                     }
                     units seconds;
                     default "10";
                     description
                        "Virtual link Hello interval (in seconds)";
                  }
                  leaf vlink-retransmit-interval {
                     type uint32 {
                        range "1..1800";
                     }
                     units seconds;
                     default "5";
                     description
                        "Virtual link LSA retransmit interval (in seconds)";
                  }
                  leaf vlink-transmit-delay {
                     type uint32 {
                        range "1..3600";
                     }
                     units seconds;
                     default "1";
                     description
                        "Virtual link LSA transmission delay (in seconds)";
                  }
               }
            }
         }

         container address-family-ipv4-unicast  {
            description
               "OSPFV3 address family IPv4 unicast.";
            uses redistribute-config;
            uses area-range-config;
         }

         container interfaces {
            description
               "All interfaces.";
            list interface {
               key "name";
               description
                  "List of OSPFV3 interfaces.";
               leaf name {
                  type leafref {
                     path "/oc-if:interfaces/oc-if:interface/oc-if:name";
                  }
                  description
                     "Interface name reference.";
               }
               uses interface-config;

            }
         }
      }
   }

   grouping neighbors-state-grouping {
      leaf area-id  {
         type yang:dotted-quad;
         description
            "Area ID";
      }

      list neighbor-state {
         key "router-id";
         description
            "OSPFv3 neighbor state";
         leaf router-id {
            type rt-types:router-id;
            description
               "Neighbor router ID";
         }

         leaf state-type {
            type string {
               length "0..255";
            }
            description
               "Neighbor state type";
         }

         leaf neighbor-event-count  {
            type  yang:counter32;
            description
               "The number of times this neighbor has changed
               state or an error has occurred. Discontinuities in the
               value of this counter can occur when the OSPFV3 neighbor
               is re-initialized.";
         }

         leaf neighbor-retrans-qlen  {
            type  uint32;
            description
               "The current length of the retransmission queue.";
         }

         leaf lsdb-count {
            type  yang:counter64;
            description
               "Link state Database Count";
         }

         leaf ls-request-count {
            type  yang:counter64;
            description
               "Link State request count";
         }

         leaf ls-retransmit-count {
            type  yang:counter32;
            description
               "Link State retransmission count";
         }

         leaf neighbor-up-time {
            type  string {
               length "0..255";
            }
            description
               "The length of time in seconds the neighbor has been in
               the full adjacency state";
         }

         leaf dr-router-id {
            type rt-types:router-id;
            description
               "Neighbor's Designated Router (DR) Router ID.";
         }

         leaf bdr-router-id {
            type rt-types:router-id;
            description
               "The Backup Designated Router (BDR) Router ID.";
         }

         leaf dead-timer  {
            type  string {
               length "0..255";
            }
            description
               "This timer tracks the remaining time before
               the neighbor is declared dead.";
         }

         leaf priority  {
            type  uint32;
            description
               "Configured OSPFV3 router priority. On multi-access network
               this value is for Designated Router (DR) election. The
               priority is ignored on other interface types. A router
               with a higher priority will be preferred in the election
               and a value of 0 indicates the router is not eligible to
               become Designated Router or Backup Designated Router
               (BDR).";
         }
      }

   }

   grouping pdu-statistics-grouping {

      leaf total-sent {
         type uint64;
         description
            "Total number of packets sent.";
      }

      leaf total-received {
         type uint64;
         description
            "Total number of packets received.";
      }

      leaf hello-sent {
         type uint32;
         description
            "Hello's sent.";
      }

      leaf hello-received {
         type uint32;
         description
            "Hello's received.";
      }

      leaf dd-sent {
         type uint32;
         description
            "Total number of database description packets sent.";
      }

      leaf dd-received {
         type uint32;
         description
            "Total number of database description packets received.";
      }

      leaf ls-request-sent {
         type uint32;
         description
            "Total number of LS requests sent.";
      }

      leaf ls-request-received {
         type uint32;
         description
            "Total number of LS requests received.";
      }

      leaf ls-update-sent {
         type uint32;
         description
            "Total number of LS updates sent.";
      }

      leaf ls-update-received {
         type uint32;
         description
            "Total number of LS updates received.";
      }

      leaf ls-ack-sent {
         type uint32;
         description
            "Total number of LS acknowledgements sent.";
      }

      leaf ls-ack-received {
         type uint32;
         description
            "Total number of LS acknowledgements received.";
      }

      leaf error-packet-tx-count{
         type uint32;
         description
            "Number of packets not transmitted due to error.";
      }

      leaf error-packet-rx-count{
         type uint32;
         description
            "Number of incoming packets with error.";
      }
   }

   grouping interface-state-grouping {
      list interface-state {
         key "name";
         description
            "OSPFV3 interface related operations";
         leaf name  {
            type  string {
               length "0..255";
            }
            description
               "Interface name";
         }

         leaf interface-id {
            type uint16;
            description
               "OSPFV3 interface ID.";
         }

         leaf state {
            type  cn-l3-types:ospfv3-intf-state-type;
            description
               "Interface state";
         }

         leaf events  {
            type  uint32;
            description
               "The number of times this interface has changed its
               state or an error has occurred. Discontinuities in the
               value of this counter can occur when the OSPFV3 interface
               is re-initialized.";
         }

         leaf lsa-count  {
            type  yang:counter32;
            description
               "The number of link-scope LSAs";
         }

         leaf lsa-cksum-sum  {
            type  uint32;
            description
               "The modulo 2**32 sum of the LSA checksums
               for link-scope LSAs. The value should be treated as
                  unsigned when comparing two sums of checksums. While
                     differing checksums indicate a different combination
                     of LSAs, equivalent checksums don't guarantee that the
                     LSAs are the same given that multiple combinations of
                     LSAs can result in the same checksum.";
         }

         leaf dr-router-id {
            type rt-types:router-id;
            description
               "Neighbor's Designated Router (DR) Router ID.";
         }

         leaf dr-ip-addr {
            type inet:ip-address;
            description
               "The Designated Router (DR) IP address.";
         }

         leaf bdr-router-id {
            type rt-types:router-id;
            description
               "The Backup Designated Router (BDR) Router ID.";
         }

         leaf remaining-hold-down-time{
            type uint32;
            units milliseconds;
            description
               "Time in milliseconds before LDP notifies OSPF to advertise original cost.";
         }

         leaf bdr-ip-addr {
            type inet:ip-address;
            description
               "The Backup Designated Router (BDR) IP Address.";
         }

         leaf operational-metric {
            type cn-l3-types:ospfv3-link-metric;
            description
               "Interface operational cost with respect to LDP-OSPF sync";
         }

         leaf instance-id {
             type uint8;
             description
                 "OSPFV3 instance id 0 to 31 for IPv6 Unicast and 64 to 95 for IPv4 unicast.";
         }

         uses pdu-statistics-grouping;

         uses neighbors-state-grouping;

         leaf mtu  {
            type  uint16;
            description
               "OSPF packet MTU size.";
         }

         leaf bfd-state {
            type ciena-types:up-down-state;
            description
               "Operational status of BFD on OSPFV3 interface.";
         }

         leaf status {
            type ciena-types:up-down-state;
            description
               "Interface operational status(up/down)";
         }

         leaf neighbors-count {
            type uint16;
            description
               "Neighbors count on the interface";
         }
         container lsdb-summary-state {
            description
               "LSDB interface summary state.";
            list lsdb-interface-entry-summary {
               key "lsa-type lsa-id adv-router";
               config false;
               description
                  "Summary of LSAs in Link Level LSDB";

            uses lsdb-summary-grouping;
            }
         }

         container lsdb-detail-state {
            description
               "LSDB interface detail state.";
            uses lsdb-interface-detail-grouping;
         }
      }
   }

   grouping ospfv3-route-grouping {
      list route-state {
         key "prefix";
         config false;
         description
            "OSPFV3 IPv6 route-table";
         leaf prefix  {
            type inet:ip-prefix;
            description
               "Destination prefix of the route";
         }

         leaf type  {
            type  string;
            description
               "Path type attribute";
         }

         list next-hop {
            key "neighbor-ip-addr";
            config false;
            description
               "OSPF IPv6 route next hop";
            leaf neighbor-ip-addr {
               type inet:ip-address;
               description
                  "IP address of the neighbor";
            }

            leaf outgoing-interface  {
               type string;
               description
                  "Name of the outgoing interface";
            }

            leaf area-id  {
               type yang:dotted-quad;
               description
                  "Area Id in quad-dotted notation";
            }

            leaf area-transit  {
               type boolean;
               description
                  "Transit area";
            }

            leaf path-cost  {
               type uint32;
               description
                  "Path cost of the route";
            }

            leaf ext-type-cost  {
               type uint32;
               description
                  "Path cost of the External route";
            }
         }
      }
   }

   grouping lsdb-summary-grouping {
      description
         "Summary of common LSAs used in LSDB for OSPFv3";
      uses lsa-header;

      leaf do-not-age  {
         type boolean;
         description
            "If true, LSA shall not be removed from the LSDB";
      }

      leaf link-count  {
         type uint32;
         description
            "The number of attached links";
      }
   }
   
   grouping lsa-header {
      description
         "Common LSA for OSPFv2 and OSPFv3";

      leaf lsa-type {
         type cn-l3-types:ospfv3-lsa-type;
         description 
            "LSA type";
      }

      leaf lsa-id {
         type yang:dotted-quad;
         description 
            "Link-State ID.";
      }

      leaf adv-router {
         type rt-types:router-id;
         description
            "LSA advertising router.";
      }

      leaf lsa-age {
         type uint16;
         description 
            "LSA age.";
      }

      leaf seq-num {
         type uint32;
         description
            "LSA sequence number.";
      }

      leaf checksum {
         type string;
         description 
            "LSA checksum.";
      }

   }

   grouping lsa-header-detail {
      leaf length {
         type uint16;
         description 
            "LSA length including the header.";
      }

      leaf options {
         type string {
            length "0..255";
         }
         description 
            "The Options field enables OSPFV3 routers to support 
            (or not support) optional capabilities, and to
            communicate their capability level to other OSPFV3 routers";
      }

   }

   grouping lsdb-area-detail-grouping {

      list lsdb-area-entry-detail {
         key "lsa-type lsa-id adv-router";
         config false;
         description
            "List OSPF LSAs.";

         uses lsa-header;
         uses lsa-header-detail;

         container router-lsa {
            description 
               "Router-LSAs are the Type 1 LSAs.
               The LSA describes the state and cost of the router's
               links (i.e., interfaces) to the area.";

            leaf flags{           
               type string;     
               description 
                  "Router LSA flag bits.";
            }  

            leaf options{           
               type string;     
               description 
                  "Router LSA options bits list.";
            }

            leaf link-count {
               type uint16;
               description 
                  "The number of links in the router LSA.";
            }

            list link {
               key "interface-id";
               description "Router LSA link.";

               leaf metric {
                  type uint16;
                  description
                     "Link Metric.";
               }

               leaf interface-id {
                  type uint32;
                  description
                     "Interface id for link.";
               }          

               leaf neighbor-interface-id {
                  type uint32;
                  description
                     "Neighbor interface id for link.";
               }

               leaf neighbor-router-id {            
                  type yang:dotted-quad;            
                  description 
                     "Neighbor router ID for link.";          
               }         
            }
         }

         container network-lsa {
            description 
               "Network-LSAs are the Type 2 LSAs.
               The LSA describes all routers attached to the
               network, including the Designated Router itself.";

            leaf options{           
               type string;     
               description 
                  "Network LSA options bits.";
            }

            list attached-router {
               key "router-id";
               description "List of attached routers to the network.";
               leaf router-id {
                  type inet:ipv4-address;
                  description
                     "Router id of the Network.";
               }
            }
         }

         container inter-area-prefix-lsa {
            description
               "Summary-LSAs are the Type 3 LSAs.
               Type3 LSAs are used when the destination is an IP network.";

            leaf metric {
               type uint16;
               description
                  "Inter-Area Prefix Metric.";
            }

            leaf prefix  {
               type  inet:ip-prefix;
               description
                  "Inter area prefix.";
            }

            leaf prefix-length  {
               type uint8;
               description
                  "Inter area prefix length.";
            }

            leaf prefix-options {
               type uint8;
               description
                  "Inter area Prefix options.";
            }
         }

         container inter-area-router-lsa {
            description 
               "Inter Area Router LSAa are the Type 4 LSAs.";

            leaf options {
               type string;     
               description
                  "Inter area Router LSA options bits.";
            }

            leaf metric {
               type uint16;
               description
                  "Inter area router Metric.";
            }

            leaf destination-router-id {            
               type yang:dotted-quad;            
               description 
                  "Destination router ID.";          
            }        
         }

         container intra-area-prefix-lsa {
            description
               "Intra Area Prefix LSA are the Type 9 LSAs.";

            leaf referenced-ls-type {
               type uint16;
               description "Referenced Link State type.";
            }

            leaf referenced-link-state-id {
               type uint32;
               description
                  "Referenced Link State ID.";
            }

            leaf referenced-adv-router {
               type rt-types:router-id;
               description
                  "Referenced Advertising Router.";
            }

            leaf prefix-count {
               type uint16;
               description
                  "Prefix count for intra area prefix LSA.";
            }

            list prefix-list {
               key "prefix";
               description "Intra area LSA prefix.";

               leaf prefix  {
                  type  inet:ip-prefix;
                  description
                     "Intra area LSA  prefix.";
               }

               leaf prefix-length {
                  type uint8;
                  description
                     "Intra area LSA  prefix length.";
               }
 
               leaf metric {
                  type uint16;
                  description
                     "Metrics given for this link.";
               }
               

               leaf prefix-options {
                  type string;     
                  description
                     "Intra area Prefix LSA options bits.";
               }
            }
         }
      }
   }


   grouping lsdb-interface-detail-grouping {

      list lsdb-interface-entry-detail {
         key "lsa-type lsa-id adv-router";
         config false;
         description
            "List OSPF LSAs.";

         uses lsa-header;
         uses lsa-header-detail;

         container link-lsa{
            description 
               "Link are the Type 8 LSAs.";

            leaf priority {
               type uint8;
               description
                  "Priority configure on Link.";
            }

            leaf options {
               type string;     
               description
                  "Link LSA options bits.";
            }

            leaf link-local-addr {
               type inet:ip-address;
               description
                  "The address of link local.";
            }

            leaf prefix-count {
               type uint32;
               description
                  "Prefix count for link  LSA.";
            }

            list prefix-list {
               key "prefix";
               description
                  "Link LSA prefix.";

               leaf prefix  {
                  type  inet:ip-prefix;
                  description
                     "Link LSA prefix.";
               }

               leaf prefix-length  {
                  type  uint8;
                  description
                     "Link LSA prefix length.";
               }

               leaf prefix-options {
                  type string;
                  description
                     "Link LSA prefix options.";
               }
            }
         }
      }
   }

   grouping lsdb-instance-detail-grouping {

      list lsdb-instance-entry-detail {
         key "lsa-type lsa-id adv-router";
         config false;
         description
            "List OSPF LSAs.";

         uses lsa-header;
         uses lsa-header-detail;

         container as-external-lsa{
            description 
               "AS-external-LSAs are the Type 5 LSAs.";

            leaf prefix {
               type inet:ip-address;
               description 
                  "External Prefix.";
            }

            leaf prefix-length {
               type uint8;
               description 
                  "External Prefix length.";
            }

            leaf prefix-options {
               type string;
               description 
                  "External Prefix options.";
            }

            leaf metric-type {
               type cn-l3-types:ospfv3-metric-type;
               description 
                  "External Prefix Metric Type.";
            }

            leaf metric {
               type uint32;
               description 
                  "External Prefix Metric.";
            }

            leaf forwarding-addr {
               type inet:ip-address;
               description 
                  "Forwarding IP Address.";
            }

            leaf route-tag {
               type uint32;
               description 
                  "A 32-bit field attached to each external route.";
            }
         }
      }
   }

   grouping ospfv3-instance-state-grouping {
      leaf up-time {
         type  string {
            length "0..255";
         }
         description
            "The length of time in seconds the protocol instance has been
            in the up state";
      }

      leaf lsa-count {
         type  yang:counter32;
         description
            "External Link State Advertisement count";
      }

      leaf lsa-cksum-sum {
         type  string {
            length "0..255";
         }
         description
            "External LSA checksum";
      }

      leaf originate-new-lsa-count {
         type  yang:counter32;
         description
            "Number of self-originating LSAs";
      }

      leaf rx-new-lsas-count {
         type  yang:counter32;
         description
            "Number of new LSAs received";
      }

      leaf area-count {
         type  yang:counter32;
         description
            "Number of areas in the OSPF instance";
      }

      leaf instance-creation-time {
         type  string {
            length "0..255";
         }
         description
            "OSPFV3 Statistics Up Time";
      }

      leaf router-id-change-count {
         type  yang:counter32;
         description
            "The number of times the router ID was modified";
      }

      leaf dr-election-counter {
         type  yang:counter32;
         description
            "Number of DR elections";
      }

      leaf neighbor-expiration-count {
         type  yang:counter32;
         description
            "Number of expired neighbors";
      }

      leaf neighbor-bad-ls-reqs-count {
         type  yang:counter32;
         description
            "Number of bad LS Requests received";
      }

      leaf neighbor-seq-num-mismatch-count {
         type  yang:counter32;
         description
            "Number of packets received from neighbors with mismatched
            sequence number";
      }

      leaf router-id {
         type rt-types:router-id;
         description
            "The router identifier";
      }

      uses pdu-statistics-grouping;

      leaf router-abr-mode  {
         type  string {
            length "0..255";
         }
         description
            "OSPF router ABR mode";
      }

      leaf router-asbr  {
         type boolean;
         default "false";
         description
            "OSPFV3 router ASBR Information";
      }
   }

   grouping virtual-link-state-grouping {
     list virtual-link-state {
       key "name";
       description
         "Grouping of virtual link parameters";
       leaf name  {
         type  string {
           length "0..255";
         }
         description
           "Virtual link identifier, unique name assigned for the virtual link";
       }
       leaf vlink-state {
         type  cn-l3-types:ospfv3-vlink-state-type;
         description
           "Virtual link state";
       }
       leaf vlink-router-id {
         type rt-types:router-id;
         description
           "Router ID of remote device.";
       }
       leaf vlink-transit-area {
         type inet:ip-address;
         description
           "The transit area address of virtual link.";
       }
       leaf vlink-interface-name  {
         type  string {
         length "0..255";
         }
         description
           "Interface name from where Virtual link is connected";
       }
       leaf vlink-local-addr {
         type inet:ip-address;
         description
           "The address of local node.";
       }
       leaf vlink-remote-addr {
         type inet:ip-address;
         description
           "The address of remote node.";
       }
       leaf vlink-hello-due  {
          type  string {
            length "0..255";
          }
          description
            "This is to get the timer that tracks the remaining time before
            the neighbor is declared dead (in seconds).";
       }
       leaf vlink-hello-timer {
         type uint32;
         description
           "This is to get the configured vlink hello timer (in seconds)";
       }
       leaf vlink-dead-timer {
         type uint32;
         units seconds;
         description
           "This is to get the vlink dead timer (in seconds)";
       }
       leaf vlink-transmit-timer {
         type uint32;
         units seconds;
         description
           "This is to get the vlink transmit timer (in seconds)";
       }
       leaf vlink-retransmit-timer {
         type uint32;
         units seconds;
         description
           "This is to get the vlink retransmit timer (in seconds)";
       }
     }
   }

   container ospfv3-state {
      description
         "OSPFV3 state.";
      config false;
      list instance {
         key "tag";
         description
            "OSPFV3 attributes for each ospfv3 process id";
         leaf tag {
            type leafref {
               path "/ospfv3/instance/tag";
            }
            description
               "OSPFV3 process tag";
         }
         uses ospfv3-instance-state-grouping;

         list area-state {
            key "id";
            description
               "List of ospf areas";
            leaf id  {
               type yang:dotted-quad;
               description
                  "area to which the network belongs";
            }

            leaf interface-count  {
               type  yang:counter32;
               description
                  "Number of interfaces in the area";
            }

            leaf neighbor-count  {
               type  yang:counter32;
               description
                  "Number of neighbors in the area";
            }

            leaf spf-last-exec-time  {
               type  string {
                  length "0..255";
               }
               description
                  "SPF last executed time";
            }

            leaf spf-runs-count  {
               type  yang:counter32;
               description
                  "The number of times the intra-area SPF has run.
                  Discontinuities in the value of this counter can occur
                  when the OSPF area is re-initialized.";
            }

            leaf lsa-count  {
               type  yang:counter32;
               description
                  "The number of LSAs of the LSA type.";
            }

            leaf lsa-checksum  {
               type  string {
                  length "0..255";
               }
               description
                  "The modulo 2**32 sum of the LSA checksums
                  for the LSAs of this type. The value should be
                     treated as unsigned when comparing two sums of
                        checksums. While differing checksums indicate a
                        different combination of LSAs, equivalent checksums
                        don't guarantee that the LSAs are the same given that
                        multiple combinations of LSAs can result in the same
                        checksum.";
            }
            container lsdb-summary-state {
               description
                  "LSDB summary state.";

               list lsdb-area-entry-summary {
                  key "lsa-type lsa-id adv-router";
                  config false;
                  description
                     "Summary of LSAs in Area Level LSDB ";
               uses lsdb-summary-grouping;
               }
            }

            container lsdb-detail-state {
               description
                  "LSDB area detail state.";
               uses lsdb-area-detail-grouping;
            }

         }

         container interfaces-state {
            description
               "OSPFV3 interface state.";
            uses interface-state-grouping;
         }

         container routes-state {
            description
               "OSPFV3 route state.";
            uses ospfv3-route-grouping;
         }

         container lsdb-summary-state {
            description
               "LSDB instance summary state.";
            list lsdb-instance-entry-summary {
               key "lsa-type lsa-id adv-router";
               config false;
               description
                  "Summary of LSAs in Instance Level LSDB";

            uses lsdb-summary-grouping;
            }
         }

         container lsdb-detail-state {
            description
               "LSDB instance detail state.";
            uses lsdb-instance-detail-grouping;
         }


         container vlink-state {
            description
               "Virtual link state.";
            uses virtual-link-state-grouping; 
         } 
      }
   }

   rpc ospfv3-clear-instance {
      input {
         leaf instance-tag {
            type cn-l3-types:string-max-256 {
               pattern '[\S]*';
            }
            description
               "OSPFV3 instance ID";
         }
      }

      output {
         leaf response {
            type string;
            description
               "The response could be 'success', or the reason for ospfv3-proc-clear failure";
         }
      }
   }
}
