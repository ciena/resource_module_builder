module ciena-capabilities {
  namespace   "http://ciena.com/ns/yang/ciena-capabilities";
  prefix "ciena-capabilities";

  organization
    "Ciena Corporation";

  contact
    "Web URL: http://www.ciena.com/
    E-mail:  yang@ciena.com
    Postal:  7035 Ridge Road
             Hanover, Maryland 21076
             U.S.A.
    Phone:   +1 800-921-1144
    Fax:     +1 410-694-5750";

  description
    "This module contains the YANG definition for Ciena Capabilities. 
        
    Copyright (c) 2022 Ciena Corporation.  All rights 
    reserved.

    All information and intellectual property contained in this
    YANG module (Specification) is, and remains the property
    of Ciena Corporation. Ciena retains all title and ownership
    in the Specification, including any revisions.

    Ciena grants all interested parties that access the
    Specification with the intent to use or distribute ('you') a
    non-exclusive, no-cost license to use and distribute
    unmodified copies of the Specification solely in connection
    with the management of Ciena products sold by or on
    behalf of Ciena, provided this copyright notice and license
    appear on all copies. Ciena may rescind or modify this
    license at any time.

    This Specification is supplied 'as is', and Ciena makes no
    warranty, either express or implied, as to the use, operation,
    condition, or performance of the Specification. You agree
    that Ciena has no liability for your use of the Specification.";

  revision 2022-03-07 {
    description
      "Initial revision.";
    reference
      "None";
  }


  container get-bulk-supported-xpaths {
    config false; 
         
    description
      "Get-bulk xpaths that are supported";
         
    list get-bulk-supported-xpath {
      key module-name;

      description 
        "List of get-bulk xpaths that are supported grouped by module names";
             
      leaf module-name {
        type string;
        description 
          "Yang module name";
      }
             
      leaf-list oper-list-xpath {
        type string;
        description
          "List of get-bulk xpaths that are supported";
      }
    }
  }
}
