module ciena-pon-ctrl {
  namespace "http://www.ciena.com/ns/yang/ciena-pon-ctrl";
  prefix "pon-ctrl";

  import ciena-types {
    prefix ciena;
  }

  import ietf-yang-types {
    prefix yang;
  }

  import openconfig-interfaces {
    prefix oc-if;
  }

  import ciena-openconfig-interfaces {
    prefix cn-if;
  }

  import ciena-mef-fp {
    prefix mef-fp;
  }

  import ciena-packet-typedefs {
    prefix cntypes;
  }

  import ietf-inet-types {
    prefix inet;
  }

  import yuma-ncx {
    prefix ncx;
  }

  organization
    "Ciena Corporation";

  contact
    "Web URL: http://www.ciena.com/
     E-mail:  yang@ciena.com
     Postal:  7035 Ridge Road
     Hanover, Maryland 21076
     U.S.A.
     Phone:   +1 800-921-1144
     Fax:     +1 410-694-5750";

  description
    "This YANG module defines Ciena's data model for the management of Passive
     Optical Network (PON) devices. This includes Optical Line Terminals (OLTs) and
     subtended Optical Network Units (ONUs).

     Copyright (c) 2021-2023 Ciena Corporation. All rights reserved.

     All information and intellectual property contained in this
     YANG module (Specification) is, and remains the property
     of Ciena Corporation. Ciena retains all title and ownership
     in the Specification, including any revisions.

     Ciena grants all interested parties that access the
     Specification with the intent to use or distribute (\"you\") a
     non-exclusive, no-cost license to use and distribute
     unmodified copies of the Specification solely in connection
     with the management of Ciena products sold by or on
     behalf of Ciena, provided this copyright notice and license
     appear on all copies. Ciena may rescind or modify this
     license at any time.

     This Specification is supplied 'as is', and Ciena makes no
     warranty, either express or implied, as to the use, operation,
     condition, or performance of the Specification. You agree
     that Ciena has no liability for your use of the Specification.";

  revision "2023-11-02" {
    description
       "Add support for external database.";
    reference
      "- ITU-T G.987    : 10-Gigabit-capable passive optical networks (XG-PON)
       - ITU-T G.9807.1 : 10-Gigabit-capable symmetric passive optical network (XGS-PON)
       - ITU-T G.988    : ONU management and control interface (OMCI) specification
       - IEEE 802.3av   : 10Gbit/s Ethernet PON (10G EPON) standard
       - RFC 2865       : Remote Authentication Dial In User Service (RADIUS)";
  }

  revision "2023-10-04" {
    description
      "Add DHCPv6 for Residential PON.
       Add receive power threshold profile and error threshold profile.
       Add support for rogue ONU.
       Modifications to the model due to moving rogue ONU to a seperate process.
       DHCPv6 flag was missing from state clear RPC.
       Add units for up min/max grant period in SLA Profile.
       Modify OLT/ONU/Datalink state notifications to clear alarms on object delete.
       Minor corrections to rogue ONU attributes and descriptions for residential PON.
       Add revision model to ONU state.
       Add OLT port number to discovery notifications.
       Add support to configure OLT using port ID.
       Add new notifications when PON is reconciled.
       Add alarm power thresholds ranges.
       Adding more ONU alarms.
       Add control plane processing for protocols DHCPv4, DHCPv6, authentication and PPPoE.
       Modify DHCP enterprise number to a integer instead of string.
       Combine control plane processing for protocols DHCPv4 and DHCPv6.
       Add support for ONU performance monitoring statistics and unicast/multicast/broadcast
       counters for OLT.
       Adding support caching for ONU power readings.
       Make Tx/Rx power threshold ranges more accurate.
       Update default values for guard-time, preamble and up-service-limit to latest manufacturer
       recommended values.
       Add 2 new DHCPv6 oper states:released, declined.
       Prefix ONU statistics with rx to be consistent with other statistics.
       Add new datalink misconfigured alarm.
       Add high/low receive power readings to OLT diagnostics.
       Add error threshold checking for rogue ONU.
       Add mass ONU deregistration event handling for rogue ONU.
       Add support for caching of OLT diagnostic data.
       Add support for global automatic ONU upgrade configuration.
       Add two states to capture the current operational state for PPPoE and authentication.
       Add auto-onu-upgrade and priority queue mapping.
       Add degraded ONU threshold configuration.
       Add last-clear-time timestamps for all PON statistics.
       Add RADIUS server attributes and update descriptions and defaults.
       Add priority attribute to RADIUS server.
       Add new statistics provided from hardware.
       Add new OLT misconfigured alarm.
       Deprecating auto-boot mode for the OLT.
       Add held/quiet start time and held/quiet operational state.
       Add config restriction for serial-number change on ONU.
       Add failure count for datalink authentication state.
       Rename auto-onu prefixed fields to onu-auto.
       Add vendor ID to ONU state.
       Deprecated unused parameters for rogue ONU.
       Add global event when statistics retrieval threshold is exceeded.
       Allow specific CPE entry to be cleared.
       Add dying gasp ONU alarm.
       Moving Datalink/XGEM/OLT/UNI Port Stats to RPC.
       Allow XGEM Stats to be cleared.
       Moving Datalink and OLT Stats to RPC.
       Add previous oper-state and reason code for OLT, ONU and UNI-Port oper-state-change notification.
       Migrating rogue ONU to Universal PON controller.
       Add service config name to ONU.
       Add ONU alarms: loss-ploam, loss-key-synchronization, tx-signal-drift, differential-reach, omci-comm-failure, LOS.
       Updated ONU power threshold description to indicate thresholds are temporarily not supported starting in release 10.8.1.
       Add config for database external access over ipv4/ipv6.
       Adding hardware-triggered to oper-state-change-reason for ONU.
       Add UNI port alarm to UNI port state.
       Add OLT disabled reason to ONU oper-state-change-reason.
       Rogue ONU attributes missing from rogue ONU command.
       Add ONU service config failure alarm.
       Add reset status for ONU.
       Deprecate onu-performance-monitoring-mode on OLT.
       Deprecate performance-monitoring-collection on ONU.
       Deprecate stats-collection on UNI Port.
       Add clear command to Rogue ONU to allow the initial power variance reading to be cleared.
       Add offline state to authentication states.
       Add reset status for OLT.";
    reference
      "- ITU-T G.987    : 10-Gigabit-capable passive optical networks (XG-PON)
       - ITU-T G.9807.1 : 10-Gigabit-capable symmetric passive optical network (XGS-PON)
       - ITU-T G.988    : ONU management and control interface (OMCI) specification
       - IEEE 802.3av   : 10Gbit/s Ethernet PON (10G EPON) standard
       - RFC 2865       : Remote Authentication Dial In User Service (RADIUS)";
  }

  revision "2022-03-10" {
    description
      "Add PPPoE for Residential PON.
       Add support for registration ID in ONU configuration.
       Add support for PON link utilization statistics.
       Add support for loopback on Datalink.
       Add support for registration ID for unconfigured ONUs.
       Add registration ID to ONU discovered notification.";
    reference
      "- ITU-T G.987    : 10-Gigabit-capable passive optical networks (XG-PON)
       - ITU-T G.9807.1 : 10-Gigabit-capable symmetric passive optical network (XGS-PON)
       - ITU-T G.988    : ONU management and control interface (OMCI) specification
       - IEEE 802.3av   : 10Gbit/s Ethernet PON (10G EPON) standard
       - RFC 2865       : Remote Authentication Dial In User Service (RADIUS)";
  }

  revision "2021-11-05" {
    description
      "Add admin state to ONU configuration.
       Add support for ONU-ID configuration.
       Add support for residential PON configuration.
       Add RADIUS, authentication and dhcp relay state for residential PON.
       Add RPC to get/set in-band management TPID and VID on an OLT.
       Add support for automatic ONU upgrades.
       Add option to control the creation of a flooding link on NNI Networks.
       Add support for UNI Port statistics.
       Add delay and distance measurements to ONU diagnostic data.
       Add authentication and DHCP reset command.
       Add support for ALLOC-ID configuration.
       Clean-up of Residential PON statistics and correction of attribute spelling.
       Add firmware-upgrade-attempts to ONU state.
       Add range restriction to ALLOC-ID and ONU-ID configuration.
       Add support for clear command of expired/failed CPE state entries for authentication and l2-relay.
       Simplify statistics for RADIUS Server.
       Clean-up of Residential PON state attributes.
       Remove dhcp-sub-option.
       Add new states for Authentication and DHCP. Change cpe-mac to type of yang:mac-address.";
    reference
      "- ITU-T G.987    : 10-Gigabit-capable passive optical networks (XG-PON)
       - ITU-T G.9807.1 : 10-Gigabit-capable symmetric passive optical network (XGS-PON)
       - ITU-T G.988    : ONU management and control interface (OMCI) specification
       - IEEE 802.3av   : 10Gbit/s Ethernet PON (10G EPON) standard
       - RFC 2865       : Remote Authentication Dial In User Service (RADIUS)";
  }

  revision "2020-11-20" {
    description
      "Add ONU cross-connect configuration.
       Add NNI Network state container.
       Add RPC to clear NNI Network statistics.
       Add XCVR data container to UNI Port state.
       Change description of some list containers for better clarity.
       Split UNI Port speed and duplex enums into separate config and state enums.
       Add expected-firmware-version to OLT state.
       Change SLA Profile value ranges to reflect correct values.
       Add uptime to OLT and ONU diagnostic data.";
    reference
      "- ITU-T G.987    : 10-Gigabit-capable passive optical networks (XG-PON)
       - ITU-T G.9807.1 : 10-Gigabit-capable symmetric passive optical network (XGS-PON)
       - ITU-T G.988    : ONU management and control interface (OMCI) specification
       - IEEE 802.3av   : 10Gbit/s Ethernet PON (10G EPON) standard";
  }

  revision "2020-08-20" {
    description
      "Add ONU diagnostic data container.
       Add OLT diagnostic data container.
       Update Datalink configuration to specify 'add-ctag' PCP and VLAN-ID list.
       Add expected-firmware-version to ONU state.";
    reference
      "- ITU-T G.987    : 10-Gigabit-capable passive optical networks (XG-PON)
       - ITU-T G.9807.1 : 10-Gigabit-capable symmetric passive optical network (XGS-PON)
       - IEEE 802.3av   : 10Gbit/s Ethernet PON (10G EPON) standard";
  }

  revision "2020-06-25" {
    description
      "Add ONU UNI port configuration and state containers.
       Add RPC for ONU admission control.
       Add default values for SLA Profile.";
    reference
      "- ITU-T G.987    : 10-Gigabit-capable passive optical networks (XG-PON)
       - ITU-T G.9807.1 : 10-Gigabit-capable symmetric passive optical network (XGS-PON)
       - IEEE 802.3av   : 10Gbit/s Ethernet PON (10G EPON) standard";
  }

  revision "2020-05-04" {
    description
      "Add unknown state to olt-oper-state and onu-oper-state enums";
    reference
      "- ITU-T G.987    : 10-Gigabit-capable passive optical networks (XG-PON)
       - ITU-T G.9807.1 : 10-Gigabit-capable symmetric passive optical network (XGS-PON)
       - IEEE 802.3av   : 10Gbit/s Ethernet PON (10G EPON) standard";
  }

  revision "2020-01-20" {
    description
      "Add RPCs for OLT/ONU firmware upgrade.";
    reference
      "- ITU-T G.987    : 10-Gigabit-capable passive optical networks (XG-PON)
       - ITU-T G.9807.1 : 10-Gigabit-capable symmetric passive optical network (XGS-PON)
       - IEEE 802.3av   : 10Gbit/s Ethernet PON (10G EPON) standard";
  }

  revision "2019-09-16" {
    description
      "Restructure and rename Network configuration objects.";
    reference
      "- ITU-T G.987  : 10-Gigabit-capable passive optical networks (XG-PON)
       - IEEE 802.3av : 10Gbit/s Ethernet PON (10G EPON) standard";
  }

  revision "2019-05-01" {
    description
      "Initial version.";
    reference
      "- ITU-T G.987  : 10-Gigabit-capable passive optical networks (XG-PON)
       - IEEE 802.3av : 10Gbit/s Ethernet PON (10G EPON) standard";
  }

  typedef name-string {
    type string {
      length "1..64";
    }
    description
      "Name string type.";
  }

  typedef pon-relay-attribute-string {
    type string {
      length "1..255";
    }
    description
      "PON Relay string for RADIUS, authentication, DHCP, DHCPv6 and PPPoE identifier attributes.";
  }

  typedef interface-ref {
    type oc-if:base-interface-ref;
    description
      "L3 Interface reference type.";
  }

  typedef radius-server-ref {
    type leafref {
      path "/pon-ctrl:pon-ctrl" +
           "/pon-ctrl:radius-servers" +
           "/pon-ctrl:radius-server" +
           "/pon-ctrl:name";
    }
    description
      "RADIUS Server reference leafref type.";
  }

  typedef olt-ref {
    type leafref {
      path "/pon-ctrl:pon-ctrl" + 
           "/pon-ctrl:olts" + 
           "/pon-ctrl:olt" + 
           "/pon-ctrl:name";
    }
    description
      "OLT reference leafref type.";
  }

  typedef nni-network-ref {
    type leafref {
      path "/pon-ctrl:pon-ctrl" +
           "/pon-ctrl:olts" +
           "/pon-ctrl:olt" +
           "/pon-ctrl:nni-networks" +
           "/pon-ctrl:nni-network" +
           "/pon-ctrl:name";
    }
    description
      "NNI Network reference leafref type.";
  }

  typedef onu-ref {
    type leafref {
      path "/pon-ctrl:pon-ctrl" + 
           "/pon-ctrl:onus" + 
           "/pon-ctrl:onu" + 
           "/pon-ctrl:name";
    }
    description
      "ONU reference leafref type.";
  }

  typedef datalink-ref {
    type leafref {
      path "/pon-ctrl:pon-ctrl" +
           "/pon-ctrl:onus" +
           "/pon-ctrl:onu" +
           "/pon-ctrl:datalinks" +
           "/pon-ctrl:datalink" +
           "/pon-ctrl:name";
    }
    description
      "Datalink reference leafref type.";
  }

  typedef uni-port-ref {
    type leafref {
      path "/pon-ctrl:pon-ctrl" +
           "/pon-ctrl:onus" +
           "/pon-ctrl:onu" +
           "/pon-ctrl:uni-ports" +
           "/pon-ctrl:uni-port" +
           "/pon-ctrl:name";
    }
    description
      "UNI Port reference leafref type.";
  }

  typedef sla-profile-ref {
    type leafref {
      path "/pon-ctrl:pon-ctrl" + 
           "/pon-ctrl:sla-profiles" + 
           "/pon-ctrl:sla-profile" + 
           "/pon-ctrl:name";
    }
    description
      "SLA Profile reference leafref type.";
  }

  typedef power-threshold-profile-ref {
    type leafref {
      path "/pon-ctrl:pon-ctrl" +
           "/pon-ctrl:power-threshold-profiles" +
           "/pon-ctrl:power-threshold-profile" +
           "/pon-ctrl:name";
    }
    description
      "Power threshold profile reference leafref type.";
  }

  typedef error-threshold-profile-ref {
    type leafref {
      path "/pon-ctrl:pon-ctrl" +
           "/pon-ctrl:error-threshold-profiles" +
           "/pon-ctrl:error-threshold-profile" +
           "/pon-ctrl:name";
    }
    description
      "Error threshold profile reference leafref type.";
  }

  typedef cos-queue-map-ref {
    type leafref {
      path "/pon-ctrl:pon-ctrl" +
           "/pon-ctrl:cos-queue-maps" +
           "/pon-ctrl:cos-queue-map" +
           "/pon-ctrl:name";
    }
    description
      "CoS queue map reference leafref type.";
  }

  typedef inband-management-action {
    type enumeration {
      enum get {
        description
          "In-band management get action.";
      }
      enum set {
        description
          "In-band management set action.";
      }
    }
    description
      "In-band management action type.";
  }

  typedef tpid {
    type enumeration {
      enum 0x8100 {
        value 33024;
        description
          "TPID 0x8100.";
      }
      enum 0x88a8 {
        value 34984;
        description
          "TPID 0x88a8.";
      }
    }
    description
      "TPID type.";
  }

  typedef pon-mode {
    type enumeration {
      enum xgs-pon {
        description
          "XGS-PON mode.";
      }
      enum 10g-epon {
        description
          "10G-EPON mode.";
      }
    }
    description
      "PON-mode type.";
  }

  typedef encryption-mode {
    type enumeration {
      enum disabled {
        description
          "Encryption is disabled.";
      }
      enum downstream {
        description
          "Encryption is enabled in the downstream direction only.";
      }
      enum bidirectional {
        description
          "Encryption is enabled bidirectionally.";
      }
    }
    description
      "Encryption mode type.";
  }

  typedef statistics-binning-mode {
    type enumeration {
      enum disabled {
        description
          "Statistics binning is disabled.";
      }
      enum history {
        description
          "Statistics binning returns 15-min historical bin.";
      }
      enum running {
        description
          "Statistics binning returns 15-min historical bin.";
      }
    }
    description
      "Statistics binning mode type.";
  }

  typedef olt-oper-state {
    type enumeration {
      enum active {
        description
          "OLT is configured and discovered.";
      }
      enum configured {
        description
          "OLT is configured/pre-provisioned but not discovered.";
      }
      enum disabled {
        description
          "OLT is disabled.";
      }
      enum unknown {
        description
          "OLT was previously active or disabled but is no longer discovered.";
      }
    }
    description
      "OLT operational state type.";
  }

  typedef onu-oper-state {
    type enumeration {
      enum registered {
        description
          "ONU is configured and registered with the OLT.";
      }
      enum configured {
        description
          "ONU is configured/pre-provisioned but has not yet registered with the OLT.";
      }
      enum deregistered {
        description
          "ONU has deregistered with the OLT.";
      }
      enum unknown {
        description
          "ONU state is unknown due to OLT state being unknown.";
      }
      enum unconfigured {
        description
          "ONU was discovered but has no corresponding configuration.";
      }
    }
    description
      "ONU operational state type.";
  }

  typedef uni-port-oper-state {
    type enumeration {
      enum up {
        description
          "UNI Port link state is up.";
      }
      enum down {
        description
          "UNI Port link state is down.";
      }
      enum unknown {
        description
          "UNI Port link state is unknown.";
      }
    }
    description
      "UNI Port operational state type.";
  }

  typedef radius-server-oper-state {
    type enumeration {
      enum up {
        description
          "RADIUS server state is up.";
      }
      enum down {
        description
          "RADIUS server state is down.";
      }
      enum unknown {
        description
          "RADIUS server state is unknown.";
      }
    }
    description
      "RADIUS server operational state type.";
  }

  typedef dhcp-relay-oper-state {
    type enumeration {
      enum discover {
        description
          "DHCP relay state is discover (discover packet is sent).";
      }
      enum offer {
        description
          "DHCP relay state is offer (offer packet is sent).";
      }
      enum request {
        description
          "DHCP relay state is request (request packet is sent).";
      }
      enum acknowledge {
        description
          "DHCP relay state is acknowledge (initialization is complete).";
      }
      enum not-acknowledge {
        description
          "DHCP relay state is not-acknowledge (requested parameters are unacceptable).";
      }
      enum decline {
        description
          "DHCP relay state is decline (network address is in use).";
      }
      enum release {
        description
          "DHCP relay state is release (network address is no longer required).";
      }
      enum inform {
        description
          "DHCP relay state is inform (network address is manually obtained).";
      }
      enum forced-renew {
        description
          "DHCP relay state is forced renew.";
      }
      enum expired {
        description
          "DHCP relay state is expired.";
      }
      enum reset {
        description
          "DHCP relay state is reset.";
      }
      enum unknown {
        description
          "DHCP relay state is unknown.";
      }
    }
    description
      "DHCP relay operational state type.";
  }

  typedef dhcpv6-oper-state {
    type enumeration {
      enum solicit {
        description
          "DHCPv6 relay state is solicit (solicit message is sent).";
      }
      enum request {
        description
          "DHCPv6 relay state is request (request message is sent).";
      }
      enum confirm {
        description
          "DHCPv6 relay state is confirm (confirm message is sent).";
      }
      enum renew {
        description
          "DHCPv6 relay state is renew (renew message is sent).";
      }
      enum rebind {
        description
          "DHCPv6 relay state is rebind (rebind message is sent).";
      }
      enum release {
        description
          "DHCPv6 relay state is release (network address is no longer required).";
      }
      enum decline {
        description
          "DHCPv6 relay state is decline (network address is in use).";
      }
      enum info-request {
        description
          "DHCPv6 relay state is info-request (info-request message is sent).";
      }
      enum advertise {
        description
          "DHCPv6 relay state is advertise (advertise message is sent).";
      }
      enum bound {
        description
          "DHCPv6 relay state is bound (normal operation).";
      }
      enum reconfigure {
        description
          "DHCPv6 relay state is reconfigure (reconfigure message is sent).";
      }
      enum expired {
        description
          "DHCPv6 relay state is expired.";
      }
      enum reset {
        description
          "DHCPv6 relay state is reset.";
      }
      enum unknown {
        description
          "DHCPv6 relay state is unknown.";
      }
      enum released {
        description
          "DHCPv6 relay state is released.";
      }
      enum declined {
        description
          "DHCPv6 relay state is declined.";
      }
    }
    description
      "DHCPv6 operational state type.";
  }

  typedef authentication-oper-state {
    type enumeration {
      enum start {
        description
          "Authentication state is start.";
      }
      enum request {
        description
          "Authentication state is request.";
      }
      enum response {
        description
          "Authentication state is response.";
      }
      enum success {
        description
          "Authentication state is success.";
      }
      enum failure {
        description
          "Authentication state is failure.";
      }
      enum initiate {
        description
          "Authentication state is initiate.";
      }
      enum finish {
        description
          "Authentication state is finish.";
      }
      enum logoff {
        description
          "Authentication state is logoff.";
      }
      enum unknown {
        description
          "Authentication state is unknown.";
      }
      enum held {
        description
          "Authentication state is held.";
      }
      enum quiet {
        description
          "Authentication state is quiet.";
      }
      enum offline {
        description
          "Authentication state is offline due to device inactive.";
      }
    }
    description
      "Authentication operational state type.";
  }

  typedef pppoe-oper-state {
    type enumeration {
      enum init {
        description
          "PPPoE state is init (initialization packet is sent).";
      }
      enum offer {
        description
          "PPPoE state is offer (offer packet is received).";
      }
      enum request {
        description
          "PPPoE state is request (request packet is sent).";
      }
      enum session {
        description
          "PPPoE state is session (session has been established).";
      }
      enum termination {
        description
          "PPPoE state is termination (session has terminated).";
      }
      enum unknown {
        description
          "PPPoE state is unknown.";
      }
    }
    description
      "PPPoE operational state type.";
  }

  typedef rogue-onu-state {
    type enumeration {
      enum inactive {
        description
          "No rogue ONU conditions are present/active.";
      }
      enum alarm-active {
        description
          "A rogue ONU condition has been detected and is waiting for operator
           approval before proceeding or another rogue ONU condition is actively
           being addressed and fast recover procedures are pending its completion";
      }
      enum fast-recovery-active {
        description
          "Rogue ONU fast recovery procedures are being run in an attempt to
           quickly correct the rogue condition.";
      }
      enum fast-recovery-complete {
        description
          "Fast recovery actions have completed without being able to resolve the
           rogue condition.";
      }
      enum isolation-active {
        description
          "Rogue ONU fast isolation procedures are being run to locate the ONU(s)
           responsible for the rogue condition.";
      }
      enum investigation-complete {
        description
          "ONU isolation actions have completed, and one or more rogue ONUs
           have been identified.";
      }
      enum remediation-active {
        description
           "Removing the identified rogue ONUs from the PON by issuing serial
            number disable requests.";
      }
    }
    description
      "ONU rogue state.";
  }

  typedef rogue-onu-defect {
    type enumeration {
      enum idle-optical-power {
        description
          "OLT idle receive power defect detection.";
      }
      enum disallowed-error {
        description
          "OLT disallowed defect detection.";
      }
      enum power-variation {
        description
          "ONU power variation defect detection.";
      }
      enum disallowed-onu {
        description
          "ONU disallowed defect detection.";
      }
    }
    description
      "Rogue ONU defect detection types.";
  }

  typedef rogue-onu-command {
    type enumeration {
      enum fast-recovery {
        description
          "Start ONU Fast recovery procedure.";
      }
      enum isolation {
        description
          "Start ONU isolation procedure.";
      }
      enum remediation {
        description
          "Start ONU remediation procedure.";
      }
      enum cancel {
        description
          "Cancel the procedure (if it is running).";
      }
      enum clear {
        description
          "Clear (reset) the initial ONU power variance reading.";
      }
    }
    description
      "Rogue ONU commands.";
  }

  typedef uni-port-speed {
    type enumeration {
      enum auto {
        description
          "Auto-configure speed.";
      }
      enum 10Mb {
        description
          "10 Mbps.";
      }
      enum 100Mb {
        description
          "100 Mbps.";
      }
      enum 1Gb {
        description
          "1 Gbps.";
      }
      enum 2500Mb {
        description
          "2.5 Gbps.";
      }
      enum 5Gb {
        description
          "5 Gbps.";
      }
      enum 10Gb {
        description
          "10 Gbps.";
      }
      enum 25Gb {
        description
          "25 Gbps.";
      }
      enum 40Gb {
        description
          "40 Gbps.";
      }
    }
    description
      "UNI Port speed type.";
  }

  typedef uni-port-oper-speed {
    type enumeration {
      enum 10Mb {
        description
          "10 Mbps.";
      }
      enum 100Mb {
        description
          "100 Mbps.";
      }
      enum 1Gb {
        description
          "1 Gbps.";
      }
      enum 2500Mb {
        description
          "2.5 Gbps.";
      }
      enum 5Gb {
        description
          "5 Gbps.";
      }
      enum 10Gb {
        description
          "10 Gbps.";
      }
      enum 25Gb {
        description
          "25 Gbps.";
      }
      enum 40Gb {
        description
          "40 Gbps.";
      }
      enum unknown {
        description
          "UNI Port speed is unknown.";
      }
    }
    description
      "UNI Port operational speed type.";
  }

  typedef uni-port-duplex {
    type enumeration {
      enum auto {
        description
          "Auto-configure duplex.";
      }
      enum full {
        description
          "Full duplex.";
      }
      enum half {
        description
          "Half duplex.";
      }
    }
    description
      "UNI Port duplex type.";
  }

  typedef uni-port-oper-duplex {
    type enumeration {
      enum full {
        description
          "Full duplex.";
      }
      enum half {
        description
          "Half duplex.";
      }
      enum unknown {
        description
          "UNI Port duplex is unknown.";
      }
    }
    description
      "UNI Port operational duplex type.";
  }

  typedef onu-pluggable-xcvr-type {
    type enumeration {
      enum gigabit-optical-ethernet {
        description
          "Gigabit Ethernet optical IF.";
      }
      enum ethernet-base-t {
        description
          "10/100/1000/2500/5000/10000/25000/40000
           BASE-T Ethernet LAN IF.";
      }
      enum unknown {
        description
          "ONU pluggable transceiver type is unknown.";
      }
    }
    description
      "ONU pluggable transceiver types as defined
       in ITU-T G.988 Table 9.1.5-1.";
  }

  typedef tag-match-vid {
    type uint32 {
      range "0..4094 | 65535";
    }
    description
      "VLAN-ID type used for network tag match fields.
       A value of 0 matches on no VLAN tag or a priority tag.
       A value of 65535 matches on any VID value, no VLAN tag or a priority tag.";
  }

  typedef tag-action {
    type enumeration {
      enum none {
        description
          "No modifications will be made to the matched frame.";
      }
      enum pop {
        description
          "The outermost VLAN tag(s) will be popped (removed). The
           number of tags popped is specified in the tag-action-pop leaf.";
      }
      enum stamp {
        description
          "Stamp the outermost VLAN to either an 802.1ad tag, with the value specified in
           the tag-action-stag leaf, or an 802.1q tag, with the value specified in
           the tag-action-ctag leaf.";
      }
      enum push {
        description
          "Push either a new 802.1ad tag, with the value specified in
           the tag-action-stag leaf, or a new 802.1q tag, with the value specified in
           the tag-action-ctag leaf.";
      }
    }
    description
      "Tag action type.";
  }

  typedef olt-alarm-bit-map {
    type bits {
      bit unreachable {
        position 0;
        description
          "OLT is unreachable.";
      }
      bit firmware-mismatch {
        position 1;
        description
          "Firmware mismatch on OLT.";
      }
      bit rx-los {
        position 2;
        description
          "Receive loss of signal.";
      }
      bit idle-rx-power {
        position 3;
        description
          "Idle receive power is outside of expected tolerance.";
      }
      bit rx-power-low {
        position 4;
        description
          "Receive power is past minimum threshold.";
      }
      bit rx-power-high {
        position 5;
        description
          "Receive power is past maximum threshold.";
      }
      bit tx-power-low {
        position 6;
        description
          "Transmit power is past minimum threshold.";
      }
      bit tx-power-high {
        position 7;
        description
          "Transmit power is past maximum threshold.";
      }
      bit misconfigured {
        position 8;
        description
          "This OLT is misconfigured.";
      }
    }
    description
      "Bit map of alarms currently active on this OLT.";
  }

  typedef onu-alarm-bit-map {
    type bits {
      bit deregistered {
        position 0;
        description
          "ONU is deregistered.";
      }
      bit firmware-mismatch {
        position 1;
        description
          "Firmware mismatch on ONU.";
      }
      bit rx-power-low {
        position 2;
        description
          "Receive power is past minimum threshold.";
      }
      bit rx-power-warning {
        position 3;
        description
          "Receive power is past warning threshold.";
      }
      bit rx-power-high {
        position 4;
        description
          "Receive power is past maximum threshold.";
      }
      bit tx-power-low {
        position 5;
        description
          "Transmit power is past minimum threshold.";
      }
      bit tx-power-warning {
        position 6;
        description
          "Transmit power is past warning threshold.";
      }
      bit tx-power-high {
        position 7;
        description
          "Transmit power is past maximum threshold.";
      }
      bit rogue-onu {
        position 8;
        description
          "This ONU is a confirmed rogue ONU.";
      }
      bit suspect-rogue-onu {
        position 9;
        description
          "This ONU is a suspect rogue ONU.";
      }
      bit physical-equipment-error {
        position 10;
        description
          "Physical equipment error has occured.";
      }
      bit self-test-failure {
        position 11;
        description
          "The self test has failed.";
      }
      bit temperature-yellow {
        position 12;
        description
          "The equipment temperature has turned to yellow.";
      }
      bit temperature-red {
        position 13;
        description
          "The equipment temperature has turned to red.";
      }
      bit signal-fail {
        position 14;
        description
          "The bit-error rate has exceeded signal-fail threshold.";
      }
      bit signal-degrade {
        position 15;
        description
          "The bit-error rate has exceeded signal-degrade threshold.";
      }
      bit laser-bias-current {
        position 16;
        description
          "The laser bias threshold has been exceeded.";
      }
      bit misconfigured {
        position 17;
        description
          "This ONU is misconfigured.";
      }
      bit dying-gasp {
        position 18;
        description
          "This ONU is deregistered due to dying gasp.";
      }
      bit loss-ploam {
        position 19;
        description
          "This ONU is deregistered due to loss of PLOAM.";
      }
      bit loss-of-key-synchronization {
        position 20;
        description
          "This ONU is deregistered due to loss of key synchronization.";
      }
      bit tx-signal-drift {
        position 21;
        description
          "This ONU is deregistered due to loss of transmission signal drift.";
      }
      bit differential-reach {
        position 22;
        description
          "This ONU is deregistered due to differential reach.";
      }
      bit omci-communication-failure {
        position 23;
        description
          "This ONU is deregistered due to OMCI communication failure.";
      }
      bit loss-of-signal {
        position 24;
        description
          "This ONU has detected LOS.";
      }
      bit service-config-failure {
        position 25;
        description
          "This ONU's service config has failed.";
      }
    }
    description
      "Bit map of alarms currently active on this ONU.";
  }

  typedef datalink-alarm-bit-map {
    type bits {
      bit rx-errored-bip-blocks {
        position 0;
        description
          "Received errored bip blocks are exceeding threshold.";
      }
      bit rx-errored-bip-bit {
        position 1;
        description
          "Received errored bip bit are exceeding threshold.";
      }
      bit rx-hec-errors {
        position 2;
        description
          "Received HEC errors are exceeding threshold.";
      }
      bit rx-crc32-drops {
        position 3;
        description
          "Received CRC32 drops are exceeding threshold.";
      }
      bit rx-crc8-errors {
        position 4;
        description
          "Received CRC8 errors are exceeding threshold.";
      }
      bit rx-overflow-drops {
        position 5;
        description
          "Received overflow drops are exceeding threshold.";
      }
      bit rx-too-short-drops {
        position 6;
        description
          "Received too short drops are exceeding threshold.";
      }
      bit rx-too-long-drops {
        position 7;
        description
          "Received too long drops are exceeding threshold.";
      }
      bit rx-fec-uncorrectable-blocks {
        position 8;
        description
          "Received FEC uncorrectable blocks are exceeding threshold.";
      }
      bit misconfigured {
        position 9;
        description
          "This datalink is misconfigured.";
      }
    }
    description
      "Bit map of alarms currently active on this Datalink.";
  }

  typedef uni-port-alarm-bit-map {
    type bits {
      bit loss-of-signal {
        position 0;
        description
          "This UNI Port has detected LOS.";
      }
    }
    description
      "Bit map of alarms currently active on this UNI port.";
  }

  typedef onu-auto-upgrade-trigger {
    type enumeration {
      enum discovery {
        description
          "Automatic ONU firmware upgrade is performed, if required, on initial ONU discovery.";
      }
      enum restart {
        description
          "Automatic ONU firmware upgrade is performed, if required, following ONU restart.";
      }
      enum now {
        description
          "Automatic ONU firmware upgrade is performed, if required, immediately.";
      }
    }
    description
      "Automatic ONU firmware upgrade trigger.";
  }

  typedef olt-oper-state-change-reason {
    type enumeration {
      enum discovery {
        description
          "The OLT oper-state changed due to the OLT being discovered.";
      }
      enum reset {
        description
          "The OLT oper-state changed due to the OLT being reset.";
      }
      enum config {
        description
          "The OLT oper-state changed due to configuration change.";
      }
      enum absent {
        description
          "The OLT oper-state changed due to the OLT being detected as absent.";
      }
      enum out-of-sync {
        description
          "The OLT oper-state changed due to the OLT being detected out of sync.";
      }
    }
    description
      "OLT oper-state change reason.";
  }

  typedef onu-oper-state-change-reason {
    type enumeration {
      enum discovery {
        description
          "The ONU oper-state changed due to the ONU being discovered.";
      }
      enum reset {
        description
          "The ONU oper-state changed due to the ONU being reset.";
      }
      enum config {
        description
          "The ONU oper-state changed due to configuration change.";
      }
      enum absent {
        description
          "The ONU oper-state changed due to the OLT being detected as absent.";
      }
      enum serial-number-not-available {
        description
          "The ONU oper-state changed due to the ONU serial number not being available.";
      }
      enum onu-unprovisioned {
        description
          "The ONU oper-state changed due to the ONU being unprovisioned.";
      }
      enum olt-discovery {
        description
          "The ONU oper-state changed due to the OLT being discovered.";
      }
      enum firmware-activation {
        description
          "The ONU oper-state changed due to ONU firmware activation.";
      }
      enum firmware-invalid {
        description
          "The ONU oper-state changed due to detection of invalid firmware.";
      }
      enum olt-absent {
        description
          "The ONU oper-state changed due to the OLT going absent.";
      }
      enum unresponsive {
        description
          "The ONU oper-state changed due to the ONU being unresponsive.";
      }
      enum deregister-mismatch {
        description
          "The ONU oper-state changed due to a deregister mismatch.";
      }
      enum hardware-triggered {
        description
          "The ONU oper-state changed due to the hardware detecting some error or change in status.";
      }
      enum admission-control {
        description
          "The ONU oper-state changed due to admission-control.";
      }
      enum olt-disabled {
        description
          "The ONU oper-state changed due to the OLT going disabled.";
      }
    }
    description
      "ONU oper-state change reason.";
  }

  typedef uni-port-oper-state-change-reason {
    type enumeration {
      enum config {
        description
          "The UNI port oper-state changed due to configuration change.";
      }
      enum onu-discovery {
        description
          "The UNI port oper-state changed due to discovery of the ONU.";
      }
      enum reset {
        description
          "The UNI port oper-state changed due to reset of hardware.";
      }
      enum alarm-notification {
        description
          "The UNI port oper-state changed due to alarm notification from hardware.";
      }
    }
    description
      "UNI port oper-state change reason.";
  }

  typedef database-access-protocol {
    type enumeration {
      enum ipv4 {
        description
          "Database access over ipv4.";
      }
      enum ipv6 {
        description
          "Database access over ipv6.";
      }
      enum both {
        description
          "Database access over ipv4 and ipv6 both.";
      }
    }
    description
      "Database access protocol types.";
  }

  typedef database-mode {
    type enumeration {
      enum internal {
        description
          "Internal database mode.";
      }
      enum external {
        description
          "External database mode.";
      }
    }
    description
      "Database modes.";
  }

  typedef database-name {
    type string {
      length 1..63;
    }
    description
      "A text string of up to 63 characters, representing the name of a database.";
  }
  grouping tag-match-grouping {
    description
      "Tag match grouping";

    leaf match-stag {
      type pon-ctrl:tag-match-vid;
      mandatory true;      
      description
        "Match on an 802.1ad tag. If present, this must be the first tag on the
         frame.";
    }
    leaf match-ctag-1 {
      type pon-ctrl:tag-match-vid;
      mandatory true;
      description
        "Match on an 802.1q tag. If present, this tag will be the first tag on the
         frame, or will be the first tag after an S-Tag.";
    }
    leaf match-ctag-2 {
      type pon-ctrl:tag-match-vid;
      mandatory true;
      description
        "Match on an 802.1q tag. If present, this tag will be last tag on the
         frame and will be after the S-Tag and C-Tag 1.";
    }
  }

  grouping tag-options-grouping {
    description
      "Tag options grouping";

    leaf tag-action {
      type pon-ctrl:tag-action;
      mandatory true;
      description
        "Tag action to perform on the matched frame.";
    }
    leaf tag-action-pop {
      when "../tag-action = 'pop'";
      type uint8 {
        range "1..3";
      }
      mandatory true;
      description
        "Number of tags to pop.";
    }
    leaf tag-action-stag {
      when "(../tag-action = 'stamp' or ../tag-action = 'push')
            and not(../tag-action-ctag)";
      type pon-ctrl:tag-match-vid;
      must ". != 65535" {
        error-message
          "Illegal value for stag.";
      }
      mandatory true;
      description
        "The 802.1ad tag to stamp or push.";
    }
    leaf tag-action-ctag {
      when "(../tag-action = 'stamp' or ../tag-action = 'push')
            and not(../tag-action-stag)";
      type pon-ctrl:tag-match-vid;
      must ". != 65535" {
        error-message
          "Illegal value for ctag.";
      }
      mandatory true;
      description
        "The 802.1q tag to stamp or push.";
    }
  }

  grouping packet-counters-grouping {
    description
      "Packet counters grouping.";
    leaf rx-frames-total {
      type yang:counter64;
      description
        "Total number of packets received.";
    }
    leaf tx-frames-total {
      type yang:counter64;
      description
        "Total number of packets transmitted.";
    }
    leaf rx-frames-64 {
      type yang:counter64;
      description
        "Count of 64-octet packets received on the interface.";
    }
    leaf tx-frames-64 {
      type yang:counter64;
      description
        "Count of 64-octet packets transmitted on the interface.";
    }
    leaf rx-frames-65-127 {
      type yang:counter64;
      description
        "Count of received packets on the interface with length 65 octets to 127
         octets.";
    }
    leaf tx-frames-65-127 {
      type yang:counter64;
      description
        "Count of transmitted packets on the interface with length 65 octets to 127
         octets.";
    }
    leaf rx-frames-128-255 {
      type yang:counter64;
      description
        "Count of received packets on the interface with length 128 octets to 255
         octets.";
    }
    leaf tx-frames-128-255 {
      type yang:counter64;
      description
        "Count of transmitted packets on the interface with length 128 octets to 255
         octets.";
    }
    leaf rx-frames-256-511 {
      type yang:counter64;
      description
        "Count of received packets on the interface with length 256 octets to 511
         octets.";
    }
    leaf tx-frames-256-511 {
      type yang:counter64;
      description
        "Count of transmitted packets on the interface with length 256 octets to 511
         octets.";
    }
    leaf rx-frames-512-1023 {
      type yang:counter64;
      description
        "Count of received packets on the interface with length 512 octets to 1023
         octets.";
    }
    leaf tx-frames-512-1023 {
      type yang:counter64;
      description
        "Count of transmitted packets on the interface with length 512 octets to 1023
         octets.";
    }
    leaf rx-frames-1024-1518 {
      type yang:counter64;
      description
        "Count of received packets on the interface with length 1024 octets to 1518
         octets.";
    }
    leaf tx-frames-1024-1518 {
      type yang:counter64;
      description
        "Count of transmitted packets on the interface with length 1024 octets to 1518
         octets.";
    }
    leaf rx-frames-1519-plus {
      type yang:counter64;
      description
        "Count of received packets on the interface with length 1519 octets up to the
         maximum size supported by the interface.";
    }
    leaf tx-frames-1519-plus {
      type yang:counter64;
      description
        "Count of transmitted packets on the interface with length 1519 octets up to the
         maximum size supported by the interface.";
    }
  }

  grouping phy-counters-grouping {
    description
      "PHY/MAC counters grouping.";
    leaf rx-octets-total {
      type yang:counter64;
      description
        "Total count of the number of octets that have been received.";
    }
    leaf tx-octets-total {
      type yang:counter64;
      description
        "Total count of the number of octets that have been transmitted.";
    }
    leaf rx-encrypted-segments {
      type yang:counter64;
      description
        "Count of encrypted segments received that were decrypted.";
    }
    leaf tx-encrypted-segments {
      type yang:counter64;
      description
        "Count of encrypted segments transmitted.";
    }
    leaf rx-plain-segments {
      type yang:counter64;
      description
        "Count of unencrypted segments received.";
    }
    leaf tx-plain-segments {
      type yang:counter64;
      description
        "Count of unencrypted segments transmitted.";
    }
    leaf rx-bandwidth-reqs {
      type yang:counter64;
      description
        "Number of bandwidth requests received.";
    }
    leaf tx-bandwidth-reqs {
      type yang:counter64;
      description
        "Number of bandwidth requests transmitted.";
    }
    leaf rx-mpcp-ploam {
      type yang:counter64;
      description
        "Number of PLOAM cells received.";
    }
    leaf tx-mpcp-ploam {
      type yang:counter64;
      description
        "Number of PLOAM cells transmitted.";
    }
    leaf tx-upstream-slots {
      type yang:counter64;
      description
        "Number of upstream slot grants issued (Allocations).";
    }
    leaf rx-filtered-frames {
      type yang:counter64;
      description
        "Count of frames received but filtered (not forwarded).";
    }
    leaf rx-empty-slots {
      type yang:counter64;
      description
        "Count of upstream slots in which data was not present.";
    }
    leaf rx-good-bip-blocks {
      type yang:counter64;
      description
        "Count of BIP blocks received without error.";
    }
    leaf rx-errored-bip-blocks {
      type yang:counter64;
      description
        "Count of BIP blocks received with error.";
    }
    leaf rx-errored-bip-bits {
      type yang:counter64;
      description
        "Count of BIP bits received with error.";
    }
    leaf rx-hec-errors {
      type yang:counter64;
      description
        "Number of errored Header Error Checksums in the XGEM header and GPON
         Framing.";
    }
    leaf rx-crc32-drops {
      type yang:counter64;
      description
        "Count of segments dropped due to CRC-32 error.";
    }
    leaf rx-crc8-errors {
      type yang:counter64;
      description
        "Count of received CRC-8 errors in XGS-PON Allocations/Bandwidth Requests.";
    }
    leaf rx-overflow-drops {
      type yang:counter64;
      description
        "Count of segments dropped due to queue overlfow.";
    }
    leaf rx-too-short-drops {
      type yang:counter64;
      description
        "Count of segments dropped due to being too short.";
    }
    leaf rx-too-long-drops {
      type yang:counter64;
      description
        "Count of segments dropped due to being too long.";
    }
  }

  grouping flooding-counters-grouping {
    description
      "Flooding (broadcast/multicast) counters grouping.";
    leaf tx-frames-total {
      type yang:counter64;
      description
        "Total number of packets transmitted.";
    }
    leaf tx-frames-64 {
      type yang:counter64;
      description
        "Count of 64-octet packets transmitted on the interface.";
    }
    leaf tx-frames-65-127 {
      type yang:counter64;
      description
        "Count of transmitted packets on the interface with length 65 octets to 127
         octets.";
    }
    leaf tx-frames-128-255 {
      type yang:counter64;
      description
        "Count of transmitted packets on the interface with length 128 octets to 255
         octets.";
    }
    leaf tx-frames-256-511 {
      type yang:counter64;
      description
        "Count of transmitted packets on the interface with length 256 octets to 511
         octets.";
    }
    leaf tx-frames-512-1023 {
      type yang:counter64;
      description
        "Count of transmitted packets on the interface with length 512 octets to 1023
         octets.";
    }
    leaf tx-frames-1024-1518 {
      type yang:counter64;
      description
        "Count of transmitted packets on the interface with length 1024 octets to 1518
         octets.";
    }
    leaf tx-frames-1519-plus {
      type yang:counter64;
      description
        "Count of transmitted packets on the interface with length 1519 octets up to the
         maximum size supported by the interface.";
    }
    leaf tx-frames-unicast {
      type yang:counter64;
      description
        "Total number of unicast packets transmitted.";
    }
    leaf tx-frames-multicast {
      type yang:counter64;
      description
        "Total number of multicast packets transmitted.";
    }
    leaf tx-frames-broadcast {
      type yang:counter64;
      description
        "Total number of broadcast packets transmitted.";
    }
    leaf tx-octets-unicast {
      type yang:counter64;
      description
        "Total number of unicast octets transmitted.";
    }
    leaf tx-octets-multicast-broadcast {
      type yang:counter64;
      description
        "Total number of multicast/broacast octets transmitted.";
    }
    leaf tx-octets-control {
      type yang:counter64;
      description
        "Total number of control octets transmitted.";
    }
    leaf tx-octets-encrypted {
      type yang:counter64;
      description
        "Total number of encrypted octets transmitted.";
    }
    leaf tx-octets-plain {
      type yang:counter64;
      description
        "Total number of plain octets transmitted.";
    }
    leaf tx-octets-total {
      type yang:counter64;
      description
        "Total number of octets transmitted.";
    }
  }

  grouping uni-port-packet-counters-grouping {
    description
      "UNI Port packet counters grouping.";
    leaf ds-octets-total {
      type yang:counter64;
      description
        "Total number of downstream packets received.";
    }
    leaf us-octets-total {
      type yang:counter64;
      description
        "Total number of upstream packets received.";
    }
    leaf ds-frames-total {
      type yang:counter64;
      description
        "Total number of downstream packets received.";
    }
    leaf us-frames-total {
      type yang:counter64;
      description
        "Total number of upstream packets received.";
    }
    leaf ds-frames-63-less {
      type yang:counter64;
      description
        "Count of downstream packets received with a length of 63 octets or less.";
    }
    leaf us-frames-63-less {
      type yang:counter64;
      description
        "Count of upstream packets received with a length of 63 octets or less.";
    }
    leaf ds-frames-64 {
      type yang:counter64;
      description
        "Count of downstream packets received with a length of 64 octets.";
    }
    leaf us-frames-64 {
      type yang:counter64;
      description
        "Count of upstream packets received with a length of 64 octets.";
    }
    leaf ds-frames-65-127 {
      type yang:counter64;
      description
        "Count of downstream packets received with length 65 octets to 127 octets.";
    }
    leaf us-frames-65-127 {
      type yang:counter64;
      description
        "Count of upstream packets received with length 65 octets to 127 octets.";
    }
    leaf ds-frames-128-255 {
      type yang:counter64;
      description
        "Count of downstream packets received with length 128 octets to 255 octets.";
    }
    leaf us-frames-128-255 {
      type yang:counter64;
      description
        "Count of upstream packets received with length 128 octets to 255 octets.";
    }
    leaf ds-frames-256-511 {
      type yang:counter64;
      description
        "Count of downstream packets received with length 256 octets to 511 octets.";
    }
    leaf us-frames-256-511 {
      type yang:counter64;
      description
        "Count of upstream packets received with length 256 octets to 511 octets.";
    }
    leaf ds-frames-512-1023 {
      type yang:counter64;
      description
        "Count of downstream packets received with length 512 octets to 1023 octets.";
    }
    leaf us-frames-512-1023 {
      type yang:counter64;
      description
        "Count of upstream packets received with length 512 octets to 1023 octets.";
    }
    leaf ds-frames-1024-1518 {
      type yang:counter64;
      description
        "Count of downstream packets received with length 1024 octets to 1518 octets.";
    }
    leaf us-frames-1024-1518 {
      type yang:counter64;
      description
        "Count of upstream packets received with length 1024 octets to 1518 octets.";
    }
    leaf ds-frames-1519-plus {
      type yang:counter64;
      description
        "Count of downstream packets received with length 1519 octets up to the
         maximum size supported by the UNI Port.";
    }
    leaf us-frames-1519-plus {
      type yang:counter64;
      description
        "Count of upstream packets received with length 1519 octets up to the
         maximum size supported by the UNI Port.";
    }
  }

  grouping relay-counters-grouping {
    description
      "DHCP relay packet counters grouping.";
    leaf rx-frames-relay-dhcp {
      type yang:counter64;
      description
        "Total number of DHCP packets received.";
    }
    leaf tx-frames-relay-dhcp {
      type yang:counter64;
      description
        "Total number of DHCP packets transmitted.";
    }
    leaf rx-frames-relay-eapol {
      type yang:counter64;
      description
        "Total number of EAPoL packets received.";
    }
    leaf tx-frames-relay-eapol {
      type yang:counter64;
      description
        "Total number of EAPoL packets transmitted.";
    }
    leaf relay-last-clear-time {
      type string;
      description
        "Time when the statistics were last cleared.";
    }
    leaf rx-pon-drops-frames-dhcp {
      type yang:counter64;
      description
        "Total number of DHCP packets dropped frames on DHCP.";
    }
    leaf rx-nni-drops-frames-dhcp {
      type yang:counter64;
      description
        "Total number of DHCP packets dropped frames on DHCP.";
    }
    leaf rx-pon-drops-frames-eapol {
      type yang:counter64;
      description
        "Total number of EAPoL packets dropped frames on EAPoL.";
    }
    leaf rx-nni-drops-frames-eapol {
      type yang:counter64;
      description
        "Total number of EAPoL packets dropped frames on EAPoL.";
    }
    leaf relay-time {
      type string;
      description
        "Time when the statistics were last collected.";
    }
  }

  grouping dhcpv6-counters-grouping {
    description
      "DHCPv6 packet counters grouping.";
    leaf rx-frames-dhcpv6 {
      type yang:counter64;
      description
        "Total number of DHCPv6 packets received.";
    }
    leaf tx-frames-dhcpv6 {
      type yang:counter64;
      description
        "Total number of DHCPv6 packets transmitted.";
    }
    leaf dhcpv6-last-clear-time {
      type string;
      description
        "Time when the statistics were last cleared.";
    }
    leaf rx-pon-drops-frames-dhcpv6 {
      type yang:counter64;
      description
        "Total number of DHCPv6 packets dropped frames on PON.";
    }
    leaf rx-nni-drops-frames-dhcpv6 {
      type yang:counter64;
      description
        "Total number of DHCPv6 packets dropped frames on NNI.";
    }
    leaf dhcpv6-time {
      type string;
      description
        "Time when the statistics were last collected.";
    }
  }

  grouping auth-counters-grouping {
    description
      "Authentication packet counters grouping.";
    leaf rx-frames-auth-radius {
      type yang:counter64;
      description
        "Total number of packets received for RADIUS authentication.";
    }
    leaf tx-frames-auth-radius {
      type yang:counter64;
      description
        "Total number of packets transmitted for RADIUS authentication.";
    }
    leaf rx-frames-auth-eapol {
      type yang:counter64;
      description
        "Total number of EAPoL packets received for RADIUS authentication.";
    }
    leaf tx-frames-auth-eapol {
      type yang:counter64;
      description
        "Total number of EAPoL packets transmitted for RADIUS authentication.";
    }
    leaf auth-last-clear-time {
      type string;
      description
        "Time when the statistics were last cleared.";
    }
    leaf auth-time {
      type string;
      description
        "Time when the statistics were last collected.";
    }
  }

  grouping pppoe-counters-grouping {
    description
      "PPPoE packet counters grouping.";
    leaf rx-frames-pppoe {
      type yang:counter64;
      description
        "Total number of PPPoE packets received.";
    }
    leaf tx-frames-pppoe {
      type yang:counter64;
      description
        "Total number of PPPoE packets transmitted.";
    }
    leaf pppoe-last-clear-time {
      type string;
      description
        "Time when the statistics were last cleared.";
    }
    leaf rx-pon-drops-frames-pppoe {
      type yang:counter64;
      description
        "Total number of PPPoE packets dropped frames on PON.";
    }
    leaf rx-nni-drops-frames-pppoe {
      type yang:counter64;
      description
        "Total number of PPPoE packets dropped frames on NNI.";
    }
    leaf pppoe-time {
      type string;
      description
        "Time when the statistics were last collected.";
    }
  }

  grouping dhcp-grouping {
    description
      "Dynamic host configuration protocol grouping.";
    leaf dhcp-circuit-id {
      type pon-ctrl:pon-relay-attribute-string;
      description
        "Dynamic host configuration protocol circuit-id.";
    }
    leaf dhcp-remote-id {
      type pon-ctrl:pon-relay-attribute-string;
      description
        "Dynamic host configuration protocol remote-id.";
    }
    leaf dhcp-enterprise-number {
      when "../dhcp-remote-id";
      type uint32;
      description
        "Dynamic host configuration protocol enterprise-number.";
    }
  }

  grouping radius-grouping {
    description
      "RADIUS grouping.";
    leaf NAS-identifier {
      type pon-ctrl:pon-relay-attribute-string;
      description
        "Network access server identifier.";
    }
    leaf NAS-port-id {
      type pon-ctrl:pon-relay-attribute-string;
      description
        "Network access server port identifier.";
    }
    leaf NAS-user-name-override {
      type pon-ctrl:pon-relay-attribute-string;
      default "Default";
      description
        "Network access server user name override.";
    }
  }

  grouping control-plane-processing {
    description
      "Enable or disable protocol control plane processing.";
    leaf dhcp-enable {
      type ciena:admin-state;
      default enabled;
      description
        "Enable or disable DHCPv4 and DHCPv6 L2 relay processing.";
    }
    leaf auth-enable {
      type ciena:admin-state;
      default enabled;
      description
        "Enable or disable RADIUS authenticator processing.";
    }
    leaf pppoe-enable {
      type ciena:admin-state;
      default enabled;
      description
        "Enable or disable PPPoE intermediate agent processing.";
    }
  }

  grouping control-plane-processing-state {
    description
      "Control plane processing state.";
    leaf auth-enable-state {
      type ciena:admin-state;
      description
        "State of RADIUS authenticator processing.";
    }
    leaf pppoe-enable-state {
      type ciena:admin-state;
      description
        "State of PPPoE intermediate agent processing.";
    }
  }

  grouping pon-ctrl-radius-server-grouping {
    description
      "RADIUS Server.";
    list radius-server-address {
      key "host port";
       description
        "RADIUS server host and port.";
      leaf host {
        type inet:host;
        description
          "RADIUS server host address.";
      }
      leaf port {
        type inet:port-number;
        description
          "RADIUS server port.";
      }
      leaf priority {
        type uint8{
          range "1..3";
        }
        default 3;
        description
          "The priority of the RADIUS server IP address.";
      }
    }
  }

  grouping pppoe-grouping {
    description
      "PPPoE grouping.";
    leaf pppoe-circuit-id {
      type pon-ctrl:pon-relay-attribute-string;
      description
        "PPPoE circuit-id.";
    }
    leaf pppoe-remote-id {
      type pon-ctrl:pon-relay-attribute-string;
      description
        "PPPoE remote-id.";
    }
  }

  grouping rogue-onu-enable-grouping {
    description
      "Rogue ONU enable grouping.";

    leaf rogue-onu-enable {
      type boolean;
      default false;
      description
        "If true, detection of a rogue ONU condition is reported.
         Corrective action will be performed if fast-recovery, isolate or
         remediate is enabled.";
    }
    leaf rogue-onu-fast-recovery-enable {
      type boolean;
      default false;
      description
        "If true, detection of a rogue ONU condition will immediately begin to perform
         a series of operations to attempt to clear the condition. Typically, this is
         a reset of the suspected set of rogue ONUs and the OLT as well.";
    }
    leaf rogue-onu-isolate-enable {
      type boolean;
      default false;
      description
        "If true, when the rogue ONU isolation steps complete, action is taken to
         immediately begin to perform the ONU isolation sequences for the condition in
         order to determine which, if any, ONUs are the cause.";
    }
    leaf rogue-onu-remediate-enable {
      type boolean;
      default false;
      description
        "If true, when the rogue ONU isolation steps complete, action is taken to
         immediately begin to perform the ONU remediation sequences for the
         condition in order to determine which, if any, ONUs are the cause.
         Remediate does not apply to rogue ONU disallowed.";
    }
  }

  grouping rogue-onu-olt-action-grouping {
    description
      "Rogue ONU OLT action grouping defines the actions take by the OLT to
       correct/isolate an ONU that has been detected as a rogue ONU.";

    leaf rogue-onu-olt-action-reset-all-onus {
      type boolean;
      default false;
      status deprecated;
      description
        "If true, the fast recovery procedures will issue a reset request to
         all ONUs in an attempt to resolve the issue.";
    }
    leaf rogue-onu-olt-action-reset-olt {
      type boolean;
      default false;
      status deprecated;
      description
        "If true, the fast recovery procedures will issue a reset request to
         the OLT in an attempt to resolve the issue.";
    }
    leaf rogue-onu-olt-action-disable-all-serial-numbers {
      type boolean;
      default false;
      status deprecated;
      description
        "If true, the isolation procedures will issue a disable all ONU
         serial numbers and begin to enable ONUs selectively in an
         attempt to isolate the condition to one or more ONUs.";
    }
    leaf rogue-onu-olt-action-disable-serial-number {
      type boolean;
      default false;
      status deprecated;
      description
        "If true, the remediation procedures will issue disable serial
         number request to all identified rogue ONUs.";
    }
  }

  grouping rogue-onu-olt-disallowed-action-grouping {
    description
      "Rogue ONU OLT action grouping defines the actions take by the OLT to
       correct/isolate an ONU that has been detected as a rogue ONU.";

    leaf rogue-onu-action-reset-all-onus {
      type boolean;
      default false;
      description
        "If true, the fast recovery procedures will issue a reset request to
         all ONUs in an attempt to resolve the issue.";
    }
    leaf rogue-onu-action-reset-olt {
      type boolean;
      default false;
      description
        "If true, the fast recovery procedures will issue a reset request to
         the OLT in an attempt to resolve the issue.";
    }
    leaf rogue-onu-action-disable-all-serial-numbers {
      type boolean;
      default false;
      description
        "If true, the isolation procedures will issue a disable all ONU
         serial numbers and begin to enable ONUs selectively in an
         attempt to isolate the condition to one or more ONUs.";
    }
    leaf rogue-onu-action-disable-serial-number {
      type boolean;
      default false;
      description
        "If true, the remediation procedures will issue disable serial
         number request to all identified rogue ONUs.";
    }
  }

  grouping rogue-onu-action-grouping {
    description
      "ONU Rogue action grouping defines the actions taken by the ONU
       to correct/isolate itself when detected to be a rogue ONU.";

    leaf rogue-onu-action-reset-onu {
      type boolean;
      default false;
      status deprecated;
      description
        "If true, the fast recovery procedure will issue a reset request to
         the ONU in an attempt to resolve the issue.
         This attribute was never used.";
    }
    leaf rogue-onu-action-reset-olt {
      type boolean;
      default false;
      status deprecated;
      description
        "If true, the fast recovery procedures will issue a reset request to
         the OLT in an attempt to resolve the issue.
         This attribute was never used.";
    }
    leaf rogue-onu-positive-rx-threshold {
      type cntypes:decimal-2-dig-small;
      units dBm;
      default 3;
      status deprecated;
      description
        "Threshold above the initial optical value at which a rogue ONU
         condition is raised.";
    }
    leaf rogue-onu-negative-rx-threshold {
      type cntypes:decimal-2-dig-small;
      units dBm;
      default -30;
      status deprecated;
      description
        "Lower optical threshold at which a rogue ONU condition is
         raised.";
    }
    leaf rogue-onu-action-sample-size {
      type uint8 {
         range "3..10";
      }
      default 5;
      status deprecated;
      description
        "Number of samples to use during calculation of whether the
         repeated occurrence threshold has been reached.";
    }
    leaf rogue-onu-action-repeat-threshold {
      type uint8 {
         range "2..9";
      }
      default 3;
      status deprecated;
      description
        "Number of samples allowed above threhsold before ONU rogue state
         is advanced to alarm condition.";
    }
  }

  grouping rogue-onu-olt-idle-power-action-grouping {
    description
      "ONU Rogue action grouping defines the actions taken by the ONU
       to correct/isolate itself when detected to be a rogue ONU.";

    leaf rogue-onu-action-reset-all-onus {
      type boolean;
      default false;
      description
        "If true, the fast recovery procedure will issue a reset request to
         the ONU(s) in an attempt to resolve the issue.";
    }
    leaf rogue-onu-action-reset-olt {
      type boolean;
      default false;
      description
        "If true, the fast recovery procedures will issue a reset request to
         the OLT in an attempt to resolve the issue.
         This attribute was never used.";
    }
    leaf rogue-onu-action-disable-all-serial-numbers {
      type boolean;
      default false;
      description
        "If true, the isolation procedures will issue a disable all ONU
         serial numbers and begin to enable ONUs selectively in an
         attempt to isolate the condition to one or more ONUs.";
    }
    leaf rogue-onu-action-disable-serial-number {
      type boolean;
      default false;
      description
        "If true, the remediation procedures will issue disable serial
         number request to all identified rogue ONUs.";
    }
    leaf rogue-onu-action-min-idle-receive-power-threshold {
      type cntypes:decimal-2-dig-small {
        range "-40..-30";
      }
      units dBm;
      default -35.0;
      description
        "Threshold for minimum receive idle power.";
    }
  }

  grouping rogue-onu-power-variation-action-grouping {
    description
      "ONU Rogue action grouping defines the actions taken by the ONU
       to correct/isolate itself when detected to be a rogue ONU.";

    leaf rogue-onu-action-reset-onu {
      type boolean;
      default false;
      description
        "If true, the fast recovery procedure will issue a reset request to
         the ONU in an attempt to resolve the issue.";
    }
    leaf rogue-onu-action-disable-serial-number {
      type boolean;
      default false;
      description
        "If true, the remediation procedures will issue disable serial
         number request to all identified rogue ONUs.";
    }
    leaf rogue-onu-positive-gain-threshold {
      type cntypes:decimal-2-dig-small {
        range "0..10";
      }
      units dBm;
      default 3;
      description
        "Threshold above the initial optical value at which a rogue ONU
         condition is raised.";
    }
    leaf rogue-onu-negative-threshold {
      type cntypes:decimal-2-dig-small {
        range "-40..0";
      }
      units dBm;
      default -30;
      description
        "Lower optical threshold at which a rogue ONU condition is
         raised.";
    }
  }

  grouping rogue-onu-disallowed-action-grouping {
    description
      "ONU Rogue action grouping defines the actions taken by the ONU
       to correct/isolate itself when detected to be a rogue ONU.";

    leaf rogue-onu-action-reset-onu {
      type boolean;
      default false;
      description
        "If true, the fast recovery procedure will issue a reset request to
         the ONU in an attempt to resolve the issue.";
    }
    leaf rogue-onu-action-disable-serial-number {
      type boolean;
      default false;
      description
        "If true, the remediation procedures will issue disable serial
         number request to all identified rogue ONUs.";
    }
    leaf rogue-onu-action-history-size {
      type uint8 {
         range "2..10";
      }
      default 10;
      description
        "Number of samples used for analysis.";
    }
    leaf rogue-onu-action-sample-size {
      type uint8 {
         range "2..10";
      }
      default 3;
      description
        "Number of samples to use during calculation of whether the
         repeated occurrence threshold has been reached.";
    }
    leaf rogue-onu-action-repeat-threshold {
      type uint16 {
         range "0 | 30..65535";
      }
      default 300;
      description
       "Average delta threshold (seconds) between occurrences
        If the average delta is less than or equal to this threshold,
        the Disallowed ONU condition will be escalated to the OLT.";
    }
  }

  grouping rogue-onu-state-grouping {
    description
      "State data related to a rogue ONU.";

    leaf state {
      type pon-ctrl:rogue-onu-state;
      status deprecated;
      description
        "Rogue state of this ONU.";
    }
    leaf alarms {
      type onu-alarm-bit-map;
      status deprecated;
      description
        "Bit map of rogue alarm conditions currently active on this ONU.";
    }
    leaf occurrences {
      type uint32;
      status deprecated;
      description
        "Number of times rogue ONU condition has been detected and a transition to
         active-alarm occurred.";
    }
    leaf last-occurrence {
      type string;
      status deprecated;
      description
        "The last time a new ONU became a suspect or identified as a rogue.";
    }
    leaf escalated {
      type boolean;
      status deprecated;
      description
        "True if the last disallowed ONU condition is escalated to the
         OLT level for further processing.";
    }
    leaf last-idle-rx-power-sample {
      type cntypes:decimal-2-dig-small;
      units dBm;
      status deprecated;
      description
        "Value of the last sampled idle rx power.";
    }
    leaf initial-rx-power {
      type cntypes:decimal-2-dig-small;
      units dBm;
      status deprecated;
      description
        "Initial power threshold value (dBm) measured for this ONU.";
    }
    leaf deregistered-event {
      type boolean;
      status deprecated;
      description
        "True if the ONU was deregistered due to excessive errors.";
    }
    leaf rx-errored-bip-blocks {
      type yang:counter64;
      status deprecated;
      description
        "Count of BIP blocks received with error.";
    }
    leaf rx-hec-errors {
      type yang:counter64;
      status deprecated;
      description
        "Number of errored Header Error Checksums in the XGEM header and GPON
         Framing.";
    }
    leaf rx-crc32-drops {
      type yang:counter64;
      status deprecated;
      description
        "Count of segments dropped due to CRC-32 error.";
    }
  }

  grouping rogue-onu-state-grouping2 {
    description
      "Common state data related to a Rogue ONU defect.";

    leaf state {
      type pon-ctrl:rogue-onu-state;
      description
        "Rogue ONU state for the associated Rogue ONU defect.";
    }
    leaf occurrences {
      type uint32;
      description
        "Number of times rogue ONU defect has been detected and a transition to
         active-alarm occurred.";
    }
    leaf last-occurrence {
      type string;
      description
        "The last time the rogue ONU defect was detected and a transition to
         active-alarm occurred.";
    }
    leaf last-results {
      type string;
      description
         "TBD";
    }
    leaf-list suspects {
      type pon-ctrl:name-string;
      description
        "Serial numbers of ONUs currently suspected of causing the rogue ONU defect.";
    }
    leaf-list rogues {
      type pon-ctrl:name-string;
      description
        "Serial numbers of ONUs identedfied as a cause for the rogue ONU defect.";
    }
  }

  grouping rogue-onu-olt-idle-power-state-grouping {
    description
      "State data related to an OLT Rogue ONU Idle Power defect.";

    uses rogue-onu-state-grouping2;

    leaf idle-rx-power-sample {
      type cntypes:decimal-2-dig-small;
      units dBm;
      description
        "Value of the sampled idle RX power that resulted in the defect.";
    }
  }

  grouping rogue-onu-olt-disallowed-error-state-grouping {
    description
      "State data related to an OLT Rogue ONU Disallowed Error.";

    uses rogue-onu-state-grouping2;
  }

  grouping rogue-onu-disallowed-onu-state-grouping {
    description
      "State data related to an ONU Disallowed ONU defect.";

    uses rogue-onu-state-grouping2;

    leaf escalated {
      type boolean;
      description
        "True if the last disallowed ONU condition is escalated to the
         OLT level for further processing.";
    }
    leaf-list samples {
      type uint64;
      description
        "Epoch times of when the Disallowed ONU defect was detected";
    }
  }

  grouping rogue-onu-power-variation-state-grouping {
    description
      "State data related to an ONU Power Variation defect.";

    uses rogue-onu-state-grouping2;

    leaf initial-rx-power {
      type cntypes:decimal-2-dig-small;
      units dBm;
      description
        "Initial power threshold value (dBm) measured for this ONU.";
    }
  }

  grouping onu-upgrade-grouping {
    description
      "ONU firmware upgrade grouping.";
    list onu-firmware-upgrade-mapping  {
      key "model";
      description
        "An ONU model number.";
      leaf model {
        type pon-ctrl:name-string;
        description
          "Name of the ONU model number. ONUs that match this model will be
           auto-upgraded to the expected firmware version, if enabled.";
      }
      leaf expected-firmware-version {
        type string;
        mandatory true;
        description
          "Expected firmware version of this ONU model. This will be used for
           auto-upgrades for this ONU model. Note, this will only take effect when
           the 'onu-auto-upgrade' option is enabled on the OLT as well as globally.";
      }
      leaf firmware-file-name {
        type pon-ctrl:name-string;
        must "../expected-firmware-version"
        {
          error-message
            "Expected firmware version for this firmware file must be configured.";
        }
        description
          "Name of the firmware file to use when auto-upgrading this ONU model.
           Note, this will only take effect when the 'onu-auto-upgrade' option
           is enabled on the OLT.";
      }
    }
    leaf onu-allow-downgrade {
      type ciena:admin-state;
      default disabled;
      description
        "Enable or disable to allow/disallow ONUs to be auto-downgraded from
         their active firmware version.";
    }
    leaf onu-auto-upgrade {
      type ciena:admin-state;
      default disabled;
      description
        "Enable or disable automatic ONU upgrades on the system.";
    }
  }

  container pon-ctrl {
    description
      "PON configuration data.";
    container global {
      description
        "PON global configuration data.";

      uses rogue-onu-enable-grouping;
      uses rogue-onu-olt-action-grouping;
      uses rogue-onu-action-grouping;
      uses onu-upgrade-grouping;

      leaf rogue-onu-mass-onu-deregistration-event {
        type boolean;
        default false;
        status deprecated;
        description
          "Trigger rogue ONU process immediately on detection of
           mass ONU deregistration event.";
      }
      leaf rogue-onu-hec-error-threshold {
        type yang:counter64;
        default 0;
        status deprecated;
        description
          "When set to non-zero value, HEC errors are used
           as part of rogue ONU analysis. This is now determined
           internally.";
      }
      leaf rogue-onu-crc32-error-threshold {
        type yang:counter64;
        default 0;
        status deprecated;
        description
          "When set to non-zero value, CRC32 errors are used
           as part of rogue ONU analysis. This is now determinded
           internally.";
      }
      leaf rogue-onu-bip-error-threshold {
        type yang:counter64;
        default 0;
        status deprecated;
        description
          "When set to non-zero value, BIP errors are used
           as part of rogue ONU analysis. This is now determined
           internally.";
      }
      leaf onu-serial-number-config-change-enable {
        type boolean;
        default true;
        description
          "Indicates if the ONU serial number is allowed to
           be modified.";
      }
      leaf rogue-onu-action-min-idle-receive-power-threshold {
        type cntypes:decimal-2-dig-small {
          range "-40..0";
        }
        units dBm;
        default -35.0;
        description
          "Threshold for minimum receive idle power.";
      }
      leaf rogue-onu-action-disable-serial-number {
        type boolean;
        default false;
        description
          "If true, the remediation procedures will issue disable serial
           number to identified rogue ONUs.";
      }
      leaf rogue-onu-action-history-size {
        type uint8 {
           range "2..10";
        }
        default 10;
        description
          "Number of samples used for analysis.";
      }
      container rogue-olt-disallowed-error {
        description
          "Global rogue ONU configuration for OLT disallowed error detection.";
        uses rogue-onu-enable-grouping;
        uses rogue-onu-olt-disallowed-action-grouping;
      }
      container rogue-olt-idle-power {
        description
          "Global rogue ONU configuration for OLT idle receive power detection.";
        uses rogue-onu-enable-grouping;
        uses rogue-onu-olt-idle-power-action-grouping;
      }
      container rogue-onu-power-variation {
        description
          "Global rogue ONU configuration for ONU power variation detection.";
        uses rogue-onu-enable-grouping;
        uses rogue-onu-power-variation-action-grouping;
      }
      container rogue-onu-disallowed {
        description
          "Global rogue ONU configuration for ONU disallowed detection.";
        uses rogue-onu-enable-grouping;
        uses rogue-onu-disallowed-action-grouping;
      }
      container database {
        description
          "Database configuration for external access.";
        leaf access-control {
          type database-access-protocol;
          description
            "Protocol type used to access the database.";
        }
        leaf database-mode {
          when "../../olt-management-interface";
          type database-mode;
          default internal;
          description
            "Specified whether an internal or external database is used.
             Setting to 'external' requires the olt-management-interface to be configured.";
        }
        leaf auth-enable {
          when "../auth-username and ../auth-password";
          type boolean;
          default false;
          description
            "Enable authentication for the connection to the external database.
             Setting to 'true' requires the auth-username and auth-password to be configured.";
        }
        leaf auth-db-name {
          type database-name;
          default "tibit_users";
          description
            "External database name for the authentication database. Only applies when ‘auth-enable’ is true.";
        }
        leaf auth-username {
          type name-string;
          description
            "External database username for the authentication database. Only applies when ‘auth-enable’ is true.";
        }
        leaf auth-password {
          ncx:password;
          type name-string;
          description
            "External database password for the authentication database. Only applies when ‘auth-enable’ is true.";
        }
        leaf compression {
          type boolean;
          default false;
          description
            "Enable compression on the connection to the external database server.";
        }
        leaf db-name {
          type database-name;
          default "tibit_pon_controller";
          description
            "Name of the PON Controller database that contains the Controller, OLT, and ONU device configuration and state.";
        }
        leaf encryption-enable {
          when "../ca-cert-name";
          type boolean;
          default false;
          description
            "Enable TLS encryption for the connection to the external database.
             Setting to 'true' requires the ca-cert-name to be configured.";
        }
        leaf ca-cert-name {
          type string;
          description
            "Name of the CA certificate used to encrypt the connection to the external database.";
        }
        leaf replica-set-enable {
          when "../replica-set-name";
          type boolean;
          default false;
          description
            "Enables connecting to an external database replica set for purposes of redundancy.
             Setting to 'true' requires the replica-set-name to be configured.";
        }
        leaf replica-set-name {
          type name-string;
          description
            "External database replica set name. This field is required when replica-set-enable is set to ‘true’.";
        }
        list database-server-address {
          key "host port";
          description
            "Database server host and port.";
          leaf host {
            type inet:host;
            description
              "IP address or hostname of the external database server.";
          }
          leaf port {
            type inet:port-number;
            description
              "TCP port number the external database server is listening on.";
          }
        }
      }
      leaf olt-management-interface {
        type pon-ctrl:interface-ref;
        must "/oc-if:interfaces/oc-if:interface[name = current()]" +
             "/oc-if:config/cn-if:type = 'ip'" {
          error-message
            "Referenced interface must be of type 'ip'.";
        }
        description
          "Reference to the L3 interface on which OLTs are to be managed when using an external database.";
      }
    }
    container radius-servers {
      description
        "The configuration data for all RADIUS servers.";
      list radius-server {
        key "name";
        description
          "An RADIUS server on the system.";
        leaf name {
          type pon-ctrl:name-string;
          description
            "Name of the RADIUS Server.";
        }
        leaf management-interface {
          type pon-ctrl:interface-ref;
          must "/oc-if:interfaces/oc-if:interface[name = current()]" +
               "/oc-if:config/cn-if:type = 'ip'" {
            error-message
              "Referenced interface must be of type 'ip'.";
          }
          mandatory true;
          description
            "Reference to the L3 interface on which this OLT is to be
             managed.";
        }
        leaf shared-secret {
          ncx:password;
          type pon-ctrl:pon-relay-attribute-string;
          description
            "Shared secret string.";
        }
        leaf revive-interval {
          type uint32{
            range "0 | 5..65535";
          }
          units "seconds";
          default 120;
          description
            "The period (in seconds) before changing operational
             state of a RADIUS server in the 'Down' state to 'Up'.
             Setting revive-interval to a value of 0 diables the
             feature. The revive-interval is only used when
             User Access Monitoring is disabled.";
        }
        leaf failure-threshold {
          type uint32{
            range "2..65535";
          }
          default 4;
          description
            "The maximum number of failed authentications
             before changing the RADIUS server operational
             state to 'Down' and switching to an alternate
             RADIUS server if configured.";
        }
        leaf uam-username {
          type pon-ctrl:pon-relay-attribute-string;
          default "username";
          description
            "The 802.1x username to be used in the test
             authentication messages.";
        }
        leaf uam-enable {
          type boolean;
          default false;
          description
            "Used to enable and disable user access monitoring
             if set to 'true', test authentication messages will
             be sent to RADIUS servers in the 'Down' operational
             state to check the server's current status.";
        }
        leaf uam-recover-threshold {
          type uint32{
            range "2..65535";
          }
          default 2;
          description
            "The number of authentication responses that
             must be received before changing the RADIUS
             server operational state to 'Up'.";
        }
        leaf uam-check-interval {
          type uint32{
            range "5..65535";
          }
          units "seconds";
          default 60;
          description
            "The period (in seconds) between test authentication
             methods sent to RADIUS servers in the 'Down' operational
             state.";
        }
        uses pon-ctrl-radius-server-grouping;
        leaf failure-period {
          type uint32{
            range "0..65535";
          }
          units "seconds";
          default 0;
          description
            "The period (in seconds) where authentication failures are recorded.
             Once the time period ends, authentication failure counts will be cleared.";
        }
        leaf held-period {
          type uint32{
            range "0..65535";
          }
          units "seconds";
          default 0;
          description
            "The number of seconds to wait before retrying after
             a failed authentication attempt.";
        }
        leaf max-retry {
          type uint32{
            range "0..65535";
          }
          default 0;
          description
            "The number of authentication attempts to make before held period is entered.";
        }
        leaf quiet-period {
          type uint32{
            range "0..65535";
          }
          units "seconds";
          default 0;
          description
            "The number of seconds in which a user cannot
             attempt authentication.";
        }
      }
    }

    container olts {
      description
        "The configuration data for all OLTs.";
      list olt {
        key "name";
        unique "port-id";
        description
          "An OLT on the system.";
        leaf name {
          type pon-ctrl:name-string;
          description
            "Name of the OLT.";
        }
        leaf admin-state {
          type ciena:admin-state;
          default enabled;
          description
            "Enable or disable the OLT.";
        }
        leaf mac-address {
          type yang:mac-address;
          must "count(../port-id)=0" {
            error-message
              "An OLT can only be configured by port ID or MAC address, but not both.";
          }
          description
            "The MAC address of the OLT.";
        }
        leaf port-id {
          type cntypes:name-string;
          must "count(../mac-address)=0" {
            error-message
              "An OLT can only be configured by port ID or MAC address, but not both.";
          }
          description
            "The port ID of where the OLT is plugged in.";
        }
        leaf management-interface {
          type pon-ctrl:interface-ref;
          must "/oc-if:interfaces/oc-if:interface[name = current()]" +
               "/oc-if:config/cn-if:type = 'ip'" {
            error-message
              "Referenced interface must be of type 'ip'.";
          }
          mandatory true;
          description
            "Reference to the L3 interface on which this OLT is to be
             managed.";
        }
        leaf pon-mode {
          type pon-ctrl:pon-mode;
          default xgs-pon;
          description
            "The PON mode this OLT will operate in.";
        }
        leaf auto-assigned-ids {
          type ciena:admin-state;
          default enabled;
          description
            "Enable or disable automatic ONU-ID and ALLOC-ID assignment on the OLT. Only valid in XGS-PON mode.
             Note, when enabled the OLT will automatically register ONUs discovered on the PON.";
        }
        leaf auto-onu-upgrade {
          type ciena:admin-state;
          default disabled;
          status deprecated;
          description
            "Enable or disable automatic ONU upgrades on the OLT. Timing of when the automatic upgrade
             occurs is controlled by the onu-auto-upgrade-trigger attribute.
             Note, this only applies to ONUs where the expected firmware version is known and where
             the firmware status is set to 'Upgrade Required'. This field has been deprecated, use
             the onu-auto-upgrade field instead.";
        }
        leaf onu-auto-upgrade {
          type ciena:admin-state;
          default disabled;
          description
            "Enable or disable automatic ONU upgrades on the OLT. Timing of when the automatic upgrade
             occurs is controlled by the onu-auto-upgrade-trigger attribute.
             Note, this only applies to ONUs where the expected firmware version is known and where
             the firmware status is set to 'Upgrade Required'.";
        }
        leaf auto-boot-mode {
          type ciena:admin-state;
          default disabled;
          status deprecated;
          description
            "Enable or disable autonomous boot mode on the OLT.";
        }
        leaf upstream-fec-0 {
          when "../pon-mode = 'xgs-pon'";
          type ciena:admin-state;
          default enabled;
          description
            "Enable or disable upstream FEC (Forward Error Correction) 
             for burst profile 0 on the OLT in XGS-PON mode.";
        }
        leaf upstream-preamble-0 {
          when "../pon-mode = 'xgs-pon'";
          type uint16 {
            range "16..1000";
          }
          default 48;
          description
            "The amount of preamble at the start of burst for profile 0
             on the OLT in XGS-PON mode; measured in units of upstream slots (12.8ns).";
        }
        leaf downstream-fec {
          type ciena:admin-state;
          default enabled;
          description
            "Enable or disable downstream FEC (Forward Error Correction) on the OLT.";
        }
        leaf encryption-mode {
          type pon-ctrl:encryption-mode;
          default disabled;
          description
            "The encryption mode on the OLT.";
        }
        leaf guard-time {
          when "../pon-mode = 'xgs-pon'";
          type uint16 {
            range "16..1000";
          }
          default 32;
          description
            "The guard time used by the OLT in XGS-PON mode.
             This is the amount of dead time between upstream burst slots 
             measured in units of upstream slots (12.8ns).";
        }
        leaf max-nni-frame-size {
          type uint16 {
            range "512..12500";
          }
          default 9600;
          description
            "The NNI port's MTU on the OLT.
             Maximum supported MTU is 9600 in XGS-PON mode and
             12500 in 10G-EPON mode.";
        }
        leaf max-pon-frame-size {
          type uint16 {
            range "512..12500";
          }
          default 9600;
          description
            "The PON port's MTU on the OLT.
             Maximum supported MTU is 9600 in XGS-PON mode and
             12500 in 10G-EPON mode.";
        }
        leaf idle-receive-power-threshold {
          type cntypes:decimal-2-dig-small{
            range "-40..0";
          }
          units "dBm";
          description
            "The OLT's idle receive power threshold in dBm.";
        }
        leaf onu-performance-monitoring-mode {
          type statistics-binning-mode;
          default disabled;
          status deprecated;
          description
            "The performance monitoring mode to be applied to all ONUs.
             Statistics are always enabled now.";
        }
        leaf onu-auto-upgrade-trigger {
          type pon-ctrl:onu-auto-upgrade-trigger;
          default discovery;
          description
            "Control when an automatic ONU firmware upgrade will start.";
        }
        leaf degraded-onu-error-ratio {
          type uint16 {
            range "1..100";
          }
          default 20;
          description
            "Set the OLT error ratio threshold used for degraded ONU detection.";
        }
        leaf degraded-onu-min-samples {
          type uint16 {
            range "1..1000";
          }
          default 100;
          description
            "Set the OLT's minimum number of sample(s) used for degraded ONU detection.";
        }
        container nni-networks {
          description
            "The configuration data for all NNI Networks.
             NNI Networks are the configuration construct that enables user traffic to flow through the OLT.
             Inside the OLT, an NNI Network is a Layer-2 Switching Domain (an instance of an IEEE 802.1Q MAC
             Bridge and Virtual Bridge). Like any bridge, a network in the OLT has ports. In the OLT, the bridge ports 
             for an NNI Network are the Datalinks (an LLID in 10G-EPON, and an XGEM port in XGS-PON) configured for each ONU and the OLT.";
          list nni-network {
            key "name";
            description
              "An NNI Network used by the OLT.";
            leaf name {
              type pon-ctrl:name-string;
              description
                "Name of the NNI Network.";
            }
            leaf flooding-link {
              type ciena:admin-state;
              default enabled;
              description
                "Controls the creation of a flooding link on the NNI Network.
                 If the flooding link is disabled on the NNI Network then only one PON Connection will be
                 allowed to be created on the NNI Network. In that scenario, any flooding traffic on the NNI Network
                 will use the Datalink specified by that PON Connection.";
            }
            uses pon-ctrl:tag-match-grouping;
            uses pon-ctrl:tag-options-grouping;
          }
        }
        container cross-connects {
          description
            "The configuration data for all Cross Connects.
             Cross Connects are the configuration construct that enables user traffic to flow between ONUs via the OLT.
             To cross-connect two ONUs, a Datalink from each ONU must be attached to the same Cross Connect via the PON Connection
             configuration.";
          list cross-connect {
            key "name";
            description
              "A Cross Connect used by the OLT.";
            leaf name {
              type pon-ctrl:name-string;
              description
                "Name of the Cross Connect.";
            }
          }
        }
      }
    }

    container onus {
      description
        "The configuration data for all ONUs.";
      list onu {
        key "name olt";
        description
          "An ONU used by the OLT.";
        leaf name {
          type pon-ctrl:name-string;
          description
            "Name of the ONU.";
        }
        leaf olt {
          type pon-ctrl:olt-ref;
          mandatory true;
          description
            "Name of the OLT this ONU is subtended from.";
        }
        leaf admin-state {
          type ciena:admin-state;
          default enabled;
          description
            "Enable or disable the ONU. Sends a Disable_Serial_Number PLOAM message to the ONU.";
        }
        leaf serial-number {
          type string {
            pattern '[a-zA-Z]{4}[0-9a-fA-F]{8}';
          }
          description
            "The serial number the OLT expects to retrieve from the ONU.";
        }
        leaf registration-id {
          type pon-ctrl:name-string;
          description
            "The registration ID that will be assigned to the ONU.";
        }
        leaf onu-id {
          type uint16 {
            range "1..128";
          }
          description
            "The ONU-ID that will be assigned to the ONU.";
        }
        leaf auto-upgrade-firmware-file-name {
          type pon-ctrl:name-string;
          description
            "Name of the firmware file to use when auto-upgrading this ONU.
             Note, this will only take effect when the 'onu-auto-upgrade' option
             is enabled on the OLT and Global configuration. This configuration
             will take priority over the global firmware-file-name for this ONU's
             model in the onu-auto-firmware-upgrade-mapping.";
        }
        leaf auto-upgrade-defer-activation {
          type boolean;
          description
            "When set to true, ONU firmware activation after auto-upgrading
             this ONU is deferred until explicitly invoked.
             Note, this will only take effect when the 'onu-auto-upgrade' option
             is enabled on the OLT and Global configuration.";
        }
        leaf power-threshold-profile {
          type pon-ctrl:power-threshold-profile-ref;
          description
            "Name of the power threshold profile this ONU implements.
             This is currently no longer supported.
             Power threshold profiles will be re-enbled at a later point in time.";
        }
        leaf performance-monitoring-collection {
          type ciena:admin-state;
          default disabled;
          status deprecated;
          description
            "When set to enabled, ONU will collect performance monitoring statistics.
             Statistics are always enabled now.";
        }
        leaf expected-firmware-version {
          type string;
          description
            "Specifies the expected firmware version for this ONU. This firmware version
             will be used for the firmware auto-upgrade feature.
             Note, this will only take effect when the 'onu-auto-upgrade' option
             is enabled on the OLT. This configuration will take priority over the
             global 'expected-firmware-version' for this ONU's model in the global
             'onu-firmware-mapping'. Updating this will overwrite the expected
             firmware version set by the 'update-expected-firmware-version' parameter
             on a manual ONU firmware install/activate.";
        }
        leaf service-config-name {
          type string;
          description
            "Name of the service configuration to use for this ONU. If not specified,
             the default service configuration is used.";
        }
        container datalinks {
          description
            "The configuration data for all Datalinks.
             A Datalink is an LLID in 10G-EPON mode or an XGEM port in XGS-PON mode.";
          list datalink {
            key "name";
            description
              "A Datalink used by the ONU.";
            leaf name {
              type pon-ctrl:name-string;
              description
                "Name of the Datalink.";
            }
            leaf admin-state {
              type ciena:admin-state;
              default enabled;
              description
                "Enable or disable traffic on this Datalink.";
            }
            leaf-list uni-ports {
              type uint8 {
                range "1..5";
              }
              min-elements 1;
              max-elements 5;
              description
                "List of ONU UNI Ports to apply the Datalink on.";
            }
            leaf-list vlan-ids {
              type pon-ctrl:tag-match-vid;
              max-elements 12;
              description
                "List of VLAN IDs to be forwarded on this Datalink.
                 Traffic will only be allowed on this Datalink if it matches
                 one of the values specified. Not specifying this field or
                 specifying a value of 65535 will match on any VID value,
                 no VLAN tag or a priority tag. Values specified must be unique
                 across all Datalinks on the same UNI Port.";
            }
            leaf sla-profile {
              type pon-ctrl:sla-profile-ref;
              mandatory true;
              description
                "Name of the SLA Profile this Datalink implements.";
            }
            leaf add-ctag {
              type mef-fp:vlan-id;
              description
                "Add an optional C-Tag at the ONU for all upstream traffic on this Datalink.
                 This tag is popped (removed) in the downstream direction.";
            }
            leaf add-ctag-pcp {
              when "../add-ctag";
              type uint8 {
                range "0..7";
              }
              description
                "Specify the 802.1p priority of the added C-Tag on this Datalink.
                 This is only valid when the add-ctag parameter is specified.
                 When this field is not specified, a PCP value of 0 is assumed for
                 untagged frames. For tagged frames the PCP value of the added C-Tag 
                 is copied from the existing VLAN.";
            }
            uses pon-ctrl:control-plane-processing;
            uses pon-ctrl:dhcp-grouping;
            uses pon-ctrl:radius-grouping;
            leaf alloc-id {
              type uint16 {
                range "1154..1534";
              }
              must ". != 1279" {
                error-message
                  "Illegal value for ALLOC-ID. ALLOC-ID 1279 is reserved.";
              }
              description
                "The configured ALLOC-ID of this Datalink.
                 An XGEM port-id is also created with the same value.
                 Only valid in XGS-PON mode.
                 ALLOC-ID 1279 is reserved.";
            }
            uses pon-ctrl:pppoe-grouping;
            leaf loopback {
              type ciena:admin-state;
              default disabled;
              description
                "Determines whether loopback is enabled or disabled on the Datalink.";
            }
            leaf error-threshold-profile {
              type pon-ctrl:error-threshold-profile-ref;
              description
                "Name of the error threshold this Datalink implements.";
            }
            leaf xgem-ports {
              when "/pon-ctrl:pon-ctrl" +
                   "/pon-ctrl:olts" +
                   "/pon-ctrl:olt[name=current()/../../../olt]" +
                   "/pon-ctrl:pon-mode = 'xgs-pon'";
              type uint16 {
                range "1..8";
              }
              default 1;
              description
                "The configured number of XGEM ports of this Datalink.
                 The starting XGEM port-id will be the same as the configured datalink alloc-id.
                 If xgem-ports is greater than 1, the allocated XGEM port-ids will be sequential
                 starting from the configured alloc-id value.
                 Only valid in XGS-PON mode.";
            }
            leaf upstream-cos-queue-map {
              type cos-queue-map-ref;
              description
                "The configured upstream CoS queue map to be used on this Datalink.";
            }
            leaf downstream-cos-queue-map {
              type cos-queue-map-ref;
              description
                "The configured downstream CoS map to be used on this Datalink.";
            }
          }
        }
        container pon-connections {
          description
            "The configuration data for all PON Connections.
             PON Connections are the configuration construct that links a Datalink on the ONU to
             an NNI Network or Cross Connect on the OLT.";
          list pon-connection {
            key "name";
            description
              "A PON Connection used by the ONU.";
            leaf name {
              type pon-ctrl:name-string;
              description
                "Name of the PON Connection.";
            }
            leaf datalink {
              type leafref {
                path "../../../datalinks/datalink/name";
              }
              mandatory true;
              description
                "Reference to the Datalink on the ONU.
                 Datalink must be configured on the same ONU as this PON Connection.";
            }
            leaf nni-network {
              when "not(../cross-connect)";              
              type leafref {
                path "/pon-ctrl:pon-ctrl" + 
                     "/pon-ctrl:olts" + 
                     "/pon-ctrl:olt[name=current()/../../../olt]" +
                     "/pon-ctrl:nni-networks" +
                     "/pon-ctrl:nni-network" +
                     "/pon-ctrl:name";
              }
              mandatory true;
              description
                "Reference to the NNI Network on the OLT.
                 NNI Network must be configured on the same OLT as the ONU where this PON Connection exists.
                 The NNI Network reference is mutually exclusive with the Cross Connect reference.";
            }
            leaf cross-connect {
              when "not(../nni-network)";              
              type leafref {
                path "/pon-ctrl:pon-ctrl" + 
                     "/pon-ctrl:olts" + 
                     "/pon-ctrl:olt[name=current()/../../../olt]" +
                     "/pon-ctrl:cross-connects" +
                     "/pon-ctrl:cross-connect" +
                     "/pon-ctrl:name";
              }
              mandatory true;
              description
                "Reference to the Cross Connect on the OLT.
                 Cross Connect must be configured on the same OLT as the ONU where this PON Connection exists.
                 The Cross Connect reference is mutually exclusive with the NNI Network reference.";
            }
            uses pon-ctrl:tag-match-grouping;
            uses pon-ctrl:tag-options-grouping;
          }
        }
        container uni-ports {
          description
            "The configuration data for all UNI Ports.
             This configuration construct is optional and can be used to modify specific UNI Port parameters
             under this ONU.";
          list uni-port {
            key "name";
            max-elements 5;
            description
              "A UNI Port on the ONU.";
            leaf name {
              type pon-ctrl:name-string;
              description
                "The numerical identifier of this UNI Port.
                 Must be a numercical value between 1 and 5.";
            }
            leaf description {
              type pon-ctrl:name-string;
              description
                "A string description of this UNI Port.";
            }
            leaf admin-state {
              type ciena:admin-state;
              default enabled;
              description
                "Enable or disable the UNI Port.";
            }
            leaf max-frame-size {
              type uint16 {
                range "64..9216";
              }
              default 9216;
              description
                "The UNI Port's configured MTU.";
            }
            leaf speed {
              type pon-ctrl:uni-port-speed;
              default auto;
              description
                "The UNI Port's configured speed.";
            }
            leaf duplex {
              type pon-ctrl:uni-port-duplex;
              default auto;
              description
                "The UNI Port's configured duplex.";
            }
            leaf stats-collection {
              type ciena:admin-state;
              default disabled;
              status deprecated;
              description
                "Determines whether stats collection will be enabled or disabled for the UNI Port.
                 Statistics are always enabled now.";
            }
          }
        }
      }
    }

    container sla-profiles {
      description
        "The configuration data for all SLA Profiles.";
      list sla-profile {
        key "name";
        description
          "An SLA Profile used by a Datalink.";
        leaf name {
          type pon-ctrl:name-string;
          description
            "Name of the SLA Profile.";
        }
        leaf up-fixed-rate {
          type uint32 {
            range "0..8000000";
          }
          units Kbps;
          default 0;
          description
            "Fixed grant rate in Kbps. This is an unsolicited
             grant by the DBA regardless of need.";
        }
        leaf up-guaranteed-rate {
          type uint32 {
            range "0 | 128..10000000";
          }
          units Kbps;
          default 128;
          description
            "Guaranteed (high priority) upstream rate in Kbps.";
        }
        leaf up-guaranteed-max-burst {
          type uint32 {
            range "16000..1000000";
          }
          units Bytes;
          default 409600;
          description
            "Maximum upstream burst size in Bytes. The
             guaranteed rate is enforced at this burst size.";
        }
        leaf up-best-effort-rate {
          type uint32 {
            range "0 | 128..10000000";
          }
          units Kbps;
          default 10000000;
          description
            "Best Effort (low priority) upstream rate in Kbps.";
        }
        leaf up-best-effort-max-burst {
          type uint32 {
            range "16000..1000000";
          }
          units Bytes;
          default 409600;
          description
            "Maximum upstream burst size in Bytes. The best
             effort rate is enforced at this burst size.";
        }        
        leaf up-priority {
          type uint8 {
            range "1..8";
          }
          default 1;
          description
            "Priority level for the Guaranteed portion of the SLA.";
        }
        leaf up-service-limit {
          type uint16 {
            range "2..150";
          }
          units kBytes;
          default 60;
          description
            "Maximum grant size for an upstream slot in Kilobytes.";
        }
        leaf up-min-grant-period {
          type uint16 {
            range "0..100";
          }
          units 100us;
          default 0;
          description
            "The minimum allowed spacing between grants on this service.";
        }
        leaf up-max-grant-period {
          type uint16 {
            range "3..200";
          }
          units 100us;
          default 10;
          description
            "The maximum allowed time between grants on
             this service. This field will cause a polling grant
             when the ONU is idle.";
        }
        leaf down-guaranteed-rate {
          type uint32 {
            range "0 | 128..10000000";
          }
          units Kbps;
          default 128;
          description
            "Guaranteed (high priority) downstream rate in Kbps.";
        }
        leaf down-guaranteed-max-burst {
          type uint32 {
            range "16000..1000000";
          }
          units Bytes;
          default 409600;
          description
            "Maximum downstream burst size in Bytes. The
             guaranteed rate is enforced at this burst size.";
        }
        leaf down-best-effort-rate {
          type uint32 {
            range "0 | 128..10000000";
          }
          units Kbps;
          default 10000000;
          description
            "Best Effort (low priority) downstream rate in Kbps.";
        }
        leaf down-best-effort-max-burst {
          type uint32 {
            range "16000..1000000";
          }
          units Bytes;
          default 409600;
          description
            "Maximum downstream burst size in Bytes. The best
             effort rate is enforced at this burst size.";
        }
      }
    }

    container power-threshold-profiles {
      description
        "The configuration data for all power threshold profiles.";
      list power-threshold-profile {
        key "name";
        description
          "A power threshold profile used by an ONU.";
        leaf name {
          type pon-ctrl:name-string;
          description
            "Name of the power threshold profile.";
        }
        leaf receive-power-min-threshold {
          type cntypes:decimal-2-dig-small{
            range "-30..-1";
          }
          units "dBm";
          description
            "The ONU's receive power minimum threshold in dBm.";
        }
        leaf receive-power-warning-threshold {
          type cntypes:decimal-2-dig-small{
            range "-30..-1";
          }
          units "dBm";
          description
            "The ONU's receive power warning threshold in dBm.";
        }
        leaf receive-power-max-threshold {
          type cntypes:decimal-2-dig-small{
            range "-30..-1";
          }
          units "dBm";
          description
            "The ONU's receive power maximum threshold in dBm.";
        }
        leaf transmit-power-min-threshold {
          type cntypes:decimal-2-dig-small{
            range "1..30";
          }
          units "dBm";
          description
            "The ONU's transmit power minimum threshold in dBm.";
        }
        leaf transmit-power-warning-threshold {
          type cntypes:decimal-2-dig-small{
            range "1..30";
          }
          units "dBm";
          description
            "The ONU's transmit power warning threshold in dBm.";
        }
        leaf transmit-power-max-threshold {
          type cntypes:decimal-2-dig-small{
            range "1..30";
          }
          units "dBm";
          description
            "The ONU's transmit power maximum threshold in dBm.";
        }
      }
    }

    container error-threshold-profiles {
      description
        "The configuration data for all error threshold profiles.";
      list error-threshold-profile {
        key "name";
        description
          "An error threshold profile used by a Datalink.
           This container contains the thresholds at which an alarm is generated.
           Thresholds are checked at 0 min, 15 min, 30 min and 45 min clock time
           intervals. If not set or set to zero, threshold checking is disabled.";
        leaf name {
          type pon-ctrl:name-string;
          description
            "Name of the error threshold profile.";
        }
        leaf rx-errored-bip-blocks-threshold {
          type yang:counter64;
          description
            "Alarm reporting threshold for BIP blocks received with error.";
        }
        leaf rx-errored-bip-bits-threshold {
          type yang:counter64;
          description
            "Alarm reporting threshold BIP bits received with error.";
        }
        leaf rx-hec-errors-threshold {
          type yang:counter64;
          description
            "Alarm reporting threshold for errored header error checksums in the XGEM header and GPON
             Framing.";
        }
        leaf rx-crc32-drops-threshold {
          type yang:counter64;
          description
            "Alarm reporting threshold for segments dropped due to CRC-32 error.";
        }
        leaf rx-crc8-errors-threshold {
          type yang:counter64;
          description
            "Alarm reporting threshold for received CRC-8 errors in XGS-PON allocations/bandwidth requests.";
        }
        leaf rx-overflow-drops-threshold {
          type yang:counter64;
          description
            "Alarm reporting threshold for segments dropped due to queue overlfow.";
        }
        leaf rx-too-short-drops-threshold {
          type yang:counter64;
          description
            "Alarm reporting threshold for segments dropped due to being too short.";
        }
        leaf rx-too-long-drops-threshold {
          type yang:counter64;
          description
            "Alarm reporting threshold for segments dropped due to being too long.";
        }
        leaf rx-fec-uncorrectable-blocks-threshold {
          type yang:counter64;
          description
            "Alarm reporting threshold for FEC blocks received with errors that were not correctable.";
        }
      }
    }

    container cos-queue-maps {
      description
        "Configuration for egress traffic quality of service.";
      list cos-queue-map {
        key "name";
        description
          "List of cos-to-queue-map templates. COS to queue maps can be referenced by datalinks
           to determine mapping to a given queue/XGEM port in both upstream and downstream
           directions.";
        leaf name {
          type string;
          description
            "Name for the CoS queue map.";
        }
        leaf queue-count {
         type uint32 {
          range "1..8";
         }
          mandatory true;
          description
            "Number of queues (or XGEM ports) supported.";
        }
        list map-entry {
          key "cos";
          description
            "List of map-entries. Each map-entry for a given cos-to-queue map gives the mapping of cos to a queue.";
          leaf cos {
            type uint32 {
              range "0..7";
            }
            description
              "CoS to use for mapping to a queue.";
          }
          leaf queue {
            type uint32 {
              range "0..7";
            }
              mandatory true;
              description
              "Queue mapped to by CoS.";
          }
        }
      }
    }
  }

  container pon-ctrl-state {
    config false;
    description
      "PON state data.";

    container radius-servers {
      description
        "The state data for all RADIUS servers.";

      list radius-server {
        key "name";
        description
          "List of RADIUS servers.";
        leaf name {
          type pon-ctrl:name-string;
          description
            "Name of the RADIUS server.";
        }
        leaf radius-max-retry-state {
          type uint32;
          description
            "The max retries set on RADIUS server before held state is entered.";
        }
        leaf radius-held-period-state {
          type ciena:admin-state;
          description
            "The state of RADIUS server set for held period.";
        }
        leaf radius-quiet-period-state {
          type ciena:admin-state;
          description
            "The state of RADIUS server set for quiet period.";
        }
        list radius-server-address {
          key "host port";
          description
            "RADIUS server host and port.";
          leaf host {
            type inet:host;
            description
              "RADIUS server host address.";
          }
          leaf port {
            type inet:port-number;
            description
              "RADIUS server port.";
          }
          leaf oper-state {
            type pon-ctrl:radius-server-oper-state;
            description
              "Operational state of the RADIUS server.";
          }
          leaf last-state-change {
              type string;
              description
                "Time when the state last changed.";
          }
          container statistics {
            description
              "Statistics objects.";
            leaf total-auth-complete {
              type yang:counter64;
              description
                "Total authentication attempts completed successfully for this RADIUS server.";
            }
            leaf total-auth-timeout {
              type yang:counter64;
              description
                "Total authentication attempts that timed-out for this RADIUS server.";
            }
            leaf last-clear-time {
              type string;
              description
                "Time when the statistics were last cleared.";
            }
            leaf time {
              type string;
              description
                "Time when the statistics were last collected.";
            }
          }
        }
      }
    }

    container olts {
      description
        "The state data for all OLTs.";

      list olt {
        key "name";
        description
          "List of OLTs.";
        leaf name {
          type pon-ctrl:name-string;
          description
            "Name of the OLT.";
        }
        leaf oper-mac-address {
          type yang:mac-address;
          description
            "The MAC address that is read from the OLT.";
        }
        leaf oper-state {
          type pon-ctrl:olt-oper-state;
          description
            "Operational state of the OLT.";
        }
        leaf physical-interface {
          type string;
          description
            "The physical port on the device that hosts this OLT.";
        }
        leaf host-management-address {
          type string;
          description
            "The management address of the device hosting this OLT.";
        }
        leaf host-system-name {
          type string;
          description
            "The system name of the device hosting this OLT.";
        }
        leaf management-tpid {
          type pon-ctrl:tpid;
          description
            "TPID used for in-band management of this OLT.";
        }
        leaf management-vid {
          type mef-fp:vlan-id;
          description
            "VID used for in-band management of this OLT.";
        }
        leaf firmware-version {
          type string;
          description
            "Version of the firmware running on this OLT.";
        }
        leaf standby-firmware-version {
          type string;
          description
            "Version of the firmware in the standby bank on this OLT.";
        }
        leaf expected-firmware-version {
          type string;
          description
            "Version of the firmware that is expected to be running
             on this OLT.";
        }
        leaf firmware-status {
          type string;
          description
            "Status of the firmware running on this OLT.";
        }
        leaf hardware-version {
          type string;
          description
            "Version of the OLT's hardware.";
        }
        leaf model {
          type string;
          description
            "Model of this OLT.";
        }
        leaf model-number {
          type string;
          description
            "Model number of this OLT.";
        }
        leaf serial-number {
          type string;
          description
            "Serial number of this OLT.";
        }
        leaf num-configured-onus {
          type uint16;
          description
            "Number of configured ONUs under this OLT.";
        }
        leaf num-registered-onus {
          type uint16;
          description
            "Number of registered ONUs under this OLT.";
        }
        leaf num-deregistered-onus {
          type uint16;
          description
            "Number of deregistered ONUs under this OLT.";
        }
        leaf num-unconfigured-onus {
          type uint16;
          description
            "Number of unconfigured ONUs under this OLT.";
        }
        leaf-list unconfigured-onu {
          type string;
          description
            "The list of ONU serial numbers which have been discovered
             but not configured.";
        }
        leaf-list unconfigured-onu-registration-id {
          type string;
          description
            "The list of ONU registration IDs which have been discovered
             but not configured.";
        }
        leaf num-links {
          type uint16;
          description
            "Number of Datalinks under this OLT.";
        }
        leaf alarms {
          type olt-alarm-bit-map;
          description
            "Bit map of alarm conditions currently active on this OLT.";
        }
        leaf-list cos-queue-maps {
          type pon-ctrl:cos-queue-map-ref;
          max-elements 3;
          description
            "List of OLT egress/downstream datalink cos-queue-maps
             configured on this OLT.
             A maximum of 3 OLT egress/downstream datalink cos-queue-maps
             are supported on the OLT";
        }
        leaf previous-oper-state {
          type pon-ctrl:olt-oper-state;
          description
            "Previous operational state of the OLT.";
        }
        leaf oper-state-change-reason {
          type olt-oper-state-change-reason;
          description
            "Reason for the oper-state change.";
        }
        leaf reset-status {
          type string;
          description
            "Status of resetting the OLT.";
        }
        container statistics {
          description
            "OLT statistics.";
          container nni {
            description
              "OLT NNI statistics";
            uses pon-ctrl:packet-counters-grouping;
            leaf rx-oam {
              type yang:counter64;
              description
                "Count of OAM frames received on the interface.";
            }
            leaf tx-oam {
              type yang:counter64;
              description
                "Count of OAM frames transmitted on the interface.";
            }
            leaf rx-mac-control-frames {
              type yang:counter64;
              description
                "Count of MAC Control frames received on the interface.";
            }
            leaf rx-filtered-frames {
              type yang:counter64;
              description
                "Count of frames received on the interface but filtered (not forwarded).";
            }
            leaf rx-crc32-drops {
              type yang:counter64;
              description
                "Count of frames received on the interface and dropped due to invalid CRC32.";
            }
            leaf rx-overflow-drops {
              type yang:counter64;
              description
                "Count of frames received on the interface and dropped due to input queues being full.";
            }
            leaf rx-too-short-drops {
              type yang:counter64;
              description
                "Count of frames received on the interface and dropped due to the frame being too short.";
            }
            leaf rx-too-long-drops {
              type yang:counter64;
              description
                "Count of frames received on the interface and dropped due to the frame being too long.";
            }
            leaf tx-octets-unicast {
              type yang:counter64;
              description
                "Count of unicast octets transmitted.";
            }
            leaf rx-octets-unicast {
              type yang:counter64;
              description
                "Count of unicast octets received.";
            }
            leaf tx-octets-broadcast {
              type yang:counter64;
              description
                "Count of broadcast octets transmitted.";
            }
            leaf rx-octets-broadcast {
              type yang:counter64;
              description
                "Count of broadcast octets received.";
            }
            leaf tx-octets-multicast {
              type yang:counter64;
              description
                "Count of multicast octets transmitted.";
            }
            leaf rx-octets-multicast {
              type yang:counter64;
              description
                "Count of multicast octets received.";
            }
            leaf tx-frames-unicast {
              type yang:counter64;
              description
                "Count of unicast frames transmitted.";
            }
            leaf rx-frames-unicast {
              type yang:counter64;
              description
                "Count of unicast frames received.";
            }
            leaf tx-frames-broadcast {
              type yang:counter64;
              description
                "Count of broadcast frames transmitted.";
            }
            leaf rx-frames-broadcast {
              type yang:counter64;
              description
                "Count of broadcast frames received.";
            }
            leaf tx-frames-multicast {
              type yang:counter64;
              description
                "Count of multicast frames transmitted.";
            }
            leaf rx-frames-multicast {
              type yang:counter64;
              description
                "Count of multicast frames received.";
            }
            leaf last-clear-time {
              type string;
              description
                "Time when the statistics were last cleared.";
            }
            leaf tx-non-control-octets {
              type yang:counter64;
              description
                "Count of non control octets transmitted.";
            }
            leaf tx-oam-octets {
              type yang:counter64;
              description
                "Count of oam octets transmitted.";
            }
            leaf tx-cascading-packets {
              type yang:counter64;
              description
                "Count of cascading packets transmitted.";
            }
            leaf tx-cascading-bytes {
              type yang:counter64;
              description
                "Count of cascading bytes transmitted.";
            }
            leaf rx-overflow-octets {
              type yang:counter64;
              description
                "Count of overflow octets received.";
            }
            leaf rx-oam-octets {
              type yang:counter64;
              description
                "Count of oam octets received.";
            }
            leaf rx-mine-cascading-bytes {
              type yang:counter64;
              description
                "Count of mine cascading bytes received.";
            }
            leaf rx-other-cascading-bytes {
              type yang:counter64;
              description
                "Count of other cascading bytes received.";
            }
            leaf rx-mine-cascading-packets {
              type yang:counter64;
              description
                "Count of mine cascading packets received.";
            }
            leaf rx-other-cascading-packets {
              type yang:counter64;
              description
                "Count of other cascading packets received.";
            }
            leaf time {
              type string;
              description
                "Time when the statistics were last collected.";
            }
          }
          container pon {
            description
              "OLT PON statistics. Bandwidth statistics are calculated in 5 minute intervals.";
            uses pon-ctrl:packet-counters-grouping;
            uses pon-ctrl:phy-counters-grouping;
            leaf rx-fec-good-blocks {
              type yang:counter64;
              description
                "Count of FEC blocks received without errors.";
            }
            leaf rx-fec-corrected-blocks {
              type yang:counter64;
              description
                "Count of FEC blocks received with errors that were correctable.";
            }
            leaf rx-fec-uncorrectable-blocks {
              type yang:counter64;
              description
                "Count of FEC blocks received with errors that were not correctable.";
            }
            leaf rx-fec-corrections {
              type yang:counter64;
              description
                "Count of FEC blocks received with correctable errors that were corrected.";
            }
            leaf rx-octets-idle {
              type yang:counter64;
              description
                "Count of idle octets received. Idle octets are used to fill data
                 gaps during transmission. Idle octets are dropped by the receiver.";
            }
            leaf tx-octets-idle {
              type yang:counter64;
              description
                "Count of idle octets transmitted. Idle octets are used to fill data
                 gaps during transmission. Idle octets are dropped by the receiver.";
            }
            leaf rx-bw-ethernet-rate {
              type yang:counter64;
              units bps;
              description
                "Received Ethernet bandwidth.";
            }
            leaf tx-bw-ethernet-rate {
              type yang:counter64;
              units bps;
              description
                "Transmitted Ethernet bandwidth.";
            }
            leaf rx-bw-data-rate {
              type yang:counter64;
              units bps;
              description
                "Received data bandwidth.";
            }
            leaf tx-bw-data-rate {
              type yang:counter64;
              units bps;
              description
                "Transmitted data bandwidth.";
            }
            leaf rx-bw-overhead-burst {
              type yang:counter64;
              units bps;
              description
                "Received burst overhead bandwidth.";
            }
            leaf tx-bw-overhead-framing {
              type yang:counter64;
              units bps;
              description
                "Transmitted framing overhead bandwidth.";
            }
            leaf rx-bw-overhead-fec {
              type yang:counter64;
              units bps;
              description
                "Received FEC overhead bandwidth.";
            }
            leaf tx-bw-overhead-fec {
              type yang:counter64;
              units bps;
              description
                "Transmitted FEC overhead bandwidth.";
            }
            leaf rx-bw-overhead-total {
              type yang:counter64;
              units bps;
              description
                "Total received overhead bandwidth.";
            }
            leaf tx-bw-overhead-total {
              type yang:counter64;
              units bps;
              description
                "Total transmitted overhead bandwidth.";
            }
            leaf rx-bw-total-used {
              type yang:counter64;
              units bps;
              description
                "Total receive bandwidth used, includes both data and overhead.";
            }
            leaf tx-bw-total-used {
              type yang:counter64;
              units bps;
              description
                "Total transmit bandwidth used, includes both data and overhead.";
            }
            leaf rx-bw-total-utilization-percent {
              type yang:counter64;
              description
                "Percentage of the total receive bandwidth used.";
            }
            leaf tx-bw-total-utilization-percent {
              type yang:counter64;
              description
                "Percentage of the total transmit bandwidth used.";
            }
            leaf rx-bw-total-free {
              type yang:counter64;
              units bps;
              description
                "Total receive bandwidth free.";
            }
            leaf tx-bw-total-free {
              type yang:counter64;
              units bps;
              description
                "Total transmit bandwidth free.";
            }
            leaf tx-octets-unicast {
              type yang:counter64;
              description
                "Count of unicast octets transmitted.";
            }
            leaf rx-octets-unicast {
              type yang:counter64;
              description
                "Count of unicast octets received.";
            }
            leaf tx-octets-multi-broadcast {
              type yang:counter64;
              description
                "Count of multicast and broadcast octets transmitted.";
            }
            leaf rx-octets-multi-broadcast {
              type yang:counter64;
              description
                "Count of multicast and broadcast octets received.";
            }
            leaf tx-frames-unicast {
              type yang:counter64;
              description
                "Count of unicast frames transmitted.";
            }
            leaf tx-frames-broadcast {
              type yang:counter64;
              description
                "Count of broadcast frames transmitted.";
            }
            leaf tx-frames-multicast {
              type yang:counter64;
              description
                "Count of multicast frames transmitted.";
            }
            leaf last-clear-time {
              type string;
              description
                "Time when the statistics were last cleared.";
            }
            leaf tx-control-octets {
              type yang:counter64;
              description
                "Count of control octets transmitted.";
            }
            leaf tx-plain-octets {
              type yang:counter64;
              description
                "Count of plain octets transmitted.";
            }
            leaf tx-encrypted-octets {
              type yang:counter64;
              description
                "Count of encrypted octets transmitted.";
            }
            leaf tx-mpcp-octets {
              type yang:counter64;
              description
                "Count of mpcp octets transmitted.";
            }
            leaf tx-oam-frames {
              type yang:counter64;
              description
                "Count of OAM frames transmitted on the interface.";
            }
            leaf tx-grant-ups-tq {
              type yang:counter64;
              description
                "Count of tq or upstreams slots granted to the ONUs.";
            }
            leaf rx-control-octets {
              type yang:counter64;
              description
                "Count of control octets received.";
            }
            leaf rx-security-drop-octets {
              type yang:counter64;
              description
                "Count of security drop octets received.";
            }
            leaf rx-plain-octets {
              type yang:counter64;
              description
                "Count of plain octets received.";
            }
            leaf rx-mpcp-octets {
              type yang:counter64;
              description
                "Count of mpcp octets received.";
            }
            leaf rx-encrypted-octets {
              type yang:counter64;
              description
                "Count of encrypted octets received.";
            }
            leaf rx-overflow-octets {
              type yang:counter64;
              description
                "Count of overflow octets received.";
            }
            leaf rx-key-mismatch-octets {
              type yang:counter64;
              description
                "Count of key mismatch octets received.";
            }
            leaf rx-unmatched-drops {
              type yang:counter64;
              description
                "Count of frames received on the interface and dropped due to no match.";
            }
            leaf rx-bad-icv-drops {
              type yang:counter64;
              description
                "Count of frames received on the interface and dropped due to bad icv.";
            }
            leaf rx-oam-frames {
              type yang:counter64;
              description
                "Count of OAM frames received on the interface.";
            }
            leaf rx-all-bw-reqs {
              type yang:counter64;
              description
                "Count of all bandwidth requests received.";
            }
            leaf time {
              type string;
              description
                "Time when the statistics were last collected.";
            }
          }
          container radius {
            description
              "OLT RADIUS statistics";
            uses auth-counters-grouping;
            uses relay-counters-grouping;
            uses pppoe-counters-grouping;
            uses dhcpv6-counters-grouping;
          }
        }
        container diagnostic-data {
          description
            "The diagnostic data for this OLT.";
          leaf asic-temperature {
            type int16;
            units "C";
            description
              "The OLT's ASIC temperature in degrees C.";
          }
          leaf xcvr-temperature {
            type int16;
            units "C";
            description
              "The OLT's transceiver temperature in degrees C.";
          }
          leaf laser-temperature {
            type int16;
            units "C";
            description
              "The OLT's laser temperature in degrees C.";
          }
          leaf vcc {
            type cntypes:decimal-2-dig;
            units "mV";
            description
              "The OLT's VCC in mV.";
          }
          leaf tec-current {
            type cntypes:decimal-2-dig;
            units "uA";
            description
              "The OLT's TEC current in uA.";
          }
          leaf transmit-bias {
            type cntypes:decimal-2-dig;
            units "uA";
            description
              "The OLT's transmit bias current in uA.";
          }
          leaf idle-receive-power {
            type cntypes:decimal-2-dig;
            units "dBm";
            description
              "The OLT's idle receive power in dBm.";
          }
          leaf transmit-power {
            type cntypes:decimal-2-dig;
            units "dBm";
            description
              "The OLT's transmit power in dBm.";
          }
          leaf last-shutdown-reason {
            type string;
            description
              "The reason for the latest shutdown of the OLT's laser.";
          }
          leaf is-laser-shutdown {
            type boolean;
            description
              "When true, indicates that the OLT's laser is currently shutdown.
               When false, indicates that the OLT's laser is currently active.";
          }
          leaf uptime {
            type uint64;
            units "seconds";
            description
              "The OLT's uptime in seconds.";
          }
          leaf time-stamp {
            type string;
            description
              "The time the data was cached.";
          }
          leaf low-receive-power {
            type cntypes:decimal-2-dig;
            units "dBm";
            description
              "The OLT's low receive optical power in dBm for the current 15 minute interval.";
          }
          leaf high-receive-power {
            type cntypes:decimal-2-dig;
            units "dBm";
            description
              "The OLT's high receive optical power in dBm for the current 15 minute interval.";
          }
        }
        container nni-networks {
          description
            "The state data for all NNI Networks.";
          list nni-network {
            key "name";
            description
              "List of NNI Networks.";
            leaf name {
              type pon-ctrl:name-string;
              description
                "Name of the NNI Network.";
            }
            leaf default-port-id {
              type uint16;
              description
                "The XGEM port ID of the default downstream flooding link for this NNI Network";
            }
            container flooding-statistics {
              description
                "Flooding link statistics on this NNI Network as viewed by the OLT.";
              uses pon-ctrl:flooding-counters-grouping;
              leaf last-clear-time {
                type string;
                description
                  "Time when the statistics were last cleared.";
              }
              leaf time {
                type string;
                description
                  "Time when the statistics were last collected.";
              }
            }
          }
        }
        container rogue-onu-idle-power-state {
          description
            "The idle power rogue ONU state data for this OLT.";
          uses rogue-onu-olt-idle-power-state-grouping;
        }
        container rogue-onu-disallowed-state {
          description
            "The disallowed error rogue ONU state data for this OLT.";
          uses rogue-onu-olt-disallowed-error-state-grouping;
        }
      }
    }

    container onus {
      description
        "The state data for all ONUs.";

      list onu {
        key "name olt";
        description
          "List of ONUs.";
        leaf name {
          type pon-ctrl:name-string;
          description
            "Name of the ONU.";
        }
        leaf olt {
          type pon-ctrl:olt-ref;
          description
            "Name of the OLT this ONU is subtended from.";
        }
        leaf oper-state {
          type pon-ctrl:onu-oper-state;
          description
            "Operational state of the ONU.";
        }
        leaf serial-number {
          type string {
            pattern '[a-zA-Z]{4}[0-9a-fA-F]{8}';
          }
          description
            "The serial number of this ONU.";
        }
        leaf registration-id {
          type pon-ctrl:name-string;
          description
            "The registration ID of this ONU.";
        }
        leaf onu-id {
          type uint16;
          description
            "The ONU-ID of this ONU as assigned by the OLT.";
        }
        leaf deregister-reason {
          type string;
          description
            "The reason for the last ONU deregistration.
             Set when the oper-state of the ONU is 'deregistered'.";
        }
        leaf firmware-version {
          type string;
          description
            "Version of the firmware running on this ONU.";
        }
        leaf standby-firmware-version {
          type string;
          description
            "Version of the firmware in the standby bank on this ONU.";
        }
        leaf expected-firmware-version {
          type string;
          description
            "Version of the firmware that is expected to be running
             on this ONU based on the model number.";
        }
        leaf firmware-status {
          type string;
          description
            "Status of the firmware running on this ONU.";
        }
        leaf firmware-upgrade-progress {
          type uint16;
          description
            "Percentage completion of the ONU firmware upgrade operation.
             Set when the ONU firmware status is 'Upgrading'.";
        }
        leaf firmware-upgrade-fail-reason {
          type string;
          description
            "The reason for the last ONU firmware upgrade failure.
             Set when the ONU firmware status is 'Upgrade Failed'.";
        }
        leaf firmware-upgrade-attempts {
          type uint16;
          description
            "The number of times the ONU firmware upgrade operation was attempted.
             Set when the ONU firmware status is 'Upgrading' or 'Upgrade Failed'.";
        }
        leaf model {
          type string;
          description
            "Model number of this ONU.";
        }
        leaf revision {
          type string;
          description
            "Revision model of this ONU.";
        }
        leaf vendor-id {
          type string;
          description
            "Vendor ID of this ONU.";
        }
        leaf mode {
          type string;
          description
            "Mode that this ONU is operating in.";
        }
        leaf num-links {
          type uint16;
          description
            "Number of Datalinks under this ONU.";
        }
        leaf num-uni-ports {
          type uint8;
          description
            "Number of UNI Ports on this ONU.";
        }
        leaf alarms {
          type onu-alarm-bit-map;
          description
            "Bit map of alarm conditions currently active on this ONU.";
        }
        leaf previous-oper-state {
          type pon-ctrl:onu-oper-state;
          description
            "Previous operational state of the ONU.";
        }
        leaf oper-state-change-reason {
          type onu-oper-state-change-reason;
          description
            "Reason for the oper-state change.";
        }
        leaf service-config-name {
          type string;
          description
            "Name of the service configuration applied to this ONU. If not specified,
             the default service configuration is used.";
        }
        leaf reset-status {
          type string;
          description
            "Status of resetting the ONU.";
        }
        container rogue-state {
          description
            "The rogue state data for this ONU.";
           uses rogue-onu-state-grouping;
        }
        container rogue-onu-disallowed-state {
          description
            "The disallowed ONU rogue state data for this ONU.";
           uses rogue-onu-disallowed-onu-state-grouping;
        }
        container rogue-onu-power-variation-state {
          description
            "The power variation rogue state data for this ONU.";
           uses rogue-onu-power-variation-state-grouping;
        }
        container datalinks {
          description
            "The state data for all Datalinks.";
          list datalink {
            key "name";
            description
              "List of Datalinks.";
            leaf name {
              type pon-ctrl:name-string;
              description
                "Name of the Datalink.";
            }
            leaf alloc-id {
              type uint16;
              description
                "The ALLOC-ID of this Datalink as assigned by the OLT/ONU.
                 Only valid in XGS-PON mode.";
            }
            container xgem-ports {
              description
                "The state data for all XGEM ports on the Datalink";
              list xgem-port {
                key "xgem-port-id";
                description
                  "List of XGEM ports";
                leaf xgem-port-id {
                  type uint16;
                  description
                    "The ID of the XGEM port.";
                }
                container statistics {
                  description
                    "Datalink XGEM port statistics as viewed by the OLT.";
                  uses pon-ctrl:packet-counters-grouping;
                  uses pon-ctrl:phy-counters-grouping;
                  leaf rx-fec-good-blocks {
                    type yang:counter64;
                    description
                      "Count of FEC blocks received without errors.";
                  }
                  leaf rx-fec-corrected-blocks {
                    type yang:counter64;
                    description
                      "Count of FEC blocks received with errors that were correctable.";
                  }
                  leaf rx-fec-uncorrectable-blocks {
                    type yang:counter64;
                    description
                      "Count of FEC blocks received with errors that were not correctable.";
                  }
                  leaf rx-fec-corrections {
                    type yang:counter64;
                    description
                      "Count of FEC blocks received with correctable errors that were corrected.";
                  }
                  leaf tx-octets-multi-broadcast {
                    type yang:counter64;
                    description
                      "Count of multicast and broadcast octets transmitted.";
                  }
                  leaf tx-control-octets {
                    type yang:counter64;
                    description
                      "Count of control octets transmitted.";
                  }
                  leaf tx-plain-octets {
                    type yang:counter64;
                    description
                      "Count of plain octets transmitted.";
                  }
                  leaf tx-encrypted-octets {
                    type yang:counter64;
                    description
                      "Count of encrypted octets transmitted.";
                  }
                  leaf tx-oam-frames {
                    type yang:counter64;
                    description
                      "Count of OAM frames transmitted on the interface.";
                  }
                  leaf tx-grant-ups-tq {
                    type yang:counter64;
                    description
                      "Count of tq or upstreams slots granted to the ONUs.";
                  }
                  leaf tx-octets-unicast {
                    type yang:counter64;
                    description
                      "Total number of unicast octets transmitted.";
                  }
                  leaf tx-frames-unicast {
                    type yang:counter64;
                    description
                      "Count of unicast frames transmitted.";
                  }
                  leaf tx-frames-multicast {
                    type yang:counter64;
                    description
                      "Count of multicast frames transmitted.";
                  }
                  leaf tx-frames-broadcast {
                    type yang:counter64;
                    description
                      "Count of broadcast frames transmitted.";
                  }
                  leaf rx-control-octets {
                    type yang:counter64;
                    description
                      "Count of control octets received.";
                  }
                  leaf rx-security-drop-octets {
                    type yang:counter64;
                    description
                      "Count of security drop octets received.";
                  }
                  leaf rx-octets-unicast {
                    type yang:counter64;
                    description
                      "Count of unicast octets received.";
                  }
                  leaf rx-octets-multi-broadcast {
                    type yang:counter64;
                    description
                      "Count of multicast and broadcast octets received.";
                  }
                  leaf rx-plain-octets {
                    type yang:counter64;
                    description
                      "Count of plain octets received.";
                  }
                  leaf rx-encrypted-octets {
                    type yang:counter64;
                    description
                      "Count of encrypted octets received.";
                  }
                  leaf rx-overflow-octets {
                    type yang:counter64;
                    description
                      "Count of overflow octets received.";
                  }
                  leaf rx-idle-octets {
                    type yang:counter64;
                    description
                      "Count of idle octets received.";
                  }
                  leaf rx-key-mismatch-octets {
                    type yang:counter64;
                    description
                      "Count of key mismatch octets received.";
                  }
                  leaf rx-bad-icv-drops {
                    type yang:counter64;
                    description
                      "Count of frames received on the interface and dropped due to bad icv.";
                  }
                  leaf rx-oam-frames {
                    type yang:counter64;
                    description
                      "Count of OAM frames received on the interface.";
                  }
                  leaf rx-all-bw-reqs {
                    type yang:counter64;
                    description
                      "Count of all bandwidth requests received.";
                  }
                  leaf last-clear-time {
                    type string;
                    description
                      "Time when the statistics were last cleared.";
                  }
                  leaf rx-mpcp-octets {
                    type yang:counter64;
                    description
                      "Count of mpcp octets received.";
                  }
                  leaf time {
                    type string;
                    description
                      "Time when the statistics were last collected.";
                  }
                }
              }
            }
            leaf llid {
              type uint16;
              description
                "The LLID of this Datalink as assigned by the OLT/ONU.
                 Only valid in 10G-EPON mode.";
            }
            leaf alarms {
              type datalink-alarm-bit-map;
              description
                "Bit map of alarm conditions currently active on this Datalink.";
            }
            uses pon-ctrl:control-plane-processing-state;
            container statistics {
              description
                "Datalink statistics as viewed by the OLT.";
              uses pon-ctrl:packet-counters-grouping;
              uses pon-ctrl:phy-counters-grouping;
              leaf rx-fec-good-blocks {
                type yang:counter64;
                description
                  "Count of FEC blocks received without errors.";
              }
              leaf rx-fec-corrected-blocks {
                type yang:counter64;
                description
                  "Count of FEC blocks received with errors that were correctable.";
              }
              leaf rx-fec-uncorrectable-blocks {
                type yang:counter64;
                description
                  "Count of FEC blocks received with errors that were not correctable.";
              }
              leaf rx-fec-corrections {
                type yang:counter64;
                description
                  "Count of FEC blocks received with correctable errors that were corrected.";
              }
              leaf tx-octets-multi-broadcast {
                type yang:counter64;
                description
                  "Count of multicast and broadcast octets transmitted.";
              }
              leaf tx-control-octets {
                type yang:counter64;
                description
                  "Count of control octets transmitted.";
              }
              leaf tx-plain-octets {
                type yang:counter64;
                description
                  "Count of plain octets transmitted.";
              }
              leaf tx-encrypted-octets {
                type yang:counter64;
                description
                  "Count of encrypted octets transmitted.";
              }
              leaf tx-oam-frames {
                type yang:counter64;
                description
                  "Count of OAM frames transmitted on the interface.";
              }
              leaf tx-grant-ups-tq {
                type yang:counter64;
                description
                  "Count of tq or upstreams slots granted to the ONUs.";
              }
              leaf tx-octets-unicast {
                type yang:counter64;
                description
                  "Total number of unicast octets transmitted.";
              }
              leaf tx-frames-unicast {
                type yang:counter64;
                description
                  "Count of unicast frames transmitted.";
              }
              leaf tx-frames-multicast {
                type yang:counter64;
                description
                  "Count of multicast frames transmitted.";
              }
              leaf tx-frames-broadcast {
                type yang:counter64;
                description
                  "Count of broadcast frames transmitted.";
              }
              leaf rx-control-octets {
                type yang:counter64;
                description
                  "Count of control octets received.";
              }
              leaf rx-security-drop-octets {
                type yang:counter64;
                description
                  "Count of security drop octets received.";
              }
              leaf rx-octets-unicast {
                type yang:counter64;
                description
                  "Count of unicast octets received.";
              }
              leaf rx-octets-multi-broadcast {
                type yang:counter64;
                description
                  "Count of multicast and broadcast octets received.";
              }
              leaf rx-plain-octets {
                type yang:counter64;
                description
                  "Count of plain octets received.";
              }
              leaf rx-encrypted-octets {
                type yang:counter64;
                description
                  "Count of encrypted octets received.";
              }
              leaf rx-overflow-octets {
                type yang:counter64;
                description
                  "Count of overflow octets received.";
              }
              leaf rx-idle-octets {
                type yang:counter64;
                description
                  "Count of idle octets received.";
              }
              leaf rx-key-mismatch-octets {
                type yang:counter64;
                description
                  "Count of key mismatch octets received.";
              }
              leaf rx-bad-icv-drops {
                type yang:counter64;
                description
                  "Count of frames received on the interface and dropped due to bad icv.";
              }
              leaf rx-oam-frames {
                type yang:counter64;
                description
                  "Count of OAM frames received on the interface.";
              }
              leaf rx-all-bw-reqs {
                type yang:counter64;
                description
                  "Count of all bandwidth requests received.";
              }
              leaf last-clear-time {
                type string;
                description
                  "Time when the statistics were last cleared.";
              }
              leaf rx-mpcp-octets {
                type yang:counter64;
                description
                  "Count of mpcp octets received.";
              }
              leaf time {
                type string;
                description
                  "Time when the statistics were last collected.";
              }
            }
          }
          list datalink-relay {
            key "name";
            description
              "List of Datalink Relays.";
            leaf name {
              type pon-ctrl:name-string;
              description
                "Name of the Datalink.";
            }
            list datalink-relay-state {
              key cpe-mac;
              description
                "List of CPE states.";
              leaf cpe-mac {
                type yang:mac-address;
                description
                  "Customer premises equipment MAC address.";
              }
              leaf oper-state {
                type pon-ctrl:dhcp-relay-oper-state;
                description
                  "Operational state of DHCP relay.";
              }
              leaf client-address {
                type pon-ctrl:pon-relay-attribute-string;
                description
                  "Dynamic host configuration protocol client address.";
              }
              leaf client-requested-address {
                type pon-ctrl:pon-relay-attribute-string;
                description
                  "Dynamic host configuration protocol client requested address.";
              }
              leaf client-identifier {
                type pon-ctrl:pon-relay-attribute-string;
                description
                  "Dynamic host configuration protocol client identifier.";
              }
              leaf server-identifier {
                type pon-ctrl:pon-relay-attribute-string;
                description
                  "Dynamic host configuration protocol server identifier.";
              }
              leaf circuit-identifier {
                type pon-ctrl:pon-relay-attribute-string;
                description
                  "Dynamic host configuration protocol circuit identifier";
              }
              leaf remote-identifier {
                type pon-ctrl:pon-relay-attribute-string;
                description
                  "Dynamic host configuration protocol remote identifier.";
              }
              leaf unicast-identifier {
                 type uint32;
                description
                  "Dynamic host configuration protocol unicast identifier.";
              }
              leaf create-time {
                type pon-ctrl:pon-relay-attribute-string;
                description
                  "Dynamic host configuration protocol create time.";
              }
              leaf expiry-time {
                type pon-ctrl:pon-relay-attribute-string;
                description
                  "Dynamic host configuration protocol expiry time.";
              }
              leaf reset-count {
                type uint32;
                description
                  "Dynamic host configuration protocol reset count.";
              }
              leaf last-success-time {
                type pon-ctrl:pon-relay-attribute-string;
                description
                  "Dynamic host configuration protocol last success time.";
              }
              container statistics {
                description
                  "DHCP relay statistics as viewed by the CPE address.";
                uses pon-ctrl:relay-counters-grouping;
              }
            }
            container statistics {
              description
                "DHCP relay statistics as viewed by the Datalink.";
              uses pon-ctrl:relay-counters-grouping;
            }
          }
          list datalink-authentication {
            key "name";
            description
              "List of Datalink Authentications.";
            leaf name {
              type pon-ctrl:name-string;
              description
                "Name of the Datalink.";
            }
            list datalink-authentication-state {
              key cpe-mac;
              description
                "List of CPE states.";
              leaf cpe-mac {
                type yang:mac-address;
                description
                  "Customer premises equipment MAC address.";
              }
              leaf oper-state {
                type pon-ctrl:authentication-oper-state;
                description
                  "Operational state of authentication.";
              }
              leaf create-time {
                type pon-ctrl:pon-relay-attribute-string;
                description
                  "Authentication create time.";
              }
              leaf last-success-time {
                type pon-ctrl:pon-relay-attribute-string;
                description
                  "Authentication last success time.";
              }
              leaf last-failure-time {
                type pon-ctrl:pon-relay-attribute-string;
                description
                  "Authentication last failure time.";
              }
              leaf held-period-start-time {
                type pon-ctrl:pon-relay-attribute-string;
                description
                  "Held period start time.";
              }
              leaf quiet-period-start-time {
                type pon-ctrl:pon-relay-attribute-string;
                description
                  "Quiet period start time.";
              }
              leaf unicast-identifier {
                type uint32;
                description
                  "Authentication unicast identifier.";
              }
              leaf reset-count {
                type uint32;
                description
                  "Authentication reset count.";
              }
              leaf failure-count {
                type uint32;
                description
                  "Authentication failure count.";
              }
              container statistics {
                description
                  "Authentication statistics as viewed by the CPE address.";
                uses pon-ctrl:auth-counters-grouping;
              }
            }
            container statistics {
              description
                "Authentication statistics as viewed by the Datalink.";
              uses pon-ctrl:auth-counters-grouping;
            }
          }
          list datalink-pppoe {
            key "name";
            description
              "List of Datalink PPPoEs.";
            leaf name {
              type pon-ctrl:name-string;
              description
                "Name of the Datalink.";
            }
            list datalink-pppoe-state {
              key cpe-mac;
              description
                "List of CPE states.";
              leaf cpe-mac {
                type yang:mac-address;
                description
                  "Customer premises equipment MAC address.";
              }
              leaf oper-state {
                type pon-ctrl:pppoe-oper-state;
                description
                  "Operational state of PPPoE.";
              }
              leaf circuit-identifier {
                type pon-ctrl:pon-relay-attribute-string;
                description
                  "PPPoE circuit identifier";
              }
              leaf remote-identifier {
                type pon-ctrl:pon-relay-attribute-string;
                description
                  "PPPoE remote identifier.";
              }
              leaf session-identifier {
                type uint32;
                description
                  "PPPoE session identifier.";
              }
              leaf unicast-identifier {
                 type uint32;
                description
                  "PPPoE unicast identifier.";
              }
              leaf create-time {
                type pon-ctrl:pon-relay-attribute-string;
                description
                  "PPPoE create time.";
              }
              leaf reset-count {
                type uint32;
                description
                  "PPPoE reset count.";
              }
              leaf last-success-time {
                type pon-ctrl:pon-relay-attribute-string;
                description
                  "PPPoE last success time.";
              }
              container statistics {
                description
                  "PPPoE statistics as viewed by the CPE address.";
                uses pon-ctrl:pppoe-counters-grouping;
              }
            }
            container statistics {
              description
                "PPPoE statistics as viewed by the Datalink.";
              uses pon-ctrl:pppoe-counters-grouping;
            }
          }
          list datalink-dhcpv6 {
            key "name";
            description
              "List of Datalink DHCPv6.";
            leaf name {
              type pon-ctrl:name-string;
              description
                "Name of the Datalink.";
            }
            list datalink-dhcpv6-state {
              key cpe-mac;
              description
                "List of CPE states.";
              leaf cpe-mac {
                type yang:mac-address;
                description
                  "Customer premises equipment MAC address.";
              }
              leaf oper-state {
                type pon-ctrl:dhcpv6-oper-state;
                description
                  "Operational state of DHCPv6 relay.";
              }
              leaf client-address {
                type pon-ctrl:pon-relay-attribute-string;
                description
                  "DHCPv6 client address.";
              }
              leaf client-requested-address {
                type pon-ctrl:pon-relay-attribute-string;
                description
                  "DHCPv6 client requested address.";
              }
              leaf client-identifier {
                type pon-ctrl:pon-relay-attribute-string;
                description
                  "DHCPv6 client identifier.";
              }
              leaf server-identifier {
                type pon-ctrl:pon-relay-attribute-string;
                description
                  "DHCPv6 server identifier.";
              }
              leaf t1-time {
                type pon-ctrl:pon-relay-attribute-string;
                description
                  "DHCPv6 T1 time.";
              }
              leaf t2-time {
                type pon-ctrl:pon-relay-attribute-string;
                description
                  "DHCPv6 T2 time.";
              }
              leaf valid-lifetime {
                type pon-ctrl:pon-relay-attribute-string;
                description
                  "DHCPv6 valid lifetime.";
              }
              leaf preferred-lifetime {
                type pon-ctrl:pon-relay-attribute-string;
                description
                  "DHCPv6 preferred lifetime.";
              }
              leaf create-time {
                type pon-ctrl:pon-relay-attribute-string;
                description
                  "DHCPv6 create time.";
              }
              leaf last-success-time {
                type pon-ctrl:pon-relay-attribute-string;
                description
                  "DHCPv6 last success time.";
              }
              leaf reset-count {
                type uint32;
                description
                  "DHCPv6 reset count.";
              }
              container statistics {
                description
                  "DHCPv6 relay statistics as viewed by the CPE address.";
                uses pon-ctrl:dhcpv6-counters-grouping;
              }
            }
            container statistics {
              description
                "DHCPv6 relay statistics as viewed by the Datalink.";
              uses pon-ctrl:dhcpv6-counters-grouping;
            }
          }
        }
        container uni-ports {
          description
            "The state data for all UNI Ports.";
          list uni-port {
            key "name";
            description
              "List of UNI Ports.";
            leaf name {
              type pon-ctrl:name-string;
              description
                "The numerical identifier of this UNI Port.";
            }
            leaf oper-state {
              type pon-ctrl:uni-port-oper-state;
              description
                "Operational state of the UNI Port.";
            }
            leaf speed {
              type pon-ctrl:uni-port-oper-speed;
              description
                "Operational speed of the UNI Port.";
            }
            leaf duplex {
              type pon-ctrl:uni-port-oper-duplex;
              description
                "Operational duplex of the UNI Port.";
            }
            leaf previous-oper-state {
              type pon-ctrl:uni-port-oper-state;
              description
                "Previous operational state of the UNI Port.";
            }
            leaf oper-state-change-reason {
              type uni-port-oper-state-change-reason;
              description
                "Reason for the oper-state change.";
            }
            container xcvr-data {
              description
                "The Small Form-factor (SFP) Pluggable transceiver data
                 for this UNI Port.
                 Only applicable to ONUs with pluggable transceivers.";
              leaf vendor-name {
                type string;
                description
                  "The vendor name of the transceiver.";
              }
              leaf vendor-part-number {
                type string;
                description
                  "The vendor part number of the transceiver.";
              }
              leaf vendor-revision {
                type string;
                description
                  "The vendor revision of the transceiver.";
              }
              leaf vendor-serial-number {
                type string;
                description
                  "The vendor serial number of the transceiver.";
              }
              leaf type {
                type pon-ctrl:onu-pluggable-xcvr-type;
                description
                  "The type of the transceiver.";
              }
            }
            container statistics {
              description
                "UNI Port statistics.";
              uses pon-ctrl:uni-port-packet-counters-grouping;
              leaf ds-frames-broadcast {
                type yang:counter64;
                description
                  "Total number of downstream broadcast packets transmitted by the UNI Port.";
              }
              leaf us-frames-broadcast {
                type yang:counter64;
                description
                  "Total number of upstream broadcast packets transmitted by the UNI Port.";
              }
              leaf ds-frames-multicast {
                type yang:counter64;
                description
                  "Total number of downstream multicast packets transmitted by the UNI Port.";
              }
              leaf us-frames-multicast {
                type yang:counter64;
                description
                  "Total number of upstream multicast packets transmitted by the UNI Port.";
              }
              leaf ds-frames-crc-error {
                type yang:counter64;
                description
                  "Total number of downstream packets received by the UNI Port that had a bad
                   frame check sequence.";
              }
              leaf us-frames-crc-error {
                type yang:counter64;
                description
                  "Total number of upstream packets received by the UNI Port that had a bad
                   frame check sequence.";
              }
              leaf ds-drop-events {
                type yang:counter64;
                description
                  "Total number of events in which downstream packets were dropped on the UNI Port
                   due to a lack of resources. This is not necessarily the number of downstream packets
                   dropped.";
              }
              leaf us-drop-events {
                type yang:counter64;
                description
                  "Total number of events in which upstream packets were dropped on the UNI Port
                   due to a lack of resources. This is not necessarily the number of upstream packets
                   dropped.";
              }
              leaf last-clear-time {
                type string;
                description
                  "Time when the statistics were last cleared.";
              }
              leaf time {
                type string;
                description
                  "Time when the statistics were last collected.";
              }
            }
            leaf alarms {
              type uni-port-alarm-bit-map;
              description
                "Bit map of alarm conditions currently active on this UNI port.";
            }
          }
        }
        container diagnostic-data {
          description
            "The cached diagnostic data for this ONU.";
          leaf olt-rx-power {
            type cntypes:decimal-2-dig;
            units "dBm";
            description
              "The OLT's Rx optical power for this ONU in dBm.";
          }
          leaf olt-tx-power {
            type cntypes:decimal-2-dig;
            units "dBm";
            description
              "The OLT's Tx optical power in dBm.";
          }
          leaf onu-rx-power {
            type cntypes:decimal-2-dig;
            units "dBm";
            description
              "The ONU's Rx optical power in dBm.";
          }
          leaf onu-tx-power {
            type cntypes:decimal-2-dig;
            units "dBm";
            description
              "The ONU's Tx optical power in dBm.";
          }
          leaf laser-bias-current {
            type cntypes:decimal-2-dig;
            units "mA";
            description
              "The ONU's laser bias current in mA.";
          }
          leaf power-feed-voltage {
            type cntypes:decimal-2-dig;
            units "V";
            description
              "The ONU's power feed voltage in V.";
          }
          leaf temperature {
            type int16;
            units "C";
            description
              "The ONU's temperature in degrees C.";
          }
          leaf uptime {
            type uint64;
            units "seconds";
            description
              "The ONU's uptime in seconds.";
          }
          leaf equalization-delay {
            type uint16;
            units "timeslots";
            description
              "The ONU’s equalization delay (in timeslots) as detected by the OLT.";
          }
          leaf one-way-delay {
            type cntypes:decimal-3-dig;
            units "microseconds";
            description
              "The calculated transit delay on the PON between the OLT and ONU in microseconds.
               This is derived from the equalization-delay value.";
          }
          leaf fiber-distance {
            type cntypes:decimal-3-dig;
            units "kilometers";
            description
              "The calculated distance between the OLT and ONU in kilometers.
               This is derived from the equalization-delay value.";
          }
          leaf time-stamp {
            type string;
            description
              "The time the data was cached.";
          }
        }
        container statistics {
          description
            "ONU performance monitoring history bin statistics.";
          leaf last-clear-time {
            type string;
            description
              "Time when the statistics were last cleared.";
          }
          leaf bin-interval {
            type uint8;
            description
              "Current bin interval. Only applies if statistics mode is binning.";
          }
          leaf rx-corrected-bytes {
            type uint64;
            description
              "Counts the number of received bytes that were corrected by the FEC function.";
          }
          leaf rx-corrected-code-words {
            type uint64;
            description
              "Counts the number of received code words that were corrected by the FEC function.";
          }
          leaf rx-uncorrectable-code-words {
            type uint64;
            description
              "Counts received errored code words that could not be corrected by the FEC function";
          }
          leaf rx-total-code-words {
            type uint64;
            description
              "Counts the total received code words.";
          }
          leaf rx-fec-seconds {
            type uint64;
            units "seconds";
            description
              "Counts number of seconds during which there was an FEC anomaly.";
          }
          leaf suspect {
            type boolean;
            description
              "Indicates if this is a partial bin sample.";
          }
          leaf time {
            type string;
            description
              "Time when the statistics were last collected.";
          }
        }
      }
    }
  }

  rpc pon-ctrl-olt-reset {
    description 
      "Reset an OLT.";
    input {
      leaf olt {
        type pon-ctrl:olt-ref;
        mandatory true;
        description
          "Name of the OLT.";
      }
    }
    output {
      leaf status {
        type string; 
        description 
          "Status of the OLT reset operation.";
      }
    }
  }

  rpc pon-ctrl-onu-reset {
    description 
      "Reset an ONU.";
    input {
      leaf olt {
        type pon-ctrl:olt-ref;
        mandatory true;
        description
          "Name of the OLT.";
      }
      leaf onu {
        type pon-ctrl:onu-ref;
        mandatory true;
        description
          "Name of the ONU.";
      }
    }
    output {
      leaf status {
        type string; 
        description 
          "Status of the ONU reset operation.";
      }
    }
  }

  rpc pon-ctrl-radius-server-statistics-clear {
    description
      "Clear the statistics of a RADIUS Server or RADIUS Server hostname.";
    input {
      leaf radius-server {
        type pon-ctrl:radius-server-ref;
        mandatory true;
        description
          "Name of the RADIUS Server.";
      }
      leaf host {
        type inet:host;
        description
          "RADIUS server host address.";
      }
      leaf port {
        type inet:port-number;
        description
          "RADIUS server port.";
      }
    }
    output {
      leaf status {
        type string;
        description
          "Status of the statistics clear operation.";
      }
    }
  }

  rpc pon-ctrl-olt-statistics-clear {
    description 
      "Clear the statistics of an OLT.";
    input {
      leaf olt {
        type pon-ctrl:olt-ref;
        mandatory true;
        description
          "Name of the OLT.";
      }
      leaf clear-pon-statistics{
        type boolean;
        description
          "Indicates whether to clear OLT PON statistics (if true) or OLT NNI statistics (if false).
           If not present, both PON and NNI statistics are cleared.";
      }
    }
    output {
      leaf status {
        type string; 
        description 
          "Status of the statistics clear operation.";
      }
    }
  }

  rpc pon-ctrl-onu-statistics-clear {
    description 
      "Clear the statistics of an ONU, or the statistics
       of a Datalink on the ONU.";
    input {
      leaf olt {
        type pon-ctrl:olt-ref;
        mandatory true;
        description
          "Name of the OLT.";
      }
      leaf onu {
        type pon-ctrl:onu-ref;
        mandatory true;
        description
          "Name of the ONU.";
      }
      leaf datalink {
        type pon-ctrl:datalink-ref;
        description
          "Name of the Datalink on the ONU.";
      }
      leaf xgem-port-id {
        type uint16;
        description
          "The ID of the XGEM port.";
      }
    }
    output {
      leaf status {
        type string; 
        description 
          "Status of the statistics clear operation.";
      }
    }
  }

  rpc pon-ctrl-relay-statistics-clear {
    description
      "Clear the authentication and/or DHCP and/or DHCPv6 and/or PPPoE statistics of the OLT or DATALINK or CPE MAC.";
    input {
      leaf olt {
        type pon-ctrl:olt-ref;
        mandatory true;
        description
          "Name of the OLT.";
      }
      leaf onu {
        type pon-ctrl:onu-ref;
        description
          "Name of the ONU.";
      }
      leaf datalink {
        type pon-ctrl:datalink-ref;
        description
          "Name of the Datalink on the ONU.";
      }
      leaf clear-authenticator {
        type boolean;
        description
          "When true, clear statistics is for authenticator.";
      }
      leaf clear-l2-dhcp-relay {
        type boolean;
        description
          "When true, clear statistics is for DHCP.";
      }
      leaf cpe-mac {
        type yang:mac-address;
        description
          "Customer premises equipment MAC address.";
      }
      leaf clear-pppoe {
        type boolean;
        description
          "When true, clear statistics is for PPPoE.";
      }
      leaf clear-dhcpv6 {
        type boolean;
        description
          "When true, clear statistics is for DHCPv6.";
      }
    }
    output {
      leaf status {
        type string;
        description
          "Status of the statistics clear operation.";
      }
    }
  }

  rpc pon-ctrl-olt-firmware-install {
    description
      "Install new firmware on an OLT.";
    input {
      leaf olt {
        type pon-ctrl:olt-ref;
        mandatory true;
        description
          "Name of the OLT.";
      }
      leaf defer-activation {
        type boolean;
        description
          "When true, OLT firmware activation is deferred until explicitly invoked.";
      }
    }
    output {
      leaf status {
        type string;
        description
          "Status of the OLT firmware install operation.";
      }
    }
  }

  rpc pon-ctrl-olt-firmware-activate {
    description
      "Activate the specified firmware version on an OLT.";
    input {
      leaf olt {
        type pon-ctrl:olt-ref;
        mandatory true;
        description
          "Name of the OLT.";
      }
      leaf firmware-version {
        type string;
        mandatory true;
        description
          "Version of firmware to activate on this OLT.
           Firmware must already be installed.";
      }
    }
    output {
      leaf status {
        type string;
        description
          "Status of the OLT firmware activate operation.";
      }
    }
  }

  rpc pon-ctrl-onu-firmware-install {
    description
      "Install new firmware on an ONU.";
    input {
      leaf olt {
        type pon-ctrl:olt-ref;
        mandatory true;
        description
          "Name of the OLT.";
      }
      leaf onu {
        type pon-ctrl:onu-ref;
        mandatory true;
        description
          "Name of the ONU.";
      }
      leaf firmware-file-name {
        type string;
        description
          "Name of the firmware file to install on this ONU.";
      }
      leaf defer-activation {
        type boolean;
        description
          "When true, ONU firmware activation is deferred until explicitly invoked.";
      }
      leaf update-expected-firmware-version {
        type boolean;
        description
          "When true, ONU firmware activation will set the expected
           firmware version to the firmware version being activated.";
      }
    }
    output {
      leaf status {
        type string;
        description
          "Status of the ONU firmware install operation.";
      }
    }
  }

  rpc pon-ctrl-onu-firmware-activate {
    description
      "Activate the specified firmware version on an ONU.";
    input {
      leaf olt {
        type pon-ctrl:olt-ref;
        mandatory true;
        description
          "Name of the OLT.";
      }
      leaf onu {
        type pon-ctrl:onu-ref;
        mandatory true;
        description
          "Name of the ONU.";
      }
      leaf firmware-version {
        type string;
        mandatory true;
        description
          "Version of firmware to activate on this ONU.
           Firmware must already be installed.";
      }
      leaf update-expected-firmware-version {
        type boolean;
        description
          "When true, ONU firmware activation will set the expected
           firmware version to the firmware version being activated.";
      }
    }
    output {
      leaf status {
        type string;
        description
          "Status of the ONU firmware activate operation.";
      }
    }
  }

  rpc pon-ctrl-onu-admission-control {
    description
      "Control whether an ONU is allowed to register or disallowed
       from registering on an OLT.";
    input {
      leaf olt {
        type pon-ctrl:olt-ref;
        mandatory true;
        description
          "Name of the OLT.";
      }
      leaf onu {
        type pon-ctrl:onu-ref;
        mandatory true;
        description
          "Name of the ONU.";
      }
      leaf registration-allowed {
        type boolean;
        mandatory true;
        description
          "When true, an ONU is allowed to register. When false,
           an ONU is disallowed from registering. An ONU that is
           disallowed from registering on the OLT will show up in
           a 'Deregistered' state with a deregister-reason of
           'Disallowed'. Note that disallowing an ONU from being
           admitted to the OLT does not persist over OLT
           reboots.";
      }
    }
    output {
      leaf status {
        type string;
        description
          "Status of the ONU admission control operation.";
      }
    }
  }

  rpc pon-ctrl-nni-network-statistics-clear {
    description
      "Clear the statistics of an NNI Network.";
    input {
      leaf olt {
        type pon-ctrl:olt-ref;
        mandatory true;
        description
          "Name of the OLT.";
      }
      leaf nni-network {
        type pon-ctrl:nni-network-ref;
        mandatory true;
        description
          "Name of the NNI Network.";
      }
      leaf flooding-statistics {
        type boolean;
        mandatory true;
        description
          "When true, flooding statistics on the NNI Network are cleared.";
      }
    }
    output {
      leaf status {
        type string;
        description
          "Status of the statistics clear operation.";
      }
    }
  }

  rpc pon-ctrl-datalink-authentication-reset {
    description
      "Reset authentication on the selected CPE.";
    input {
      leaf olt {
        type pon-ctrl:olt-ref;
        description
          "Name of the OLT.";
      }
      leaf onu {
        type pon-ctrl:onu-ref;
        description
          "Name of the ONU.";
      }
      leaf datalink {
        type pon-ctrl:datalink-ref;
        description
          "Name of the Datalink.";
      }
      leaf cpe-mac {
        type yang:mac-address;
        description
          "Customer premises equipment MAC address.";
      }
    }
    output {
      leaf status {
        type string;
        description
          "Status of the reset operation.";
      }
    }
  }

  rpc pon-ctrl-datalink-dhcp-reset {
    description
      "Reset DHCP relay on the selected CPE.";
    input {
      leaf olt {
        type pon-ctrl:olt-ref;
        description
          "Name of the OLT.";
      }
      leaf onu {
        type pon-ctrl:onu-ref;
        description
          "Name of the ONU.";
      }
      leaf datalink {
        type pon-ctrl:datalink-ref;
        description
          "Name of the Datalink.";
      }
      leaf cpe-mac {
        type yang:mac-address;
        description
          "Customer premises equipment MAC address.";
      }
    }
    output {
      leaf status {
        type string;
        description
          "Status of the reset operation.";
      }
    }
  }

  rpc pon-ctrl-datalink-dhcpv6-reset {
    description
      "Reset DHCPv6 on the selected CPE.";
    input {
      leaf olt {
        type pon-ctrl:olt-ref;
        description
          "Name of the OLT.";
      }
      leaf onu {
        type pon-ctrl:onu-ref;
        description
          "Name of the ONU.";
      }
      leaf datalink {
        type pon-ctrl:datalink-ref;
        description
          "Name of the Datalink.";
      }
      leaf cpe-mac {
        type yang:mac-address;
        description
          "Customer premises equipment MAC address.";
      }
    }
    output {
      leaf status {
        type string;
        description
          "Status of the reset operation.";
      }
    }
  }

  rpc pon-ctrl-relay-state-clear {
    description
      "Clear the CPE state for authentication and/or DHCP and/or DHCPv6 and/or PPPoE.
       Authentication state is cleared if it is not success.
       DHCP state is cleared if it is not acknowledged.
       DHCPv6 state is cleared if it is not bound.
       PPPoE state is cleared if it is not session.";
    input {
      leaf olt {
        type pon-ctrl:olt-ref;
        mandatory true;
        description
          "Name of the OLT.";
      }
      leaf onu {
        type pon-ctrl:onu-ref;
        mandatory true;
        description
          "Name of the ONU.";
      }
      leaf datalink {
        type pon-ctrl:datalink-ref;
        mandatory true;
        description
          "Name of the Datalink on the ONU.";
      }
      leaf clear-authenticator {
        type boolean;
        description
          "When true, clear is for authenticator.";
      }
      leaf clear-l2-dhcp-relay {
        type boolean;
        description
          "When true, clear is for DHCP.";
      }
      leaf clear-pppoe {
        type boolean;
        description
          "When true, clear is for PPPoE.";
      }
      leaf clear-dhcpv6 {
        type boolean;
        description
          "When true, clear is for DHCPv6.";
      }
      leaf cpe-mac {
        type yang:mac-address;
        description
          "Customer premises equipment MAC address.";
      }
    }
    output {
      leaf status {
        type string;
        description
          "Status of the clear operation.";
      }
    }
  }

  rpc pon-ctrl-datalink-pppoe-reset {
    description
      "Reset PPPoE on the selected CPE.";
    input {
      leaf olt {
        type pon-ctrl:olt-ref;
        mandatory true;
        description
          "Name of the OLT.";
      }
      leaf onu {
        type pon-ctrl:onu-ref;
        mandatory true;
        description
          "Name of the ONU.";
      }
      leaf datalink {
        type pon-ctrl:datalink-ref;
        mandatory true;
        description
          "Name of the Datalink.";
      }
      leaf cpe-mac {
        type yang:mac-address;
        description
          "Customer premises equipment MAC address.";
      }
    }
    output {
      leaf status {
        type string;
        description
          "Status of the reset operation.";
      }
    }
  }

  rpc pon-ctrl-olt-inband-management {
    description
      "Get/Set the OLT in-band management TPID and VID.";
    input {
      leaf action {
        type pon-ctrl:inband-management-action;
        mandatory true;
        description
          "Action to perform on the OLT.";
      }
      leaf olt {
        type pon-ctrl:olt-ref;
        mandatory true;
        description
          "Name of the OLT.";
      }
      leaf management-tpid {
        type pon-ctrl:tpid;
        must "../action = 'set'" {
          error-message
            "management-tpid can be set only if in-band mangement action is 'set'.";
        }
        description
          "TPID to be configured for in-band management.";
      }
      leaf management-vid {
        type mef-fp:vlan-id;
        must "../action = 'set'" {
          error-message
            "management-vid can be set only if in-band mangement action is 'set'.";
        }
        description
          "VID to be configured for in-band management.";
      }
    }
    output {
      leaf status {
        type string;
        description
          "Status of the OLT in-band management get/set operation.";
      }
      leaf management-tpid {
        type pon-ctrl:tpid;
        description
          "TPID configured for in-band management.";
      }
      leaf management-vid {
        type mef-fp:vlan-id;
        description
          "VID configured for in-band management.";
      }
    }
  }

  rpc pon-ctrl-uni-port-statistics-clear {
    description
      "Clear the statistics of a UNI Port.";
    input {
      leaf olt {
        type pon-ctrl:olt-ref;
        mandatory true;
        description
          "Name of the OLT.";
      }
      leaf onu {
        type pon-ctrl:onu-ref;
        mandatory true;
        description
          "Name of the ONU.";
      }
      leaf uni-port {
        type pon-ctrl:uni-port-ref;
        mandatory true;
        description
          "ID of the UNI Port on the ONU.";
      }
    }
    output {
      leaf status {
        type string;
        description
          "Status of the statistics clear operation.";
      }
    }
  }

  rpc pon-ctrl-olt-diagnostic-data-get {
    description
      "Retrieves current diagnostic data for the OLT.";
    input {
      leaf olt {
        type pon-ctrl:olt-ref;
        mandatory true;
        description
          "Name of the OLT.";
      }
    }
    output {
      leaf asic-temperature {
        type int16;
        units "C";
        description
          "The OLT's ASIC temperature in degrees C.";
      }
      leaf xcvr-temperature {
        type int16;
        units "C";
        description
          "The OLT's transceiver temperature in degrees C.";
      }
      leaf laser-temperature {
        type int16;
        units "C";
        description
          "The OLT's laser temperature in degrees C.";
      }
      leaf vcc {
        type cntypes:decimal-2-dig;
        units "mV";
        description
          "The OLT's VCC in mV.";
      }
      leaf tec-current {
        type cntypes:decimal-2-dig;
        units "uA";
        description
          "The OLT's TEC current in uA.";
      }
      leaf transmit-bias {
      type cntypes:decimal-2-dig;
      units "uA";
      description
        "The OLT's transmit bias current in uA.";
      }
      leaf idle-receive-power {
        type cntypes:decimal-2-dig;
        units "dBm";
        description
          "The OLT's idle receive power in dBm.";
      }
      leaf transmit-power {
        type cntypes:decimal-2-dig;
        units "dBm";
        description
          "The OLT's transmit power in dBm.";
      }
      leaf last-shutdown-reason {
        type string;
        description
          "The reason for the latest shutdown of the OLT's laser.";
      }
      leaf is-laser-shutdown {
        type boolean;
        description
          "When true, indicates that the OLT's laser is currently shutdown.
           When false, indicates that the OLT's laser is currently active.";
      }
      leaf uptime {
        type uint64;
        units "seconds";
        description
          "The OLT's uptime in seconds.";
      }
      leaf low-receive-power {
        type cntypes:decimal-2-dig;
        units "dBm";
        description
          "The OLT's low receive optical power in dBm for the current 15 minute interval.";
      }
      leaf high-receive-power {
        type cntypes:decimal-2-dig;
        units "dBm";
        description
          "The OLT's high receive optical power in dBm for the current 15 minute interval.";
      }
    }
  }

  rpc pon-ctrl-onu-diagnostic-data-get {
    description
      "Retrieves current diagnostic data for the ONU if available otherwise
        latest cached values from ANI-G test are reported.";
    input {
      leaf olt {
        type pon-ctrl:olt-ref;
        mandatory true;
        description
          "Name of the OLT.";
      }
      leaf onu {
        type pon-ctrl:onu-ref;
        mandatory true;
        description
          "Name of the ONU.";
      }
    }
    output {
      leaf olt-rx-power {
        type cntypes:decimal-2-dig;
        units "dBm";
        description
          "The OLT's Rx optical power for this ONU in dBm.";
      }
      leaf olt-tx-power {
        type cntypes:decimal-2-dig;
        units "dBm";
        description
          "The OLT's Tx optical power in dBm.";
      }
      leaf onu-rx-power {
        type cntypes:decimal-2-dig;
        units "dBm";
        description
          "The ONU's Rx optical power in dBm.";
      }
      leaf onu-tx-power {
        type cntypes:decimal-2-dig;
        units "dBm";
        description
          "The ONU's Tx optical power in dBm.";
      }
      leaf laser-bias-current {
        type cntypes:decimal-2-dig;
        units "mA";
        description
          "The ONU's laser bias current in mA.
            This is a cached value from the last ANI-G test.";
      }
      leaf power-feed-voltage {
        type cntypes:decimal-2-dig;
        units "V";
        description
          "The ONU's power feed voltage in V.
            This is a cached value from the last ANI-G test.";
      }
      leaf temperature {
        type int16;
        units "C";
        description
          "The ONU's temperature in degrees C.
            This is a cached value from the last ANI-G test.";
      }
      leaf uptime {
        type uint64;
        units "seconds";
        description
          "The ONU's uptime in seconds.";
      }
      leaf equalization-delay {
        type uint16;
        units "timeslots";
        description
          "The ONU’s equalization delay (in timeslots) as detected by the OLT.";
      }
      leaf one-way-delay {
        type cntypes:decimal-3-dig;
        units "microseconds";
        description
          "The calculated transit delay on the PON between the OLT and ONU in microseconds.
            This is derived from the equalization-delay value.";
      }
      leaf fiber-distance {
        type cntypes:decimal-3-dig;
        units "kilometers";
        description
          "The calculated distance between the OLT and ONU in kilometers.
            This is derived from the equalization-delay value.";
      }
      leaf time-stamp {
        type string;
        description
          "The time the data was cached.";
      }
    }
  }

  rpc pon-ctrl-onu-statistics-get {
    description
      "Retrieves ONU performance monitoring statistics for the current bin.";
    input {
      leaf olt {
        type pon-ctrl:olt-ref;
        mandatory true;
        description
          "Name of the OLT.";
      }
      leaf onu {
        type pon-ctrl:onu-ref;
        mandatory true;
        description
          "Name of the ONU.";
      }
    }
    output {
      leaf rx-corrected-bytes {
        type uint64;
        description
          "Counts the number of received bytes that were corrected by the FEC function.";
      }
      leaf rx-corrected-code-words {
        type uint64;
        description
          "Counts the number of received code words that were corrected by the FEC function.";
      }
      leaf rx-uncorrectable-code-words {
        type uint64;
        description
          "Counts received errored code words that could not be corrected by the FEC function";
      }
      leaf rx-total-code-words {
        type uint64;
        description
          "Counts the total received code words.";
      }
      leaf rx-fec-seconds {
        type uint64;
        units "seconds";
        description
          "Counts number of seconds during which there was an FEC anomaly.";
      }
      leaf last-clear-time {
        type string;
        description
          "Time when the statistics were last cleared.";
      }
      leaf bin-interval {
        type uint8;
        description
          "Current bin interval. Only applies if statistics mode is binning.";
      }
      leaf suspect {
        type boolean;
        description
          "Indicates if this is a partial bin sample.";
      }
    }
  }

  rpc pon-ctrl-datalink-statistics-get {
    description
      "Retrieves Datalink statistics for the current bin.";
    input {
      leaf olt {
        type pon-ctrl:olt-ref;
        mandatory true;
        description
          "Name of the OLT.";
      }
      leaf onu {
        type pon-ctrl:onu-ref;
        mandatory true;
        description
          "Name of the ONU.";
      }
      leaf datalink {
        type pon-ctrl:datalink-ref;
        mandatory true;
        description
          "Name of the Datalink.";
      }
    }
    output {
      uses pon-ctrl:packet-counters-grouping;
      uses pon-ctrl:phy-counters-grouping;
      leaf rx-fec-good-blocks {
        type yang:counter64;
        description
          "Count of FEC blocks received without errors.";
      }
      leaf rx-fec-corrected-blocks {
        type yang:counter64;
        description
          "Count of FEC blocks received with errors that were correctable.";
      }
      leaf rx-fec-uncorrectable-blocks {
        type yang:counter64;
        description
          "Count of FEC blocks received with errors that were not correctable.";
      }
      leaf rx-fec-corrections {
        type yang:counter64;
        description
          "Count of FEC blocks received with correctable errors that were corrected.";
      }
      leaf tx-octets-multi-broadcast {
        type yang:counter64;
        description
          "Count of multicast and broadcast octets transmitted.";
      }
      leaf tx-control-octets {
        type yang:counter64;
        description
          "Count of control octets transmitted.";
      }
      leaf tx-plain-octets {
        type yang:counter64;
        description
          "Count of plain octets transmitted.";
      }
      leaf tx-encrypted-octets {
        type yang:counter64;
        description
          "Count of encrypted octets transmitted.";
      }
      leaf tx-oam-frames {
        type yang:counter64;
        description
          "Count of OAM frames transmitted on the interface.";
      }
      leaf tx-grant-ups-tq {
        type yang:counter64;
        description
          "Count of tq or upstreams slots granted to the ONUs.";
      }
      leaf tx-octets-unicast {
        type yang:counter64;
        description
          "Total number of unicast octets transmitted.";
      }
      leaf tx-frames-unicast {
        type yang:counter64;
        description
          "Count of unicast frames transmitted.";
      }
      leaf tx-frames-multicast {
        type yang:counter64;
        description
          "Count of multicast frames transmitted.";
      }
      leaf tx-frames-broadcast {
        type yang:counter64;
        description
          "Count of broadcast frames transmitted.";
      }
      leaf rx-control-octets {
        type yang:counter64;
        description
          "Count of control octets received.";
      }
      leaf rx-security-drop-octets {
        type yang:counter64;
        description
          "Count of security drop octets received.";
      }
      leaf rx-octets-unicast {
        type yang:counter64;
        description
          "Count of unicast octets received.";
      }
      leaf rx-octets-multi-broadcast {
        type yang:counter64;
        description
          "Count of multicast and broadcast octets received.";
      }
      leaf rx-plain-octets {
        type yang:counter64;
        description
          "Count of plain octets received.";
      }
      leaf rx-encrypted-octets {
        type yang:counter64;
        description
          "Count of encrypted octets received.";
      }
      leaf rx-overflow-octets {
        type yang:counter64;
        description
          "Count of overflow octets received.";
      }
      leaf rx-idle-octets {
        type yang:counter64;
        description
          "Count of idle octets received.";
      }
      leaf rx-key-mismatch-octets {
        type yang:counter64;
        description
          "Count of key mismatch octets received.";
      }
      leaf rx-bad-icv-drops {
        type yang:counter64;
        description
          "Count of frames received on the interface and dropped due to bad icv.";
      }
      leaf rx-oam-frames {
        type yang:counter64;
        description
          "Count of OAM frames received on the interface.";
      }
      leaf rx-all-bw-reqs {
        type yang:counter64;
        description
          "Count of all bandwidth requests received.";
      }
      leaf last-clear-time {
        type string;
        description
          "Time when the statistics were last cleared.";
      }
      leaf rx-mpcp-octets {
        type yang:counter64;
        description
          "Count of mpcp octets received.";
      }
    }
  }

  rpc pon-ctrl-olt-pon-statistics-get {
    description
      "Retrieves OLT PON statistics for the current bin.";
    input {
      leaf olt {
        type pon-ctrl:olt-ref;
        mandatory true;
        description
          "Name of the OLT.";
      }
    }
    output {
      uses pon-ctrl:packet-counters-grouping;
      uses pon-ctrl:phy-counters-grouping;
      leaf rx-fec-good-blocks {
        type yang:counter64;
        description
          "Count of FEC blocks received without errors.";
      }
      leaf rx-fec-corrected-blocks {
        type yang:counter64;
        description
          "Count of FEC blocks received with errors that were correctable.";
      }
      leaf rx-fec-uncorrectable-blocks {
        type yang:counter64;
        description
          "Count of FEC blocks received with errors that were not correctable.";
      }
      leaf rx-fec-corrections {
        type yang:counter64;
        description
          "Count of FEC blocks received with correctable errors that were corrected.";
      }
      leaf rx-octets-idle {
        type yang:counter64;
        description
          "Count of idle octets received. Idle octets are used to fill data
            gaps during transmission. Idle octets are dropped by the receiver.";
      }
      leaf tx-octets-idle {
        type yang:counter64;
        description
          "Count of idle octets transmitted. Idle octets are used to fill data
            gaps during transmission. Idle octets are dropped by the receiver.";
      }
      leaf rx-bw-ethernet-rate {
        type yang:counter64;
        units bps;
        description
          "Received Ethernet bandwidth.";
      }
      leaf tx-bw-ethernet-rate {
        type yang:counter64;
        units bps;
        description
          "Transmitted Ethernet bandwidth.";
      }
      leaf rx-bw-data-rate {
        type yang:counter64;
        units bps;
        description
          "Received data bandwidth.";
      }
      leaf tx-bw-data-rate {
        type yang:counter64;
        units bps;
        description
          "Transmitted data bandwidth.";
      }
      leaf rx-bw-overhead-burst {
        type yang:counter64;
        units bps;
        description
          "Received burst overhead bandwidth.";
      }
      leaf tx-bw-overhead-framing {
        type yang:counter64;
        units bps;
        description
          "Transmitted framing overhead bandwidth.";
      }
      leaf rx-bw-overhead-fec {
        type yang:counter64;
        units bps;
        description
          "Received FEC overhead bandwidth.";
      }
      leaf tx-bw-overhead-fec {
        type yang:counter64;
        units bps;
        description
          "Transmitted FEC overhead bandwidth.";
      }
      leaf rx-bw-overhead-total {
        type yang:counter64;
        units bps;
        description
          "Total received overhead bandwidth.";
      }
      leaf tx-bw-overhead-total {
        type yang:counter64;
        units bps;
        description
          "Total transmitted overhead bandwidth.";
      }
      leaf rx-bw-total-used {
        type yang:counter64;
        units bps;
        description
          "Total receive bandwidth used, includes both data and overhead.";
      }
      leaf tx-bw-total-used {
        type yang:counter64;
        units bps;
        description
          "Total transmit bandwidth used, includes both data and overhead.";
      }
      leaf rx-bw-total-utilization-percent {
        type yang:counter64;
        description
          "Percentage of the total receive bandwidth used.";
      }
      leaf tx-bw-total-utilization-percent {
        type yang:counter64;
        description
          "Percentage of the total transmit bandwidth used.";
      }
      leaf rx-bw-total-free {
        type yang:counter64;
        units bps;
        description
          "Total receive bandwidth free.";
      }
      leaf tx-bw-total-free {
        type yang:counter64;
        units bps;
        description
          "Total transmit bandwidth free.";
      }
      leaf tx-octets-unicast {
        type yang:counter64;
        description
          "Count of unicast octets transmitted.";
      }
      leaf rx-octets-unicast {
        type yang:counter64;
        description
          "Count of unicast octets received.";
      }
      leaf tx-octets-multi-broadcast {
        type yang:counter64;
        description
          "Count of multicast and broadcast octets transmitted.";
      }
      leaf rx-octets-multi-broadcast {
        type yang:counter64;
        description
          "Count of multicast and broadcast octets received.";
      }
      leaf tx-frames-unicast {
        type yang:counter64;
        description
          "Count of unicast frames transmitted.";
      }
      leaf tx-frames-broadcast {
        type yang:counter64;
        description
          "Count of broadcast frames transmitted.";
      }
      leaf tx-frames-multicast {
        type yang:counter64;
        description
          "Count of multicast frames transmitted.";
      }
      leaf last-clear-time {
        type string;
        description
          "Time when the statistics were last cleared.";
      }
      leaf tx-control-octets {
        type yang:counter64;
        description
          "Count of control octets transmitted.";
      }
      leaf tx-plain-octets {
        type yang:counter64;
        description
          "Count of plain octets transmitted.";
      }
      leaf tx-encrypted-octets {
        type yang:counter64;
        description
          "Count of encrypted octets transmitted.";
      }
      leaf tx-mpcp-octets {
        type yang:counter64;
        description
          "Count of mpcp octets transmitted.";
      }
      leaf tx-oam-frames {
        type yang:counter64;
        description
          "Count of OAM frames transmitted on the interface.";
      }
      leaf tx-grant-ups-tq {
        type yang:counter64;
        description
          "Count of tq or upstreams slots granted to the ONUs.";
      }
      leaf rx-control-octets {
        type yang:counter64;
        description
          "Count of control octets received.";
      }
      leaf rx-security-drop-octets {
        type yang:counter64;
        description
          "Count of security drop octets received.";
      }
      leaf rx-plain-octets {
        type yang:counter64;
        description
          "Count of plain octets received.";
      }
      leaf rx-mpcp-octets {
        type yang:counter64;
        description
          "Count of mpcp octets received.";
      }
      leaf rx-encrypted-octets {
        type yang:counter64;
        description
          "Count of encrypted octets received.";
      }
      leaf rx-overflow-octets {
        type yang:counter64;
        description
          "Count of overflow octets received.";
      }
      leaf rx-key-mismatch-octets {
        type yang:counter64;
        description
          "Count of key mismatch octets received.";
      }
      leaf rx-unmatched-drops {
        type yang:counter64;
        description
          "Count of frames received on the interface and dropped due to no match.";
      }
      leaf rx-bad-icv-drops {
        type yang:counter64;
        description
          "Count of frames received on the interface and dropped due to bad icv.";
      }
      leaf rx-oam-frames {
        type yang:counter64;
        description
          "Count of OAM frames received on the interface.";
      }
      leaf rx-all-bw-reqs {
        type yang:counter64;
        description
          "Count of all bandwidth requests received.";
      }
    }
  }

  rpc pon-ctrl-olt-nni-statistics-get {
    description
      "Retrieves OLT NNI statistics for the current bin.";
    input {
      leaf olt {
        type pon-ctrl:olt-ref;
        mandatory true;
        description
          "Name of the OLT.";
      }
    }
    output {
      uses pon-ctrl:packet-counters-grouping;
      leaf rx-oam {
        type yang:counter64;
        description
          "Count of OAM frames received on the interface.";
      }
      leaf tx-oam {
        type yang:counter64;
        description
          "Count of OAM frames transmitted on the interface.";
      }
      leaf rx-mac-control-frames {
        type yang:counter64;
        description
          "Count of MAC Control frames received on the interface.";
      }
      leaf rx-filtered-frames {
        type yang:counter64;
        description
          "Count of frames received on the interface but filtered (not forwarded).";
      }
      leaf rx-crc32-drops {
        type yang:counter64;
        description
          "Count of frames received on the interface and dropped due to invalid CRC32.";
      }
      leaf rx-overflow-drops {
        type yang:counter64;
        description
          "Count of frames received on the interface and dropped due to input queues being full.";
      }
      leaf rx-too-short-drops {
        type yang:counter64;
        description
          "Count of frames received on the interface and dropped due to the frame being too short.";
      }
      leaf rx-too-long-drops {
        type yang:counter64;
        description
          "Count of frames received on the interface and dropped due to the frame being too long.";
      }
      leaf tx-octets-unicast {
        type yang:counter64;
        description
          "Count of unicast octets transmitted.";
      }
      leaf rx-octets-unicast {
        type yang:counter64;
        description
          "Count of unicast octets received.";
      }
      leaf tx-octets-broadcast {
        type yang:counter64;
        description
          "Count of broadcast octets transmitted.";
      }
      leaf rx-octets-broadcast {
        type yang:counter64;
        description
          "Count of broadcast octets received.";
      }
      leaf tx-octets-multicast {
        type yang:counter64;
        description
          "Count of multicast octets transmitted.";
      }
      leaf rx-octets-multicast {
        type yang:counter64;
        description
          "Count of multicast octets received.";
      }
      leaf tx-frames-unicast {
        type yang:counter64;
        description
          "Count of unicast frames transmitted.";
      }
      leaf rx-frames-unicast {
        type yang:counter64;
        description
          "Count of unicast frames received.";
      }
      leaf tx-frames-broadcast {
        type yang:counter64;
        description
          "Count of broadcast frames transmitted.";
      }
      leaf rx-frames-broadcast {
        type yang:counter64;
        description
          "Count of broadcast frames received.";
      }
      leaf tx-frames-multicast {
        type yang:counter64;
        description
          "Count of multicast frames transmitted.";
      }
      leaf rx-frames-multicast {
        type yang:counter64;
        description
          "Count of multicast frames received.";
      }
      leaf last-clear-time {
        type string;
        description
          "Time when the statistics were last cleared.";
      }
      leaf tx-non-control-octets {
        type yang:counter64;
        description
          "Count of non control octets transmitted.";
      }
      leaf tx-oam-octets {
        type yang:counter64;
        description
          "Count of oam octets transmitted.";
      }
      leaf tx-cascading-packets {
        type yang:counter64;
        description
          "Count of cascading packets transmitted.";
      }
      leaf tx-cascading-bytes {
        type yang:counter64;
        description
          "Count of cascading bytes transmitted.";
      }
      leaf rx-overflow-octets {
        type yang:counter64;
        description
          "Count of overflow octets received.";
      }
      leaf rx-oam-octets {
        type yang:counter64;
        description
          "Count of oam octets received.";
      }
      leaf rx-mine-cascading-bytes {
        type yang:counter64;
        description
          "Count of mine cascading bytes received.";
      }
      leaf rx-other-cascading-bytes {
        type yang:counter64;
        description
          "Count of other cascading bytes received.";
      }
      leaf rx-mine-cascading-packets {
        type yang:counter64;
        description
          "Count of mine cascading packets received.";
      }
      leaf rx-other-cascading-packets {
        type yang:counter64;
        description
          "Count of other cascading packets received.";
      }
    }
  }

  rpc pon-ctrl-uni-port-statistics-get {
    description
      "Get the statistics of a UNI Port.";
    input {
      leaf olt {
        type pon-ctrl:olt-ref;
        mandatory true;
        description
          "Name of the OLT.";
      }
      leaf onu {
        type pon-ctrl:onu-ref;
        mandatory true;
        description
          "Name of the ONU.";
      }
      leaf uni-port {
        type pon-ctrl:uni-port-ref;
        mandatory true;
        description
          "ID of the UNI Port on the ONU.";
      }
    }
    output {
      uses pon-ctrl:uni-port-packet-counters-grouping;
      leaf ds-frames-broadcast {
        type yang:counter64;
        description
          "Total number of downstream broadcast packets transmitted by the UNI Port.";
      }
      leaf us-frames-broadcast {
        type yang:counter64;
        description
          "Total number of upstream broadcast packets transmitted by the UNI Port.";
      }
      leaf ds-frames-multicast {
        type yang:counter64;
        description
          "Total number of downstream multicast packets transmitted by the UNI Port.";
      }
      leaf us-frames-multicast {
        type yang:counter64;
        description
          "Total number of upstream multicast packets transmitted by the UNI Port.";
      }
      leaf ds-frames-crc-error {
        type yang:counter64;
        description
          "Total number of downstream packets received by the UNI Port that had a bad
            frame check sequence.";
      }
      leaf us-frames-crc-error {
        type yang:counter64;
        description
          "Total number of upstream packets received by the UNI Port that had a bad
            frame check sequence.";
      }
      leaf ds-drop-events {
        type yang:counter64;
        description
          "Total number of events in which downstream packets were dropped on the UNI Port
            due to a lack of resources. This is not necessarily the number of downstream packets
            dropped.";
      }
      leaf us-drop-events {
        type yang:counter64;
        description
          "Total number of events in which upstream packets were dropped on the UNI Port
            due to a lack of resources. This is not necessarily the number of upstream packets
            dropped.";
      }
      leaf last-clear-time {
        type string;
        description
          "Time when the statistics were last cleared.";
      }
    }
  }

  rpc pon-ctrl-datalink-xgem-statistics-get {
    description
      "Retrieves XGEM Port statistics for the current bin.";
    input {
      leaf olt {
        type pon-ctrl:olt-ref;
        mandatory true;
        description
          "Name of the OLT.";
      }
      leaf onu {
        type pon-ctrl:onu-ref;
        mandatory true;
        description
          "Name of the ONU.";
      }
      leaf datalink {
        type pon-ctrl:datalink-ref;
        mandatory true;
        description
          "Name of the Datalink.";
      }
      leaf xgem-port-id {
        type uint16;
        mandatory true;
        description
          "The ID of the XGEM port.";
      }
    }
    output {
      uses pon-ctrl:packet-counters-grouping;
      uses pon-ctrl:phy-counters-grouping;
      leaf rx-fec-good-blocks {
        type yang:counter64;
        description
          "Count of FEC blocks received without errors.";
      }
      leaf rx-fec-corrected-blocks {
        type yang:counter64;
        description
          "Count of FEC blocks received with errors that were correctable.";
      }
      leaf rx-fec-uncorrectable-blocks {
        type yang:counter64;
        description
          "Count of FEC blocks received with errors that were not correctable.";
      }
      leaf rx-fec-corrections {
        type yang:counter64;
        description
          "Count of FEC blocks received with correctable errors that were corrected.";
      }
      leaf tx-octets-multi-broadcast {
        type yang:counter64;
        description
          "Count of multicast and broadcast octets transmitted.";
      }
      leaf tx-control-octets {
        type yang:counter64;
        description
          "Count of control octets transmitted.";
      }
      leaf tx-plain-octets {
        type yang:counter64;
        description
          "Count of plain octets transmitted.";
      }
      leaf tx-encrypted-octets {
        type yang:counter64;
        description
          "Count of encrypted octets transmitted.";
      }
      leaf tx-oam-frames {
        type yang:counter64;
        description
          "Count of OAM frames transmitted on the interface.";
      }
      leaf tx-grant-ups-tq {
        type yang:counter64;
        description
          "Count of tq or upstreams slots granted to the ONUs.";
      }
      leaf tx-octets-unicast {
        type yang:counter64;
        description
          "Total number of unicast octets transmitted.";
      }
      leaf tx-frames-unicast {
        type yang:counter64;
        description
          "Count of unicast frames transmitted.";
      }
      leaf tx-frames-multicast {
        type yang:counter64;
        description
          "Count of multicast frames transmitted.";
      }
      leaf tx-frames-broadcast {
        type yang:counter64;
        description
          "Count of broadcast frames transmitted.";
      }
      leaf rx-control-octets {
        type yang:counter64;
        description
          "Count of control octets received.";
      }
      leaf rx-security-drop-octets {
        type yang:counter64;
        description
          "Count of security drop octets received.";
      }
      leaf rx-octets-unicast {
        type yang:counter64;
        description
          "Count of unicast octets received.";
      }
      leaf rx-octets-multi-broadcast {
        type yang:counter64;
        description
          "Count of multicast and broadcast octets received.";
      }
      leaf rx-plain-octets {
        type yang:counter64;
        description
          "Count of plain octets received.";
      }
      leaf rx-encrypted-octets {
        type yang:counter64;
        description
          "Count of encrypted octets received.";
      }
      leaf rx-overflow-octets {
        type yang:counter64;
        description
          "Count of overflow octets received.";
      }
      leaf rx-idle-octets {
        type yang:counter64;
        description
          "Count of idle octets received.";
      }
      leaf rx-key-mismatch-octets {
        type yang:counter64;
        description
          "Count of key mismatch octets received.";
      }
      leaf rx-bad-icv-drops {
        type yang:counter64;
        description
          "Count of frames received on the interface and dropped due to bad icv.";
      }
      leaf rx-oam-frames {
        type yang:counter64;
        description
          "Count of OAM frames received on the interface.";
      }
      leaf rx-all-bw-reqs {
        type yang:counter64;
        description
          "Count of all bandwidth requests received.";
      }
      leaf last-clear-time {
        type string;
        description
          "Time when the statistics were last cleared.";
      }
      leaf rx-mpcp-octets {
        type yang:counter64;
        description
          "Count of mpcp octets received.";
      }
    }
  }

  rpc pon-ctrl-residential-statistics-get {
    description
      "Retrieve residential statistics current bin.";
    input {
      leaf olt {
        type pon-ctrl:olt-ref;
        mandatory true;
        description
          "Name of the OLT.";
      }
      leaf onu {
        type pon-ctrl:onu-ref;
        description
          "Name of the ONU.";
      }
      leaf datalink {
        type pon-ctrl:datalink-ref;
        description
          "Name of the Datalink.";
      }
      leaf cpe-mac {
        type yang:mac-address;
        description
          "Customer premises equipment MAC address.";
      }
    }
    output {
      uses auth-counters-grouping;
      uses relay-counters-grouping;
      uses pppoe-counters-grouping;
      uses dhcpv6-counters-grouping;
    }
  }

  rpc pon-ctrl-radius-server-statistics-get {
    description
      "Retrieve RADIUS server statistics current bin.";
    input {
      leaf radius-server {
        type pon-ctrl:radius-server-ref;
        mandatory true;
        description
          "Name of the RADIUS Server.";
      }
    }
    output {
      list radius-server-address {
          key "host port";
          description
            "RADIUS server host and port.";
          leaf host {
            type inet:host;
            description
              "RADIUS server host address.";
          }
          leaf port {
            type inet:port-number;
            description
              "RADIUS server port.";
          }
          leaf total-auth-complete {
            type yang:counter64;
            description
              "Total authentication attempts completed successfully for this RADIUS server.";
          }
          leaf total-auth-timeout {
            type yang:counter64;
            description
              "Total authentication attempts that timed-out for this RADIUS server.";
          }
      }
    }
  }


  rpc pon-ctrl-rogue-onu-control {
    description
      "Allows specific rogue ONU procedures to be started (or cancelled) on an OLT or ONU.";
    input {
      leaf olt {
        type pon-ctrl:olt-ref;
        mandatory true;
        description
          "Name of the OLT.";
      }
      leaf onu {
        type pon-ctrl:onu-ref;
        description
          "Name of the ONU.";
      }
      leaf defect {
        type rogue-onu-defect;
        mandatory true;
        description
          "Type of rogue ONU defect.";
       }
      leaf command {
        type rogue-onu-command;
        mandatory true;
        description
          "Rogue ONU command to execute.";
      }
    }
    output {
      leaf status {
        type string;
        description
          "Status of the requested rogue ONU procedure.";
      }
    }
  }

  notification olt-discovered {
    description
      "Generated when a new OLT is discovered on an interface and has not yet been configured.";
    leaf l3-interface {
      type pon-ctrl:interface-ref;
      description
        "Name of the L3 interface on which this OLT was discovered.";
    }
    leaf olt-mac-address {
      type yang:mac-address;
      description
        "The MAC address of the discovered OLT.";
    }
    leaf olt-port-id {
      type cntypes:name-string;
      description
        "OLT port number.";
    }
  }

  notification onu-discovered {
    description
      "Generated when a new ONU is discovered on an OLT and has not yet been configured.";
    leaf olt {
      type pon-ctrl:olt-ref;
      description
        "Name of the OLT on which this ONU was discovered.";
    }
    leaf onu-serial-number {
      type string {
        pattern '[a-zA-Z]{4}[0-9a-fA-F]{8}';
      }
      description
        "The serial number of the discovered ONU.";
    }
    leaf onu-registration-id {
      type string;
      description
        "The registration ID of the discovered ONU.";
    }
    leaf oper-state {
      type pon-ctrl:onu-oper-state;
      description
        "Operational state of the ONU.";
    }
  }

  notification olt-oper-state-change {
    description
      "Generated when the operational state of an OLT changes.";
    leaf olt {
      type pon-ctrl:olt-ref;
      description
        "Name of the OLT whose operational state has changed.";
    }
    leaf oper-state {
      type pon-ctrl:olt-oper-state;
      description
        "Operational state of the OLT.";
    }
    leaf alarms {
      type olt-alarm-bit-map;
      description
        "Bit map of alarm conditions currently active on this OLT.";
    }
    leaf previous-oper-state {
      type pon-ctrl:olt-oper-state;
      description
        "Previous operational state of the OLT.";
    }
    leaf oper-state-change-reason {
      type olt-oper-state-change-reason;
      description
        "Reason for the oper-state change.";
    }
  }

  notification onu-oper-state-change {
    description
      "Generated when the operational state of an ONU changes.";
    leaf olt {
      type pon-ctrl:olt-ref;
      description
        "Name of the OLT.";
    }
    leaf onu {
      type pon-ctrl:onu-ref;
      description
        "Name of the ONU whose operational state has changed.";
    }
    leaf oper-state {
      type pon-ctrl:onu-oper-state;
      description
        "Operational state of the ONU.";
    }
    leaf deregister-reason {
      type string;
      description
        "The reason for the last ONU deregistration.
         Set when the oper-state of the ONU is 'deregistered'.";
    }
    leaf alarms {
      type onu-alarm-bit-map;
      description
        "Bit map of alarm conditions currently active on this ONU.";
    }
    leaf previous-oper-state {
      type pon-ctrl:onu-oper-state;
      description
        "Previous operational state of the ONU.";
    }
    leaf oper-state-change-reason {
      type onu-oper-state-change-reason;
      description
        "Reason for the oper-state change.";
    }
  }

  notification uni-port-oper-state-change {
    description
      "Generated when the operational state of an ONU UNI Port changes.";
    leaf olt {
      type pon-ctrl:olt-ref;
      description
        "Name of the OLT.";
    }
    leaf onu {
      type pon-ctrl:onu-ref;
      description
        "Name of the ONU.";
    }
    leaf uni-port {
      type pon-ctrl:uni-port-ref;
      description
        "ID of the UNI Port whose operational state has changed.";
    }
    leaf oper-state {
      type pon-ctrl:uni-port-oper-state;
      description
        "Operational state of the UNI Port.";
    }
    leaf speed {
      type pon-ctrl:uni-port-oper-speed;
      description
        "Operational speed of the UNI Port
         Set when the oper-state of the ONU is 'up'.";
    }
    leaf duplex {
      type pon-ctrl:uni-port-oper-duplex;
      description
        "Operational duplex of the UNI Port.
         Set when the oper-state of the ONU is 'up'.";
    }
    leaf previous-oper-state {
      type pon-ctrl:uni-port-oper-state;
      description
        "Previous operational state of the UNI port.";
    }
    leaf oper-state-change-reason {
      type uni-port-oper-state-change-reason;
      description
        "Reason for the oper-state change.";
    }
    leaf alarms {
      type uni-port-alarm-bit-map;
      description
        "Bit map of alarm conditions currently active on this UNI port.";
    }
  }

  notification radius-server-oper-state-change {
    description
      "Generated when the operational state of a RADIUS server changes.";
    leaf radius-server {
      type pon-ctrl:radius-server-ref;
      description
        "Name of the RADIUS server.";
    }
    leaf host {
      type inet:host;
      description
        "RADIUS server host address.";
    }
    leaf port {
      type inet:port-number;
      description
        "RADIUS server port.";
    }
    leaf oper-state {
      type pon-ctrl:radius-server-oper-state;
      description
        "Operational state of the RADIUS server.";
    }
  }

  notification dhcp-relay-oper-state-change {
    description
      "Generated when the operational state of a DHCP relay changes.";
    leaf olt {
      type pon-ctrl:olt-ref;
      description
        "Name of the OLT.";
    }
    leaf onu {
      type pon-ctrl:onu-ref;
      description
        "Name of the ONU.";
    }
    leaf datalink {
      type pon-ctrl:datalink-ref;
      description
        "Name of the Datalink.";
    }
    leaf cpe-mac {
      type yang:mac-address;
      description
        "Customer premises equipment MAC address.";
    }
    leaf oper-state {
      type pon-ctrl:dhcp-relay-oper-state;
      description
        "Operational state of the DHCP relay.";
    }
  }

  notification dhcpv6-oper-state-change {
    description
      "Generated when the operational state of a DHCPv6 changes.";
    leaf olt {
      type pon-ctrl:olt-ref;
      description
        "Name of the OLT.";
    }
    leaf onu {
      type pon-ctrl:onu-ref;
      description
        "Name of the ONU.";
    }
    leaf datalink {
      type pon-ctrl:datalink-ref;
      description
        "Name of the Datalink.";
    }
    leaf cpe-mac {
      type yang:mac-address;
      description
        "Customer premises equipment MAC address.";
    }
    leaf oper-state {
      type pon-ctrl:dhcpv6-oper-state;
      description
        "Operational state of the DHCPv6.";
    }
  }

 notification authentication-oper-state-change {
    description
      "Generated when the operational state of an authentication changes.";
    leaf olt {
      type pon-ctrl:olt-ref;
      description
        "Name of the OLT.";
    }
    leaf onu {
      type pon-ctrl:onu-ref;
      description
        "Name of the ONU.";
    }
    leaf datalink {
      type pon-ctrl:datalink-ref;
      description
        "Name of the Datalink.";
    }
    leaf cpe-mac {
      type yang:mac-address;
      description
        "Customer premises equipment MAC address.";
    }
    leaf oper-state {
      type pon-ctrl:authentication-oper-state;
      description
        "Operational state of authentication.";
    }
  }

  notification pppoe-oper-state-change {
    description
      "Generated when the operational state of a PPPOE changes.";
    leaf olt {
      type pon-ctrl:olt-ref;
      description
        "Name of the OLT.";
    }
    leaf onu {
      type pon-ctrl:onu-ref;
      description
        "Name of the ONU.";
    }
    leaf datalink {
      type pon-ctrl:datalink-ref;
      description
        "Name of the Datalink.";
    }
    leaf cpe-mac {
      type yang:mac-address;
      description
        "Customer premises equipment MAC address.";
    }
    leaf oper-state {
      type pon-ctrl:pppoe-oper-state;
      description
        "Operational state of the PPPoE.";
    }
  }

  notification datalink-error-state-change {
    description
      "Generated when an error threshold on the Datalink is reached or cleared.";
    leaf olt {
      type pon-ctrl:olt-ref;
      description
        "Name of the OLT.";
    }
    leaf onu {
      type pon-ctrl:onu-ref;
      description
        "Name of the ONU.";
    }
    leaf datalink {
      type pon-ctrl:datalink-ref;
      description
        "Name of the Datalink whose error threshold is reached or cleared.";
    }
    leaf alarms {
      type datalink-alarm-bit-map;
      description
        "Bit-map of active alarms.";
    }
    leaf clear {
      type boolean;
      description
        "Indicates if the alarms should be cleared.";
    }
  }

  notification pon-ctrl-config-state-change {
    description
      "Generated when PON configuration state changes.";
    leaf reconciled {
      type boolean;
      description
        "Indicates if PON configuration is complete";
    }
  }

  notification pon-relay-config-state-change {
    description
      "Generated when PON configuration state changes.";
    leaf reconciled {
      type boolean;
      description
        "Indicates if PON configuration is complete";
    }
  }

  notification rogue-onu-state-change {
    description
      "Generated when the rogue state of an ONU changes.";
    leaf olt {
      type pon-ctrl:olt-ref;
      description
        "Name of the OLT.";
    }
    leaf onu {
      type pon-ctrl:onu-ref;
      description
        "Name of the ONU.";
    }
    leaf state {
      type pon-ctrl:rogue-onu-state;
      description
        "Rogue state of the ONU.";
    }
    leaf alarms {
      type onu-alarm-bit-map;
      description
        "Bit map of alarm conditions currently active on this ONU.
         Only set on ONU delete to indicate which alarms to clear.";
    }
  }

  notification rogue-olt-idle-power-state-change {
    description
      "Generated when the rogue OLT idle receive power state changes.";
    leaf olt {
      type pon-ctrl:olt-ref;
      description
        "Name of the OLT.";
    }
    leaf state {
      type pon-ctrl:rogue-onu-state;
      description
        "Rogue idle power state of the OLT.";
    }
  }

  notification rogue-olt-disallowed-state-change {
    description
      "Generated when the rogue OLT disallowed state changes.";
    leaf olt {
      type pon-ctrl:olt-ref;
      description
        "Name of the OLT.";
    }
    leaf state {
      type pon-ctrl:rogue-onu-state;
      description
        "Rogue disallowed state of the OLT.";
    }
  }

  notification rogue-onu-power-variation-state-change {
    description
      "Generated when the rogue ONU power variation state changes.";
    leaf olt {
      type pon-ctrl:olt-ref;
      description
        "Name of the OLT.";
    }
    leaf onu {
      type pon-ctrl:onu-ref;
      description
        "Name of the ONU.";
    }
    leaf state {
      type pon-ctrl:rogue-onu-state;
      description
        "Rogue power variation state of the ONU.";
    }
  }

  notification rogue-onu-disallowed-state-change {
    description
      "Generated when the rogue ONU disallowed state changes.";
    leaf olt {
      type pon-ctrl:olt-ref;
      description
        "Name of the OLT.";
    }
    leaf onu {
      type pon-ctrl:onu-ref;
      description
        "Name of the ONU.";
    }
    leaf state {
      type pon-ctrl:rogue-onu-state;
      description
        "Rogue disallowed state of the ONU.";
    }
  }

  notification pon-ctrl-global-state-change {
    description
      "Generated when the global PON state changes.";
    leaf statistics-retrieval-threshold {
      type boolean;
      description
        "When set to true indicates statistics retrieval has exceeded internal threshold.
         Action has been taken to drop new statistics get requests when the total
         requests exceeds internal thresold over a 15 minute period. Statistics will resume after
         the 15 minute period expires. The user should reduce the frequency of either
         sensor subscriptions or gNMI subscriptions to recover from this condition.";
    }
  }
}
