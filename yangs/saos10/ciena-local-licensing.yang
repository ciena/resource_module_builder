module ciena-local-licensing {
  namespace "urn:ciena:params:xml:ns:yang:ciena:ciena-local-licensing";

  prefix "local-license";

  import ietf-inet-types {
    prefix "inet";
  }

  organization "Ciena Corporation";

  contact
    "Web URL: http://www.ciena.com/
     Postal:  7035 Ridge Road
              Hanover, Maryland 21076
              U.S.A.
     Phone:   +1 800-921-1144
     Fax:     +1 410-694-5750";

  description
    "This YANG module defines Ciena's local licensing interfaces. ";

  revision "2020-12-07" {
    description
      "1. In this revision, the built-in-trial-license-activate and
      startup-license-activate RPCs has been added";
      reference
      "No specific reference; standard not available.";
  }

  revision "2017-05-05" {
    description
      "1.0";
      reference
      "No specific reference; standard not available.";
  }

  typedef string-max-256 {
    type string {
      length 1..256;
    }
  }

  rpc regid-generate {
    description
      "The regid-generate rpc would trigger the generation of the
      device registration identification file. The path to the file
      is returned as output filepath.";
    output {
      leaf filepath {
        type inet:uri;
        description
          "This is the path of the generated regid file. The regid
          file can be upload from the device from this path.";
      }
      leaf response {
        type string-max-256;
        description
          "The response to the regid-generate action could be
          'success', or the reason for regid generation failure";
      }
    }
  }

  rpc licensekey-activate {
    description
      "The licensekey-activate rpc would apply the license-key
      on the device. The filename of the license-key is supplied
      as input in this rpc.";
    input {
      leaf filename {
        type string-max-256;
        description
          "This is the name of the licensekey file that is to be
          activated.";
      }
    }
    output {
      leaf response {
        type string-max-256;
        description
          "The response to the licensekey-activate action could be
          'success', or the reason for license key activation
          failure";
      }
    }
  }

  rpc built-in-trial-license-activate {
    description
      "Applies the trial license that is included with the box.";
    output {
      leaf response {
        type string-max-256;
        description
          "The response to the built-in-trial-license-activate action could be
          'success', or the reason for trial license activation
          failure";
      }
    }
  }

  rpc startup-license-activate {
    description
      "Applies the startup license that is included with the box.";
    output {
      leaf response {
        type string-max-256;
        description
          "The response to the startup-license-activate action could be
          'success', or the reason for startup license activation
          failure";
      }
    }
  }
}
