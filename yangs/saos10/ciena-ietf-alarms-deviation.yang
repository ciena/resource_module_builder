module ciena-ietf-alarms-deviation {
  yang-version 1.1;
  namespace "http://www.ciena.com/ns/yang/ciena-ietf-alarms-deviation";
  prefix ciena-alarms-dev;

  import ietf-alarms {
    prefix al;
  }

  import ciena-ietf-alarms {
    prefix ciena-al;
  }

  organization
    "Ciena Corporation";
  
  contact
    "Web URL: http://www.ciena.com/
     E-mail:  yang@ciena.com
     Postal:  7035 Ridge Road
              Hanover, Maryland 21076
              U.S.A.
     Phone:   +1 800-921-1144
     Fax:     +1 410-694-5750";
      
  description
    "This YANG module defines Ciena's augmentations to the draft-ietf-ccamp-alarm-module-01 model.

      Copyright (c) 2016 Ciena Corporation.  All rights 
      reserved.

      All information contained herein is, and remains
      the property of Ciena Corporation. Dissemination of this 
      information or reproduction of this material is strictly 
      forbidden unless prior written permission is obtained from 
      Ciena Corporation.";

  revision "2021-10-18" {
    description
      "Restrict number of shelves to 8";
  }

  revision "2021-07-25" {
    description
    "Enabled severity in alarm inventory";
  }

  revision "2021-05-07" {
    description
      "Default value for max-alarm-status-changes is changed to 16";
  }

  revision "2018-08-01" {
    description 
      "Initial version";
    reference
      "RFC 6020: YANG - A Data Modeling Language for
       the Network Configuration Protocol (NETCONF).
       No specific reference; standard not available.";
  }

  deviation /al:alarms/al:control/al:alarm-shelving/al:shelf/al:resource {
    deviate replace {
      type string;
    }
  }

  deviation /al:alarms/al:control/al:alarm-shelving/al:shelf/al:alarm-type-id {
    deviate replace {
      type ciena-al:alarm-types;
    }
  }

  deviation /al:alarms/al:control/al:max-alarm-status-changes{
     deviate replace {
        default 16;
     }
  }

  deviation /al:alarms/al:alarm-inventory/al:alarm-type/al:alarm-type-id {
    deviate replace {
      type ciena-al:alarm-types;
    }
  }

  deviation /al:alarms/al:alarm-list/al:alarm/al:resource {
    deviate replace {
      type string;
    }
  }
  deviation /al:alarms/al:alarm-list/al:alarm/al:alarm-type-id {
    deviate replace {
      type ciena-al:alarm-types;
    }
  }

  deviation /al:alarms/al:shelved-alarms/al:shelved-alarm/al:resource {
    deviate replace {
      type string;
    }
  }

  deviation /al:alarms/al:shelved-alarms/al:shelved-alarm/al:alarm-type-id {
    deviate replace {
      type ciena-al:alarm-types;
    }
  }

  deviation /al:alarms/al:alarm-inventory/al:alarm-type/al:resource {
    deviate not-supported;
  }

  deviation /al:alarms/al:summary/al:shelves-active {
    deviate not-supported;
  }

  deviation /al:alarms/al:alarm-list/al:alarm/al:alt-resource {
    deviate not-supported;
  }

  deviation /al:alarms/al:alarm-list/al:alarm/al:related-alarm {
    deviate not-supported;
  }

  deviation /al:alarms/al:alarm-list/al:alarm/al:impacted-resource {
    deviate not-supported;
  }

  deviation /al:alarms/al:alarm-list/al:alarm/al:root-cause-resource {
    deviate not-supported;
  }

  deviation /al:alarms/al:alarm-list/al:alarm/al:set-operator-state {
    deviate not-supported;
  }
  deviation /al:alarms/al:shelved-alarms/al:shelved-alarm/al:alt-resource {
    deviate not-supported;
  }

  deviation /al:alarms/al:shelved-alarms/al:shelved-alarm/al:related-alarm {
    deviate not-supported;
  }

  deviation /al:alarms/al:shelved-alarms/al:shelved-alarm/al:impacted-resource {
    deviate not-supported;
  }

  deviation /al:alarms/al:shelved-alarms/al:shelved-alarm/al:root-cause-resource {
    deviate not-supported;
  }

  deviation /al:alarm-notification/al:alt-resource {
    deviate not-supported;
  }

  deviation /al:alarm-notification/al:related-alarm {
    deviate not-supported;
  }

  deviation /al:alarm-notification/al:impacted-resource {
    deviate not-supported;
  }

  deviation /al:alarm-notification/al:root-cause-resource {
    deviate not-supported;
  }

  deviation /al:alarm-notification/al:resource {
    deviate replace {
      type string;
    }
  }

  deviation /al:alarm-notification/al:alarm-type-id {
    deviate replace {
      type ciena-al:alarm-types;
    }
  }

  deviation /al:compress-alarms/al:input/al:resource {
    deviate replace {
      type string;
    }
  }

  deviation /al:compress-alarms/al:input/al:alarm-type-id {
    deviate replace {
      type ciena-al:alarm-types;
    }
  }

  deviation /al:compress-alarms/al:input/al:alarm-type-qualifier {
    deviate replace {
      type string;
    }
  }

  deviation /al:alarms/al:control/al:alarm-shelving/al:shelf {
    deviate add {
      max-elements 8;
    }
  }
}
