module ciena-cfm-types {
  namespace "urn:ciena:params:xml:ns:yang:ciena-pn:ciena-cfm-types";
  prefix "ciena-cfm-types";

  organization
     "Ciena Corporation";

  contact
     "Web URL: http://www.ciena.com/
     E-mail:  yang@ciena.com
     Postal:  7035 Ridge Road
     Hanover, Maryland 21076
     U.S.A.
     Phone:   +1 800-921-1144
     Fax:     +1 410-694-5750";

  description
     "This YANG module defines Ciena's CFM module specific types.

      Copyright (c) 2016 Ciena Corporation.  All rights
      reserved.

      All information contained herein is, and remains the
      property of Ciena Corporation. Dissemination of this
      information or reproduction of this material is strictly
      forbidden unless prior written permission is obtained
      from Ciena Corporation.";

  revision "2023-10-01" {
     description
        "Initial version.
         Added new typedef active-defects-bits-type for CFM MEP active-defects";
  }

  typedef active-defects-bits-type {
    type bits {
      bit remote-rdi;
      bit remote-mac-error;
      bit remote-invalid-ccm;
      bit invalid-ccm;
      bit cross-connect-ccm;
      bit instability;
    }

    description
      "A set of bits indicating the the current defects:
        - cross-connect-ccm One or more cross connect CCMs has been received
        - invalid-ccm One or more invalid CCMs has been received
        - remote-invalid-ccm At least one of the Remote MEP state machines is not
          receiving valid CCMs from its remote MEP
        - remote-mac-error One or more of the remote MEPs is reporting a failure
          in its Port Status TLV or Interface Status
        - remote-rdi Indicates that at least one of the Remote MEP state machines is
          receiving valid CCMs from its remote MEP that has the RDI bit set
        - instability Indicates that local MEP has not discovered any remote MEP yet and
          is in Instability defect.";
    reference
      "[802.1q] 20.33.9";
  }

}
