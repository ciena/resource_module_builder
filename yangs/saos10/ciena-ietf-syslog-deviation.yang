module ciena-ietf-syslog-deviation {
  namespace "http://ciena.com/ns/yang/ciena-ietf-syslog-deviation";
  prefix ciena-ietf-syslog-deviation;
  
  import ietf-syslog {
    prefix syslog;
  }
  
  organization
    "Ciena Corporation";
  
  contact
    "Web URL: http://www.ciena.com/
     E-mail:  yang@ciena.com
     Postal:  7035 Ridge Road
              Hanover, Maryland 21076
              U.S.A.
     Phone:   +1 800-921-1144
     Fax:     +1 410-694-5750";

  description
    "This module contains the Ciena proprietary YANG deviations 
     of the standard ietf-syslog YANG module.

     Copyright (c) 2016 Ciena Corporation.  All rights reserved.

     All information contained herein is, and remains
     the property of Ciena Corporation. Dissemination of this
     information or reproduction of this material is strictly
     forbidden unless prior written permission is obtained from
     Ciena Corporation.";

  revision "2016-03-01" {
    description 
      "Initial version";
    reference
      "";
  }   
  deviation /syslog:syslog/syslog:log-actions/syslog:console {
    deviate not-supported;
  }
  
  deviation /syslog:syslog/syslog:log-actions/syslog:buffer {
    deviate not-supported;
  }
  
  deviation /syslog:syslog/syslog:log-actions/syslog:file {
    deviate not-supported;
  }
    
  deviation /syslog:syslog/syslog:log-actions/syslog:remote/syslog:destination {
    deviate not-supported;
  }
  
  deviation /syslog:syslog/syslog:log-actions/syslog:terminal {
    deviate not-supported;
  }    
  
  deviation /syslog:syslog/syslog:log-actions/syslog:session {
    deviate not-supported;
  }

}
