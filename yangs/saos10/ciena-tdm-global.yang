module ciena-tdm-global {

  namespace "http://www.ciena.com/ns/yang/ciena-tdm-global";
  prefix tdm-global;

  import openconfig-interfaces {
    prefix oc-if;
  }

  organization
    "Ciena Corporation";

  contact
    "Web URL: http://www.ciena.com/
    E-mail:  yang@ciena.com
    Postal:  7035 Ridge Road
    Hanover, Maryland 21076
    U.S.A.
    Phone:   +1 800-921-1144
    Fax:     +1 410-694-5750";

  description
    "This YANG module defines Ciena's data definition for the
    management of TDM interfaces.

    Copyright (c) 2019 Ciena Corporation.  All rights
    reserved.

    All information contained herein is, and remains
    the property of Ciena Corporation. Dissemination of this
    information or reproduction of this material is strictly
    forbidden unless prior written permission is obtained from
    Ciena Corporation.";

  revision "2019-10-17" {
    description
      "Initial version.";
    reference
      "Ciena Functional Specification.";
  }

  
  /* 
   * Typedefs
   */

  typedef interface-ref {
    type oc-if:base-interface-ref;
    description
      "L3 Interface reference type.";
  }


  /*
   * Config data
   */

  container tdm-global {
    description
      "TDM global configuration data.";

    leaf mode {
      type enumeration {
        enum ansi {
          description 
          "ANSI";
        }
        enum etsi {
          description
          "ETSI";
          }
      }
      default ansi;
      description
        "Select ANSI or ETSI mode.";
    }

    leaf ctpid {
        type enumeration {
          enum 0x8100 {
            description
            "0x8100";
          }
          enum 0x88a8 {
            description
            "0x88a8";
          }
          enum 0x9100 {
            description
            "0x9100";
          }
        }
        default 0x8100;
        description
          "Default customer TPID.  This may be overridden on an individual pseudowire.";
    }

    leaf sfp-auto-upgrade {
      type boolean;
      default true;
      description
        "Default is auto-upgrade of SFP firmware on bootup.";
    }
    
    leaf mgmt-interface {
      type interface-ref;
      description
      "Interface for Managing Smart SFPs."; 
    }
  }
}
