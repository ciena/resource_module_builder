module ciena-openconfig-if-ethernet-port-deviation {
    namespace "http://ciena.com/ns/yang/ciena-openconfig-if-ethernet-port-deviation";
    prefix "cn-oc-if-eth-deviation";

    import ciena-openconfig-if-ethernet-port {
        prefix "cn-oc-if-eth";
    }
    import openconfig-interfaces {
        prefix oc-if;
    }

    organization "Ciena Corporation";

    contact
        "Web URL: http://www.ciena.com/
         Postal : 7035 Ridge Road
                  Hanover, Maryland 21076
                  U.S.A.
         Phone  : +1 800-921-1144
         Fax    : +1 410-694-5750";

    description
        "This module contains the Ciena proprietary YANG
         augmentations to the standard openconfig-interface
         YANG module for IEEE 802.3 CSMA/CD Ethernet port
         deviation definitions.

         Copyright (c) 2018 Ciena Corporation.  All rights reserved.

         All information contained herein is, and remains
         the property of Ciena Corporation. Dissemination of this
         information or reproduction of this material is strictly
         forbidden unless prior written permission is obtained from
         Ciena Corporation.";

    revision "2022-07-28" {
        description
            "Initial version";
    }

    deviation "/oc-if:interfaces/"
            + "oc-if:interface/"
            + "oc-if:config/"
            + "cn-oc-if-eth:mac-address" {
        deviate not-supported;
    }
}
