module yumaworks-term-msg {

    namespace "http://yumaworks.com/ns/yumaworks-term-msg";

    prefix "ytm";

    organization "YumaWorks, Inc.";

    contact
        "Support <support at yumaworks.com>";

    description
       "Notification event for terminal message feature.

     Copyright (c) 2019 YumaWorks, Inc. All rights reserved.

     Redistribution and use in source and binary forms, with or
     without modification, is permitted pursuant to, and subject
     to the license terms contained in, the BSD 3-Clause License
     http://opensource.org/licenses/BSD-3-Clause";

    revision 2019-05-05 {
        description
          "Initial version.";
    }

    notification term-msg {
      description
        "Used to send terminal messages to the yp-shell client";
      leaf data {
        type string;
        mandatory true;
        description "Terminal message to display";
      }
    }

}
