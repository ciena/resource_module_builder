module ciena-pkix-types {
  namespace "http://www.ciena.com/ns/yang/ciena-pkix-types";
  prefix pkix-types;

  import ietf-inet-types {
    prefix inet;
  }

  organization
    "Ciena Corporation";

  contact
    "Web URL: http://www.ciena.com/
     E-mail:  yang@ciena.com
     Postal:  7035 Ridge Road
              Hanover, Maryland 21076
              U.S.A.
     Phone:   +1 800-921-1144
     Fax:     +1 410-694-5750";

  description
    "This YANG module defines the data types and groupings for Public
     Key Infrastructure (PKI) Security Certificates CA (Certificate
     Authority) and CRL (Certificate Revocation List) for the NETCONF
     protocol.

     Copyright (c) 2016-2017 Ciena Corporation.  All rights reserved.

     All information contained herein is, and remains the property of
     Ciena Corporation. Dissemination of this information or
     reproduction of this material is strictly forbidden unless prior
     written permission is obtained from Ciena Corporation.";

  revision 2023-04-28 {
    description
      "Added pem-string to pass the certificate as a string
       and validate-trust-store boolean to validate device cert install against trusted rootCA, if set to true";
    reference
      "No specific reference; standard not available.";
  }

  revision 2022-04-22 {
    description
      "Fixed the typo useExisiting to useExisting";
    reference
      "No specific reference; standard not available.";
  }

  revision 2021-03-23 {
    description
      "Updated to add an new algorithm type";
    reference
      "No specific reference; standard not available.";
  }

  revision 2018-04-27 {
    description
      "Updated to add an new algorithm type";
    reference
      "No specific reference; standard not available.";
  }
  revision 2017-10-27 {
    description
      "Initial version";
    reference
      "RFC 6020: YANG - A Data Modeling Language for
       the Network Configuration Protocol (NETCONF).
       No specific reference; standard not available.";
  }

  /*
   * Identities
   */
  
  identity key-algorithm {
    description
      "Base identity from which all key-algorithms are derived.";
  }

  identity rsa1024 {
    base key-algorithm;
    description
      "The RSA algorithm using a 1024-bit key.";
    reference
      "RFC3447: Public-Key Cryptography Standards (PKCS) #1:
                RSA Cryptography Specifications Version 2.1.";
  }

  identity rsa2048 {
    base key-algorithm;
    description
      "The RSA algorithm using a 2048-bit key.";
    reference
      "RFC3447: Public-Key Cryptography Standards (PKCS) #1:
                RSA Cryptography Specifications Version 2.1.";
  }

  identity rsa3072 {
    base key-algorithm;
    description
      "The RSA algorithm using a 3072-bit key.";
    reference
      "RFC3447: Public-Key Cryptography Standards (PKCS) #1:
                RSA Cryptography Specifications Version 2.1.";
  }

identity rsa4096 {
  base key-algorithm;
  description
    "The RSA algorithm using a 4096-bit key.";
  reference
    "RFC3447: Public-Key Cryptography Standards (PKCS) #1:
              RSA Cryptography Specifications Version 2.1.";
}

//identity rsa7680 {
//  base key-algorithm;
//  description
//    "The RSA algorithm using a 7680-bit key.";
//  reference
//    "RFC3447: Public-Key Cryptography Standards (PKCS) #1:
//              RSA Cryptography Specifications Version 2.1.";
//}

//identity rsa15360 {
//  base key-algorithm;
//  description
//    "The RSA algorithm using a 15360-bit key.";
//  reference
//    "RFC3447: Public-Key Cryptography Standards (PKCS) #1:
//              RSA Cryptography Specifications Version 2.1.";
//}

//identity secp192r1 {
//  base key-algorithm;
//  description
//    "The secp192r1 algorithm.";
//  reference
//    "RFC5480:
//       Elliptic Curve Cryptography Subject Public Key Information.";
//}

  identity secp256r1 {
    base key-algorithm;
    description
      "The secp256r1 algorithm.  Also referred to in some contexts such
       as RFC 4754 as ecdsa256.";
    reference
      "RFC5480:
         Elliptic Curve Cryptography Subject Public Key Information.";
  }

  identity secp384r1 {
    base key-algorithm;
    description
      "The secp384r1 algorithm.  Also referred to in some contexts such
       as RF 4754 as ecdsa384.";
    reference
      "RFC5480:
         Elliptic Curve Cryptography Subject Public Key Information.";
  }

  identity secp521r1 {
    base key-algorithm;
    description
      "The secp521r1 algorithm.  Also referred to in some contexts such
       as RFC 4754 as ecdsa521.";
    reference
      "RFC5480:
         Elliptic Curve Cryptography Subject Public Key Information.";
  }

  // key-algorithm identities used by SAOS but not included in the IETF
  // model.

  identity dsa1024 {
    base key-algorithm;
    description
      "The dsa1024 algorithm.";
    reference
      "";
  }

  identity dsa2048 {
    base key-algorithm;
    description
      "The dsa2048 algorithm.";
    reference
      "";
  }

  identity dsa3072 {
    base key-algorithm;
    description
      "The dsa3072 algorithm.";
    reference
      "";
  }

  identity useExisting {
    base key-algorithm;
    description
      "The the existing algorithm.";
    reference
      "";
  }

  typedef min-tls-version {
     type enumeration {
        enum tls1_0 {
           description
              "TLSv1.0 would be minimum version supported";
        }
        enum tls1_1 {
           description
              "TLSv1.1 would be minimum version supported";
        }
        enum tls1_2 {
           description
              "TLSv1.2 would be minimum version supported";
        }
     }
     description
        "This enum contains the minimum TLS versions that, once set
        within a protocol, prevents the use of any TLS version
        older than the version set.";
  } 

  /*
   * Groupings
   */

  grouping pkix-certificate-fields {
    leaf subject-common-name {
      type string;
      description
        "The Subject Common Name of this X.509 certificate.";
    }

    leaf issuer-common-name {
      type string;
      description
        "The certificate Issuer Common Name.";
    }

    leaf valid-not-after {
      type string;
      description
        "The end of the certificate's validity period.";
    }

    description
      "Common X.509 certificate fields";
  }

  grouping pkix-file-transfer-parameters {
  /*
   * the sil generation fails with this so not yet
    uses ciena-ftt:file-transfer-parameters;
    */

    leaf login-id {
      type string {
        length 0..32;
      }
      description
        "Login ID for the specified server.  Not needed for TFTP.";
    }

    leaf password {
      type string;
      description
        "The string used for the clear text password.  Not needed for
         TFTP.";
    }

    leaf sftp-passphrase {
      type string;
      description
        "Passphrase for SFTP (Secure File Transfer Protocol)
         transfers.";
    }

    leaf force {
      type boolean;
      description
        "Use force to overwrite the local file with the same filename.
         Applies only to install operations.";
    }

    description
      "Common file transfer parameters";
  }

}
