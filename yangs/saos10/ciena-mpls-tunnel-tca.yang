module ciena-mpls-tunnel-tca {
   namespace "http://ciena.com/ns/yang/ciena-mpls-tunnel-tca";

   prefix tca-profile;

   organization
      "Ciena Corporation";

   contact
      "Web URL: http://www.ciena.com/
       E-mail:  yang@ciena.com
       Postal:  7035 Ridge Road
                Hanover, Maryland 21076
                U.S.A.

       Phone:   +1 800-921-1144
       Fax:     +1 410-694-5750";

   description
      "This module contains the Ciena proprietary YANG defintion
       of Threshold Crossing Alert (TCA) profile configuration.

       Copyright (c) 2022 Ciena Corporation. All rights reserved.

       All information and intellectual property contained in this
       YANG module (Specification) is, and remains the property
       of Ciena Corporation. Ciena retains all title and ownership
       in the Specification, including any revisions.

       Ciena grants all interested parties that access the
       Specification with the intent to use or distribute ('you') a
       non-exclusive, no-cost license to use and distribute
       unmodified copies of the Specification solely in connection
       with the management of Ciena products sold by or on
       behalf of Ciena, provided this copyright notice and license
       appear on all copies. Ciena may rescind or modify this
       license at any time.

       This Specification is supplied 'as is', and Ciena makes no
       warranty, either express or implied, as to the use, operation,
       condition, or performance of the Specification. You agree
       that Ciena has no liability for your use of the Specification.";

   revision "2023-02-24" {
      description
         "Initial Version for TCA profile Support.
          Updated unit type of sample-interval and range of adjustment-threshold,
          overflow-threshold underflow-threshold.";
   }

   container tca-profiles {
      description
         "The list of MPLS tunnel TCA profiles";

      list tca-profile {
         key "name";
         description
            "An MPLS tunnel TCA profile";

         leaf name {
            type string {
               length "1..64";
            }
            description
               "An MPLS tunnel TCA profile name";
         }

         leaf sample-interval {
            type uint32 {
               range "1|5|10|15|30|60|1440";
            }
            units minutes;
            description
               "Interval in minutes for the bandwidth-sample collection";
         }

         leaf adjustment-interval {
            type uint32 {
               range 1..604800;
            }
            units seconds;
            default 300;
            description
               "Interval in seconds for the periodic adjustment TCA check";
         }

         leaf adjustment-threshold {
            type uint32 {
               range 0..2147483;
            }
            description
               "The absolute range for adjustment TCA, expressed in kbps";
         }

         leaf adjustment-threshold-percentage {
            type uint8 {
               range 0..100;
            }
            default 5;
            description
               "Percentage range for adjustment TCA";
         }
		 
         leaf overflow-threshold {
            type uint32 {
               range 0..2147483;
            }
            description
               "The absolute value of overflow region, expressed in kbps";
         }

         leaf overflow-threshold-percentage {
            type uint8 {
               range 0..100;
            }
            description
               "Percentage value of overflow region";
         }

         leaf overflow-count {
            type uint32 {
               range 1..2147483647;
            }
            description
               "Consecutive overflow samples for TCA";
         }

         leaf underflow-threshold {
            type uint32 {
               range 0..2147483;
            }
            description
               "The absolute value of underflow region, expressed in kbps";
         }

         leaf underflow-threshold-percentage {
            type uint8 {
               range 0..100;
            }
            description
               "Percentage value of underflow region";
         }

         leaf underflow-count {
            type uint32 {
               range 1..2147483647;
            }
            description
               "Consecutive underflow samples for TCA";
         }

         leaf alert-interval {
            type uint32 {
               range 1..604800;
            }
            units seconds;
            description
               "Interval in seconds for periodic alert TCA check";
         }

         leaf alert-threshold-percentage {
            type uint8 {
               range 0..100;
            }
            description
               "Percentage range for alert TCA";
         }
      }
   }
}
