module ciena-ssh-types {
  namespace "http://ciena.com/ns/yang/ciena-ssh-types";
  
  prefix sshtypes;
  
  organization 
    "Ciena Corporation";
  
  contact
    "Web URL: http://www.ciena.com/
     E-mail:  yang@ciena.com
     Postal:  7035 Ridge Road
              Hanover, Maryland 21076
              U.S.A.
     Phone:   +1 800-921-1144
     Fax:     +1 410-694-5750";
  
  description
    "This module contains a collection of YANG type definitions for 
     SSH.

     This module contains the YANG definition of SSH.

     Copyright (c) 2016 Ciena Corporation.  All rights reserved.

     All information contained herein is, and remains
     the property of Ciena Corporation. Dissemination of this
     information or reproduction of this material is strictly
     forbidden unless prior written permission is obtained from
     Ciena Corporation.";

  revision 2023-03-29 {
    description
      "Added rsa-sha2-256 and rsa-sha2-512 public key algorithms.";

     reference
       "RFC 8332";
   }

  revision 2020-09-29 {
    description
      "Updated to add and modify existing mac-algorithms, kex-algorithms and encryption-algorithms.";

     reference
       "";
   }
  
  revision 2016-03-01 {
    description
      "Initial revision. Defines data types used by Ciena
       YANG models.";
    
     reference
       "";
   }
  
  identity mac-algo {
    description
      "Base identity from which all ssh mac algorithms are derived.";
  }

  identity hmac-sha1 {
    base mac-algo;
    description
      "The hmac-sha1 algorithm.";
  }

  identity hmac-sha1-96 {
    base mac-algo;
    description
      "The hmac-sha1-96 algorithm.";
  }

  identity hmac-sha2-256 {
    base mac-algo;
    description
      "The hmac-sha2-256 algorithm.";
  }

  identity hmac-sha2-512 {
    base mac-algo;
    description
      "The hmac-sha2-512 algorithm.";
  }

  identity hmac-md5 {
    base mac-algo;
    description
      "The hmac-md5 algorithm.";
  }

  identity hmac-md5-96 {
    base mac-algo;
    description
      "The hmac-md5-96 algorithm.";
  }

  identity umac-64-openssh.com {
    base mac-algo;
    description
      "The umac-64@openssh.com algorithm.";
  }

  identity umac-128-openssh.com {
    base mac-algo;
    description
      "The umac-128@openssh.com algorithm.";
  }

  identity hmac-sha1-etm-openssh.com {
    base mac-algo;
    description
      "The hmac-sha1-etm@openssh.com algorithm.";
  }

  identity hmac-sha1-96-etm-openssh.com {
    base mac-algo;
    description
      "The hmac-sha1-96-etm@openssh.com algorithm.";
  }

  identity hmac-sha2-256-etm-openssh.com {
    base mac-algo;
    description
      "The hmac-sha2-256-etm@openssh.com algorithm.";
  }

  identity hmac-sha2-512-etm-openssh.com {
    base mac-algo;
    description
      "The hmac-sha2-512-etm@openssh.com algorithm.";
  }

  identity hmac-md5-etm-openssh.com {
    base mac-algo;
    description
      "The hmac-md5-etm@openssh.com algorithm.";
  }

  identity hmac-md5-96-etm-openssh.com {
    base mac-algo;
    description
      "The hmac-md5-96-etm@openssh.com algorithm.";
  }

  identity umac-64-etm-openssh.com {
    base mac-algo;
    description
      "The umac-64-etm@openssh.com algorithm.";
  }

  identity umac-128-etm-openssh.com {
    base mac-algo;
    description
      "The umac-128-etm@openssh.com algorithm.";
  }

  identity kex-algo {
    description
      "Base identity from which all ssh kex algorithms are derived.";
  }

  identity curve25519-sha256 {
    base kex-algo;
    description
      "The curve25519-sha256 algorithm.";
  }

  identity curve25519-sha256-libssh.org {
    base kex-algo;
    description
      "The curve25519-sha256@libssh.org algorithm.";
  }

  identity ecdh-sha2-nistp256 {
    base kex-algo;
    description
      "The ecdh-sha2-nistp256 algorithm.";
  }

  identity ecdh-sha2-nistp384 {
    base kex-algo;
    description
      "The ecdh-sha2-nistp384 algorithm.";
  }

  identity ecdh-sha2-nistp521 {
    base kex-algo;
    description
      "The ecdh-sha2-nistp521 algorithm.";
  }

  identity diffie-hellman-group1-sha1 {
    base kex-algo;
    description
      "The diffie-hellman-group1-sha1 algorithm.";
  }

  identity diffie-hellman-group14-sha1 {
    base kex-algo;
    description
      "The diffie-hellman-group14-sha1 algorithm.";
  }

  identity diffie-hellman-group14-sha256 {
    base kex-algo;
    description
      "The diffie-hellman-group14-sha256 algorithm.";
  }

  identity diffie-hellman-group16-sha512 {
    base kex-algo;
    description
      "The diffie-hellman-group16-sha512 algorithm.";
  }

  identity diffie-hellman-group18-sha512 {
    base kex-algo;
    description
      "The diffie-hellman-group18-sha512 algorithm.";
  }

  identity diffie-hellman-group-exchange-sha1 {
    base kex-algo;
    description
      "The diffie-hellman-group-exchange-sha1 algorithm.";
  }

  identity diffie-hellman-group-exchange-sha256 {
    base kex-algo;
    description
      "The diffie-hellman-group-exchange-sha256 algorithm.";
  }

  identity encryption-algo {
    description
      "Base identity from which all ssh encryption algorithms are derived.";
  }

  identity aes128-ctr {
    base encryption-algo;
    description
      "The aes128-ctr algorithm.";
  }

  identity aes192-ctr {
    base encryption-algo;
    description
      "The aes192-ctr algorithm.";
  }

  identity aes256-ctr {
    base encryption-algo;
    description
      "The aes256-ctr algorithm.";
  }

  identity three-des-cbc {
    base encryption-algo;
    description
      "The 3des-cbc algorithm.";
  }

  identity aes128-cbc {
    base encryption-algo;
    description
      "The aes128-cbc algorithm.";
  }

  identity aes192-cbc {
    base encryption-algo;
    description
      "The aes192-cbc algorithm.";
  }

  identity aes256-cbc {
    base encryption-algo;
    description
      "The aes256-cbc algorithm.";
  }

  identity rijndael-cbc-lysator.liu.se {
    base encryption-algo;
    description
      "The rijndael-cbc@lysator.liu.se algorithm.";
  }

  identity aes128-gcm-openssh.com {
    base encryption-algo;
    description
      "The aes128-gcm@openssh.com algorithm.";
  }

  identity aes256-gcm-openssh.com {
    base encryption-algo;
    description
      "The aes256-gcm@openssh.com.";
  }

  identity chacha20-poly1305-openssh.com {
    base encryption-algo;
    description
      "The chacha20-poly1305@openssh.com algorithm.";
  }
  
  identity pka-algo {
    description
      "Base identity from which all ssh public key authentication
       algorithms are derived.";
  }

  identity ssh-dss {
    base pka-algo;
    description
      "The ssh-dss public key authentication algorithm.";
  }

  identity ssh-rsa {
    base pka-algo;
    description
      "The ssh-rsa public key authentication algorithm.";
  }

  identity ssh-ed25519 {
    base pka-algo;
    description
      "The ssh-ed25519 public key authentication algorithm.";
  }

  identity ecdsa-sha2-nistp256 {
    base pka-algo;
    description
      "The ecdsa-sha2-nistp256 public key authentication algorithm.";
  }

  identity ecdsa-sha2-nistp384 {
    base pka-algo;
    description
      "The ecdsa-sha2-nistp384 public key authentication algorithm.";
  }

  identity ecdsa-sha2-nistp521 {
    base pka-algo;
    description
      "The ecdsa-sha2-nistp521 public key authentication algorithm.";
  }

  identity rsa-sha2-256 {
    base pka-algo;
    description
      "The rsa-sha2-256 public key authentication algorithm.";
  }

  identity rsa-sha2-512 {
    base pka-algo;
    description
      "The rsa-sha2-512 public key authentication algorithm.";
  }
}
