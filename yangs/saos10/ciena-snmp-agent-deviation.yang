module ciena-snmp-agent-deviation {
  namespace "http://www.ciena.com/ns/yang/ciena-snmp-agent-deviation";
  prefix "snmp-agent-dev";

  import ietf-snmp {
    prefix "snmp";
  }

  organization
    "Ciena Corporation";
  
  contact
    "Web URL: http://www.ciena.com/
     E-mail:  yang@ciena.com
     Postal:  7035 Ridge Road
              Hanover, Maryland 21076
              U.S.A.
     Phone:   +1 800-921-1144
     Fax:     +1 410-694-5750";
  
  description
    "This YANG module defines Ciena's deviations from rfc7407.

     Copyright (c) 2018 Ciena Corporation.  All rights 
     reserved.

     All information contained herein is, and remains
     the property of Ciena Corporation. Dissemination of this 
     information or reproduction of this material is strictly 
     forbidden unless prior written permission is obtained from 
     Ciena Corporation.";
  
  revision 2023-01-11 {
    description
        "Replacing the mandatory type to false for snmp:key.";
    reference
        "No specific reference or standard available";
  }

  revision 2021-03-17 {
    description
        "Only exact can be configured in context-match as part of SNMP VACM group access CLI.
         Limiting SNMP config according to FS.
         Enabling support to fix the value of
         prefix-length to 32 for SNMP target config.
         Enabling support for not allowing special characters
         other than *, - and . for SNMP vacm view config.
         Enabling SNMPv3 config for local and remote enging-id user creation.
         Enabling read-view option as part of SNMP VACM Group Access config
         and target-tag as part of SNMP Community config";
  }

  revision 2018-01-31 {
    description 
      "Initial version";
    reference
      "[rfc7407](https://tools.ietf.org/rfc/rfc7407.txt)";
  }
  deviation /snmp:snmp/snmp:engine {
    deviate not-supported;
  }
  deviation /snmp:snmp/snmp:target/snmp:transport/snmp:tls {
    deviate not-supported;
  }
  deviation /snmp:snmp/snmp:target/snmp:transport/snmp:dtls {
    deviate not-supported;
  }
  deviation /snmp:snmp/snmp:target/snmp:transport/snmp:ssh {
    deviate not-supported;
  }
  deviation /snmp:snmp/snmp:target-params/snmp:params/snmp:tsm {
    deviate not-supported;
  }
  deviation /snmp:snmp/snmp:target-params/snmp:notify-filter-profile {
    deviate not-supported;
  }
  deviation /snmp:snmp/snmp:proxy {
    deviate not-supported;
  }
  deviation /snmp:snmp/snmp:tlstm {
    deviate not-supported;
  }
  deviation /snmp:snmp/snmp:tsm {
    deviate not-supported;
  }
  deviation /snmp:snmp/snmp:community/snmp:context {
    deviate not-supported;
  }
  deviation /snmp:snmp/snmp:community/snmp:engine-id {
    deviate not-supported;
  }
  deviation /snmp:snmp/snmp:community/snmp:name/snmp:binary-name {
    deviate not-supported;
  }
  deviation /snmp:snmp/snmp:target/snmp:mms {
    deviate not-supported;
  }
  deviation /snmp:snmp/snmp:notify-filter-profile {
    deviate not-supported;
  }
  deviation /snmp:snmp/snmp:vacm/snmp:group/snmp:access/snmp:write-view {
    deviate not-supported;
  }
  deviation /snmp:snmp/snmp:vacm/snmp:view/snmp:include {
    deviate replace {
        type string {
            pattern '[a-zA-Z0-9*.-]+';
        }
    }
  }
  deviation /snmp:snmp/snmp:vacm/snmp:view/snmp:exclude {
    deviate replace {
        type string {
            pattern '[a-zA-Z0-9*.-]+';
        }
    }
  }
  deviation /snmp:snmp/snmp:target/snmp:transport/snmp:udp/snmp:udp/snmp:prefix-length {
    deviate add {
        must ". = 32";
    }
  }
  deviation /snmp:snmp/snmp:notify {
    deviate add {
        max-elements 17;
    }
  }
  deviation /snmp:snmp/snmp:community {
    deviate add {
        max-elements 18;
    }
  }
  deviation /snmp:snmp/snmp:target-params {
    deviate add {
        max-elements 15;
    }
  }
  deviation /snmp:snmp/snmp:target {
    deviate add {
        max-elements 17;
    }
  }
  deviation /snmp:snmp/snmp:target/snmp:tag {
    deviate add {
        max-elements 2;
    }
  }
  deviation /snmp:snmp/snmp:usm/snmp:local/snmp:user {
    deviate add {
        max-elements 10;
    }
  }
  deviation /snmp:snmp/snmp:vacm/snmp:group/snmp:access/snmp:context-match {
    deviate add {
        must ". = 'exact'";
    }
  }
  deviation /snmp:snmp/snmp:usm/snmp:local/snmp:user/snmp:auth/snmp:protocol/snmp:md5/snmp:md5/snmp:key {
    deviate replace {
        mandatory false;
    }
  }
  deviation /snmp:snmp/snmp:usm/snmp:local/snmp:user/snmp:auth/snmp:protocol/snmp:sha/snmp:sha/snmp:key {
    deviate replace {
        mandatory false;
    }
  }
  deviation /snmp:snmp/snmp:usm/snmp:local/snmp:user/snmp:priv/snmp:protocol/snmp:aes/snmp:aes/snmp:key {
    deviate replace {
        mandatory false;
    }
  }
  deviation /snmp:snmp/snmp:usm/snmp:local/snmp:user/snmp:priv/snmp:protocol/snmp:des/snmp:des/snmp:key {
    deviate replace {
        mandatory false;
    }
  }
  deviation /snmp:snmp/snmp:usm/snmp:remote/snmp:user/snmp:auth/snmp:protocol/snmp:md5/snmp:md5/snmp:key {
    deviate replace {
        mandatory false;
    }
  }
  deviation /snmp:snmp/snmp:usm/snmp:remote/snmp:user/snmp:auth/snmp:protocol/snmp:sha/snmp:sha/snmp:key {
    deviate replace {
        mandatory false;
    }
  }
  deviation /snmp:snmp/snmp:usm/snmp:remote/snmp:user/snmp:priv/snmp:protocol/snmp:aes/snmp:aes/snmp:key {
    deviate replace {
        mandatory false;
    }
  }
  deviation /snmp:snmp/snmp:usm/snmp:remote/snmp:user/snmp:priv/snmp:protocol/snmp:des/snmp:des/snmp:key {
    deviate replace {
        mandatory false;
    }
  }
}
