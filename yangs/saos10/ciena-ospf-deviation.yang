module ciena-ospf-deviation {
  yang-version 1.1;
  namespace
    "http://ciena.com/ns/yang/ciena-ospf-deviation";
  prefix
    "ospf-deviation";

  import ciena-ospf {
    prefix "ospf";
  }
  
  organization
    "Ciena Corporation";

  contact
    "Web URL: http://www.ciena.com/
     E-mail:  yang@ciena.com
     Postal:  7035 Ridge Road
              Hanover, Maryland 21076
              U.S.A.
     Phone:   +1 800-921-1144
     Fax:     +1 410-694-5750";

  description
    "This YANG module defines Ciena proprietary YANG deviations
     of OSPF protocol.

     Copyright (c) 2020-2022  Ciena Corporation.  All rights
     reserved.

     All information and intellectual property contained in this
     YANG module (Specification) is, and remains the property
     of Ciena Corporation. Ciena retains all title and ownership
     in the Specification, including any revisions.

     Ciena grants all interested parties that access the
     Specification with the intent to use or distribute ('you') a
     non-exclusive, no-cost license to use and distribute
     unmodified copies of the Specification solely in connection
     with the management of Ciena products sold by or on
     behalf of Ciena, provided this copyright notice and license
     appear on all copies. Ciena may rescind or modify this
     license at any time.

     This Specification is supplied 'as is', and Ciena makes no
     warranty, either express or implied, as to the use, operation,
     condition, or performance of the Specification. You agree
     that Ciena has no liability for your use of the Specification.";

  revision "2023-03-29" {
    description
      "Removal of deviation for Secondary IP as it is supported.";
  }

  revision "2023-02-02" {
    description
      "Added deviation for Secondary IP support in OSPF";
  }
  revision "2022-07-29" {
    description
      "Initial Version of ospf deviation model.";
  }

  deviation /ospf:ospf/ospf:instance/ospf:areas/ospf:area/ospf:type/ospf:stub {
    deviate not-supported;
  }

}
