module ciena-routing {
    namespace "http://ciena.com/ns/yang/ciena-routing";
    prefix "routing";

    organization
        "Ciena Corporation";

    contact
        "Web URL: http://www.ciena.com/
         E-mail:  yang@ciena.com
         Postal:  7035 Ridge Road
                  Hanover, Maryland 21076
                      U.S.A.
         Phone:   +1 800-921-1144
         Fax:     +1 410-694-5750";

    description
        "This YANG module defines Ciena's system wide routing level configurations and states.

         Copyright (c) 2022  Ciena Corporation.  All rights
         reserved.

         All information and intellectual property contained in this
         YANG module (Specification) is, and remains the property
         of Ciena Corporation. Ciena retains all title and ownership
         in the Specification, including any revisions.

         Ciena grants all interested parties that access the
         Specification with the intent to use or distribute ('you') a
         non-exclusive, no-cost license to use and distribute
         unmodified copies of the Specification solely in connection
         with the management of Ciena products sold by or on
         behalf of Ciena, provided this copyright notice and license
         appear on all copies. Ciena may rescind or modify this
         license at any time.

         This Specification is supplied 'as is', and Ciena makes no
         warranty, either express or implied, as to the use, operation,
         condition, or performance of the Specification. You agree
         that Ciena has no liability for your use of the Specification.";

    revision "2023-01-06" {
        description
            "Added changes for IS-IS global Graceful Restart config.";
    }

    revision "2021-12-17" {
        description
            "Initial revision.
            Supports 'neighbor refresh-timer' configuration.";
    }

    container routing {
        description
            "Global routing configurations";

        container ecmp {
            description
                "ECMP configuration parameters";

            leaf enable {
                type  boolean;
                description
                    "Enable ECMP capability";
            }
        }

        container isis {
            description
                 "IS-IS configuration parameters.";

            container graceful-restart {
                 description
                      "IS-IS GR configuration parameters.";

                 leaf restart-capable {
                      type boolean;
                      default "false";
                      description
                           "Global enable/disable graceful restart capability (disabled by default).";
                 }

                 leaf helper-enable {
                      type boolean;
                      default "true";
                      description
                           "Global enable/disable graceful restart helper mode (enabled by default).";
                 }
            }
        }
   }

   container routing-state {
        config false;
        description
            "Global routing state";

        container ecmp {
            description
                "ECMP operational state";
            leaf platform-max-paths {
                type uint32;
                description
                    "Maximum ECMP paths supported.";
            }
        }
    }

    container ip {
        container neighbor {
            description
                "Neighbor related global configurations";

            leaf refresh-timer {
                type  uint32;
                units seconds;
                default "50";
                description
                    "Used to configure the ARP retry timer in seconds";
            }
        }
    }
    container ip-neighbor-state {
        config false;
        container neighbor {
            description
                "Neighbor related global configurations";

            leaf refresh-timer {
                type  uint32;
                units seconds;
                default "50";
                description
                    "Used to configure the ARP retry timer in seconds";
            }
        }
    }
}
