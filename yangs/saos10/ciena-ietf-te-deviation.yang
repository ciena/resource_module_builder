module ciena-ietf-te-deviation {
   namespace "http://ciena.com/ns/yang/ciena-ietf-te-deviation";
   prefix "ciena-te-deviation";

   import ciena-ietf-te {
      prefix ciena-te;
   }

   organization
      "Ciena Corporation";

   contact
      "Web URL: http://www.ciena.com/
       E-mail:  yang@ciena.com
       Postal:  7035 Ridge Road
                Hanover, Maryland 21076
                U.S.A.
       Phone:   +1 800-921-1144
       Fax:     +1 410-694-5750";

   description
      "This YANG module defines the deviations for Ciena's configuration of
       the TE attributes.";

   revision "2021-01-18" {
      description 
         "Initial version";
   }

   deviation /ciena-te:te/ciena-te:interfaces/ciena-te:interface/ciena-te:admin-status {
      deviate replace {
         type enumeration {
            enum up {
               description
                  "Enable TE attributes signalling over this interface.";
            }
            enum down {
               description
                  "Disable TE attributes signalling over this interface.";
            }
         }
      }
   }
}
