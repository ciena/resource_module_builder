module ciena-oam-ping-deviation {
  yang-version 1.1;
  namespace
    "http://ciena.com/ns/yang/ciena-oam-ping-deviation";
  prefix
    "oam-ping-deviation";

  import ciena-oam-ping {
    prefix "oam-ping";
  }
  
  organization
    "Ciena Corporation";

  contact
    "Web URL: http://www.ciena.com/
     E-mail:  yang@ciena.com
     Postal:  7035 Ridge Road
              Hanover, Maryland 21076
              U.S.A.
     Phone:   +1 800-921-1144
     Fax:     +1 410-694-5750";

  description
    "This YANG module defines Ciena proprietary YANG deviations
     of the IP ping and traceroute module.

     Copyright (c) 2020  Ciena Corporation.  All rights
     reserved.

     All information contained herein is, and remains the
     property of Ciena Corporation. Dissemination of this
     information or reproduction of this material is strictly
     forbidden unless prior written permission is obtained
     from Ciena Corporation.";

  revision "2021-08-19" {
    description
      "Removed deviation of reverse-fec-stack-validation";
  }

  revision "2020-01-29" {
    description
      "Initial Version of deviation ping model.";
  }


  //For RPC
  deviation /oam-ping:start-ping/oam-ping:input/oam-ping:reply-mode {
    deviate not-supported;
  }

  deviation /oam-ping:start-ping/oam-ping:input/oam-ping:traffic-class {
    deviate not-supported;
  }

  deviation /oam-ping:start-ping/oam-ping:input/oam-ping:encap {
    deviate not-supported;
  }

  //For Container oam-ping-sessions
  deviation /oam-ping:oam-ping-sessions/oam-ping:oam-ping-session/oam-ping:oam-ping-config-params/oam-ping:reply-mode {
    deviate not-supported;
  }

  deviation /oam-ping:oam-ping-sessions/oam-ping:oam-ping-session/oam-ping:oam-ping-config-params/oam-ping:traffic-class {
    deviate not-supported;
  }

  deviation /oam-ping:oam-ping-sessions/oam-ping:oam-ping-session/oam-ping:oam-ping-config-params/oam-ping:encap {
    deviate not-supported;
  }

  deviation /oam-ping:oam-ping-sessions/oam-ping:oam-ping-session/oam-ping:ping-results/oam-ping:ping-probe-results/oam-ping:ping-probe-result/oam-ping:return-sub-code {
    deviate not-supported;
  }
}
