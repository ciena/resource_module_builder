module ciena-load-balancing {
   namespace "urn:ciena:params:xml:ns:yang:ciena-pn:ciena-load-balancing";
   prefix "cn-load-bal";

   import ciena-types {
      prefix ciena;
   }

   organization
      "Ciena Corporation";

   contact
      "Web URL: http://www.ciena.com/
       E-mail:  yang@ciena.com
       Postal:  7035 Ridge Road
                Hanover, Maryland 21076
                U.S.A.
       Phone:   +1 800-921-1144
       Fax:     +1 410-694-5750";

    description
      "This YANG module defines Ciena's configurabiilty of load-balancing for ECMP and/or LAG

      Copyright (c) 2023  Ciena Corporation.  All rights
      reserved.

      All information and intellectual property contained in this
      YANG module (Specification) is, and remains the property
      of Ciena Corporation. Ciena retains all title and ownership
      in the Specification, including any revisions.

      Ciena grants all interested parties that access the
      Specification with the intent to use or distribute (you) a
      non-exclusive, no-cost license to use and distribute
      unmodified copies of the Specification solely in connection
      with the management of Ciena products sold by or on
      behalf of Ciena, provided this copyright notice and license
      appear on all copies. Ciena may rescind or modify this
      license at any time.

      This Specification is supplied 'as is', and Ciena makes no
      warranty, either express or implied, as to the use, operation,
      condition, or performance of the Specification. You agree
      that Ciena has no liability for your use of the Specification.";

   revision "2023-06-20" {
      description
         "Added load-balancing operational state";
   }

   revision "2023-05-04" {
      description
         "Initial version";
   }

   /*
    * Configuration data nodes
    */
   container load-balancing {
      leaf mpls-speculative-hashing {
         type ciena:admin-state;
         description
            "Configuration Control of Speculative Hashing for MPLS forwarded frames.
            For Example, on an LSR, if speculative-hashing is off, only the MPLS Labels will be considered for ECMP/LAG hashing.
            Whereas, if speculative-hashing is on, the payload after MPLS Labels could also be considered with some speculation
            as to what that payload is for ECMP/LAG hashing purposes.
            If speculative-hashing is on, for example, if 4 is seen in the first nibble after the MPLS labels, the payload could
            be deemed to be IPv4, if 6 is seen it could be deemed to be IPv6 and more..";
      }

      leaf lag-load-balancing-seed {
         type uint32;
         description
            "Seed value to use on this node as input to the hashing algorithm for LAG for load-balancing.";
      }
   }

   // load-balancing operational state
   container load-balancing-operational-state {
      config false;

      description
         "Load balancing operational data.";

      leaf mpls-speculative-hashing {
         type ciena:admin-state;
         description
            "The Operational value of the Speculative Hashing for MPLS forwarded frames";
      }

      leaf lag-load-balancing-seed {
         type uint32;
         description
            "Seed value that is used on this node as input to the hashing algorithm for LAG for load-balancing.";
      }
   }
}
