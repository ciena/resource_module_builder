module ciena-module{
  namespace "http://www.ciena.com/ns/yang/ciena-module";
  prefix "ciena-mod";

  import openconfig-platform {
    prefix "oc-platform";
  }

  organization
    "Ciena Corporation";

  contact
    "Web URL: http://www.ciena.com/
    E-mail:  yang@ciena.com
    Postal:  7035 Ridge Road
             Hanover, Maryland 21076
             U.S.A.
    Phone:   +1 800-921-1144
    Fax:     +1 410-694-5750";

  description
    "This YANG module defines the node
    for fru module restart.

    Copyright (c) 2019 Ciena Corporation.  All rights
    reserved.

    All information contained herein is, and remains
    the property of Ciena Corporation. Dissemination of this
    information or reproduction of this material is strictly
    forbidden unless prior written permission is obtained from
    Ciena Corporation.";

  revision 2019-01-16 {
    description
      "Initial revision with module restart RPC";
    reference
      "";
  }

  rpc module-restart {
    description
      "Request that the FRU module be reset immediately.
       A server SHOULD send an rpc reply to the client before
       FRU reset.";
    input {
      leaf name {
        type leafref {
          path "/oc-platform:components/oc-platform:component/oc-platform:name";
        }
        description
          "The name of the module component which will be reset.";
      }
      leaf type {
        type enumeration {
          enum warm {
            description
              "FRU warm restart, user traffic will not be affected";
          }
          enum cold {
            description
              "FRU cold restart, user traffic will be interrupted";
          }
        }
        default warm;
        description
          "Set the restart type for the module.";
      }
    }
  }
}
