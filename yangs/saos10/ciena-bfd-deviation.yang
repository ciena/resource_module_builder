module ciena-bfd-deviation {
  yang-version 1.1;
  namespace
    "http://ciena.com/ns/yang/ciena-bfd-deviation";
  prefix
    "bfd-deviation";

  import ciena-bfd {
    prefix "bfd";
  }
  
  organization
    "Ciena Corporation";

  contact
    "Web URL: http://www.ciena.com/
     E-mail:  yang@ciena.com
     Postal:  7035 Ridge Road
              Hanover, Maryland 21076
              U.S.A.
     Phone:   +1 800-921-1144
     Fax:     +1 410-694-5750";

  description
    "This YANG module defines Ciena proprietary YANG deviations
     of BFD protocol.

     Copyright (c) 2020-2022  Ciena Corporation.  All rights
     reserved.

     All information and intellectual property contained in this
     YANG module (Specification) is, and remains the property
     of Ciena Corporation. Ciena retains all title and ownership
     in the Specification, including any revisions.

     Ciena grants all interested parties that access the
     Specification with the intent to use or distribute ('you') a
     non-exclusive, no-cost license to use and distribute
     unmodified copies of the Specification solely in connection
     with the management of Ciena products sold by or on
     behalf of Ciena, provided this copyright notice and license
     appear on all copies. Ciena may rescind or modify this
     license at any time.

     This Specification is supplied 'as is', and Ciena makes no
     warranty, either express or implied, as to the use, operation,
     condition, or performance of the Specification. You agree
     that Ciena has no liability for your use of the Specification.";

  revision "2022-02-04" {
    description
      "Gach-type and encap is not supported for seamless BFD";
  }

  revision "2021-05-21" {
    description
      "MH BFD on IPv6 is not supported.";
  }

  revision "2020-10-17" {
    description
      "Initial Version of bfd deviation model.";
  }


  //For bfd container
  deviation /bfd:bfd/bfd:global {
    deviate add {
      must "admin-down != 'true'" {
        error-message
          "admin-down must be set to false.";
      }
    }
  }

  deviation /bfd:bfd/bfd:session-config-entry/bfd:ip/bfd:multi-hop/bfd:vrf/bfd:ipv6 {
    deviate not-supported;
  }

  deviation /bfd:bfd/bfd:session-config-entry-state/bfd:ip/bfd:multi-hop/bfd:vrf/bfd:ipv6 {
    deviate not-supported;
  }

  deviation /bfd:bfd/bfd:profiles/bfd:mpls-seamless-bfd-profile/bfd:gach-type {
    deviate not-supported;
  }

  deviation /bfd:bfd/bfd:profiles-state/bfd:mpls-seamless-bfd-profile/bfd:gach-type {
    deviate not-supported;
  }

  deviation /bfd:bfd/bfd:profiles/bfd:mpls-seamless-bfd-profile/bfd:encap {
    deviate not-supported;
  }

  deviation /bfd:bfd/bfd:profiles-state/bfd:mpls-seamless-bfd-profile/bfd:encap {
    deviate not-supported;
  }
}
