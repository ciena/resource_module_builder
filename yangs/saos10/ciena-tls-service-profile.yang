module ciena-tls-service-profile {
  namespace "http://www.ciena.com/tls/yang/ciena-tls-service-profile";
  prefix "ciena-tls-service-profile";

  import ciena-tls {
    prefix ciena-tls;

  }
  import ciena-pkix {
    prefix ciena-pkix;

  }

  organization "Ciena Corporation";

  contact
    "Web URL: http://www.ciena.com/
     E-mail:  yang@ciena.com
     Postal:  7035 Ridge Road
              Hanover, Maryland 21076
              U.S.A.
     Phone:   +1 800-921-1144
     Fax:     +1 410-694-5750";

  description
    "This YANG module defines a TLS service profile.

     Copyright (c) 2018 Ciena Corporation.  All rights 
     reserved.

     All information contained herein is, and remains
     the property of Ciena Corporation. Dissemination of this 
     information or reproduction of this material is strictly 
     forbidden unless prior written permission is obtained from 
     Ciena Corporation.";

  revision 2019-12-20 {
    description
      "Updating description text for list tls-service-profiles and
      leafs under grouping tls-service-profile";
    reference
      "No specific reference";
  }

  revision 2018-02-15 {
    description
      "Initial revision.";
    reference
      "RFC XXXX: YANG Groupings for TLS Clients and TLS Servers";

  }
  grouping tls-service-profile {
    description
      "Group of TLS profile, Certificates, and Peer Auth Profile.";
    
    leaf tls-profile-name {
      type leafref {
        path "/ciena-tls:hello-params/ciena-tls:profile-name";

      }
      description
        "The name of the hello-params profile being used.";
    }
    leaf tls-peer-auth-profile-name {
      type leafref {
        path "/ciena-pkix:pkix/ciena-pkix:peer-auth-profiles/ciena-pkix:peer-auth-profile/ciena-pkix:peer-auth-profile-name";

      }
      description
        "The name of the peer auth profile being used.";
    }
    leaf tls-certificate-name {
      type string;
      description
        "The name of certificate being used.";
    }

  }// grouping tls service profile

  list tls-service-profiles {
    key tls-service-profile-name;
    leaf tls-service-profile-name {
      type string;
      description
        "Unique string name of the TLS service profile list.";

    }
    uses tls-service-profile;
    description
      "List of TLS service profiles.";

  }
}
