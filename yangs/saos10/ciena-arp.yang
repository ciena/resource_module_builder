module ciena-arp {
    namespace   "http://ciena.com/ns/yang/ciena-arp";
    prefix "arp";

    import ietf-inet-types {
        prefix inet;
    }

    import openconfig-interfaces {
        prefix "oc-if";
    }

    organization
        "Ciena Corporation";

    contact
        "Web URL: http://www.ciena.com/
        E-mail:  yang@ciena.com
        Postal:  7035 Ridge Road
        Hanover, Maryland 21076
        U.S.A.
        Phone:   +1 800-921-1144
        Fax:     +1 410-694-5750";

    description
        "This YANG module defines Ciena's cli to manage arp

        Copyright (c) 2018-2022  Ciena Corporation.  All rights
        reserved.

        All information contained herein is, and remains the
        property of Ciena Corporation. Dissemination of this
        information or reproduction of this material is strictly
        forbidden unless prior written permission is obtained
        from Ciena Corporation.";

    revision "2022-01-11" {
        description
            "Added rpc to clear ARP/ND neighbor entries globally";
    }

    revision "2018-07-12" {
        description
            "Initial version of ciena-arp config, state and rpc yang model";
    }

    rpc arp-flush {
        input  {
            leaf interface {
                type leafref {
                    path "/oc-if:interfaces/oc-if:interface/oc-if:config/oc-if:name";
                }
                description
                    "flush arp entries for this interface.";
            }
        }
        output{
            leaf response {
                type string;
                description
                    "The response could be 'success', or the reason for arp-flush failure";
            }
        }
    }

    rpc arp-delete {
        input  {
            leaf ip-address {
                type inet:ipv4-address ;
                description
                    "Delete ARP entries for this IP address.";
            }
        }
        output {
            leaf response {
                type string;
                description
                    "The response could be 'success', or the reason for arp-delete failure";
            }
        }
    }

    rpc ip-neighbor {
        input  {
            leaf flush-all {
                type empty;
                description
                    "Flushes complete ARP/ND cache";
            }
        }
        output {
            leaf response {
                type string;
                description
                    "The response could be 'success', or the reason for ip-neighbor failure";
            }
        }
    }
}
