module ciena-ntp-deviation {
  namespace "http://www.ciena.com/ns/yang/ciena-ntp-dev";
  prefix "ciena-ntp-dev";

  import openconfig-system {
    prefix "oc-sys";
  }

  import ciena-ntp {
    prefix "ciena-ntp";
  }

  organization
    "Ciena Corporation";
  
  contact
    "Web URL: http://www.ciena.com/
     E-mail:  yang@ciena.com
     Postal:  7035 Ridge Road
              Hanover, Maryland 21076
              U.S.A.
     Phone:   +1 800-921-1144
     Fax:     +1 410-694-5750";
      
  description
    "This YANG module defines Ciena's deviations from the ciena-ntp model.

      Copyright (c) 2022 Ciena Corporation.  All rights 
      reserved.

      All information contained herein is, and remains
      the property of Ciena Corporation. Dissemination of this 
      information or reproduction of this material is strictly 
      forbidden unless prior written permission is obtained from 
      Ciena Corporation.";
  
  revision 2022-02-16 {
    description
      "Removing augmented then deviated NTP leaves
       sync-notification, auth-key and peer-server";
    reference
      "";
  }

  revision 2018-06-14 {
    description 
      "Remove deviation on multicast and authentication.";
    reference
      "";
  }

  revision 2017-11-01 {
    description 
      "Initial version";
    reference
      "RFC 6020: YANG - A Data Modeling Language for
       the Network Configuration Protocol (NETCONF).
       No specific reference; standard not available.";
  }

  deviation /oc-sys:system/ciena-ntp:ntp/ciena-ntp:associations/ciena-ntp:remote-ntp-server/ciena-ntp:server-entry/ciena-ntp:admin-state {
     deviate add {
        default enabled;
     }
  }

  deviation /oc-sys:system/ciena-ntp:ntp/ciena-ntp:authentication/ciena-ntp:auth-admin-state {
     deviate add {
        default disabled;
     }
  }
}
