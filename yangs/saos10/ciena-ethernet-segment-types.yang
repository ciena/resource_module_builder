module ciena-ethernet-segment-types {
  namespace "http://ciena.com/ns/yang/ciena-ethernet-segment-types";
  prefix "es";

  import ietf-yang-types {
    prefix "yang";
  }

  organization
      "Ciena Corporation";

  contact
      "Web URL: http://www.ciena.com/
      E-mail:  yang@ciena.com
      Postal:  7035 Ridge Road
      Hanover, Maryland 21076
      U.S.A.
      Phone:   +1 800-921-1144
      Fax:     +1 410-694-5750";

  description
      "This module contains the Ciena proprietary Ethernet-Segment YANG module.
      Copyright (c) 2022 Ciena Corporation.  All rights reserved.

      All information contained herein is, and remains
      the property of Ciena Corporation. Dissemination of this
      information or reproduction of this material is strictly
      forbidden unless prior written permission is obtained from
      Ciena Corporation.";

  revision "2022-02-17" {
    description
        "Initial version";
    reference   "";
  }

  /* Typedefs */
  typedef status-type {
    type enumeration {
      enum up {
        description "Status is up";
      }
      enum down {
        description "Status is down";
      }
    }
    description "status type";
  }

  typedef df-election-method-type {
    type enumeration {
      enum default {
        value 0;
        description "The default DF election method";
      }
      enum highest-random-weight {
        value 1;
        description "The highest random weight (HRW) method";
        reference "draft-mohanty-bess-evpn-df-election";
      }
      enum preference {
        value 2;
        description "The preference based method";
        reference "draft-rabadan-bess-evpn-pref-df";
      }
    }
    description "The DF election method type";
  }

  typedef ethernet-segment-identifier-type {
    type yang:hex-string {
      length "29";
    }
    description "10-octet Ethernet segment identifier (esi),
                 ex: 00:5a:5a:5a:5a:5a:5a:5a:5a:5a";
  }
}
