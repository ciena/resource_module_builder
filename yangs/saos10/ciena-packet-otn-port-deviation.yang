module ciena-packet-otn-port-deviation {
  namespace "http://www.ciena.com/ns/yang/ciena-packet-otn-port-dev";
  prefix port-dev;

  import ciena-packet-otn-port{
    prefix port;
  }

  import yuma-ncx {
    prefix ncx;
  }

  revision 2019-10-14 {
    description 
      "Remove the deviation of admin-state";
  }

  revision 2018-09-17 {
    description "Initial revision.";
  }

  deviation /port:otn-ports/port:ports/port:properties/port:forward-error-correction{
     deviate not-supported;
  }

  deviation /port:otn-ports/port:ports/port:properties/port:service-index{
     deviate not-supported;
  }

  deviation /port:otn-ports/port:ports/port:properties/port:service-domain-index{
     deviate not-supported;
  }

  deviation /port:otn-ports/port:ports/port:properties/port:otn/port:pre-fec-otu-sf-threshold{
     deviate not-supported;
  }

  deviation /port:otn-ports/port:ports/port:properties/port:otn/port:pre-fec-otu-sd-threshold{
     deviate not-supported;
  }

  deviation /port:otn-ports/port:ports/port:properties/port:otn/port:conditioning-type{
     deviate not-supported;
  }

  deviation /port:otn-ports/port:ports/port:channels/port:properties/port:service-index{
     deviate not-supported;
  }

  deviation /port:otn-ports/port:ports/port:channels/port:properties/port:service-domain-index{
     deviate not-supported;
  }

}
