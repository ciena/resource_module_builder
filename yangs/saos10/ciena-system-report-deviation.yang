module ciena-system-report-deviation {
  namespace "http://www.ciena.com/ns/yang/ciena-system-report-dev";
  prefix "ciena-system-report-dev";

  import ciena-system-report { prefix system-report; }

  organization
    "Ciena Corporation";

  contact
    "Web URL: http://www.ciena.com/
     E-mail:  yang@ciena.com
     Postal:  7035 Ridge Road
              Hanover, Maryland 21076
              U.S.A.
     Phone:   +1 800-921-1144
     Fax:     +1 410-694-5750";

  description
    "This YANG module defines deviations to the ciena-system-report
     yang module.

     Copyright (c) 2023 Ciena Corporation.  All rights
     reserved.

     All information and intellectual property contained in this
     YANG module (Specification) is, and remains the property
     of Ciena Corporation. Ciena retains all title and ownership
     in the Specification, including any revisions.

     Ciena grants all interested parties that access the
     Specification with the intent to use or distribute ('you') a
     non-exclusive, no-cost license to use and distribute
     unmodified copies of the Specification solely in connection
     with the management of Ciena products sold by or on
     behalf of Ciena, provided this copyright notice and license
     appear on all copies. Ciena may rescind or modify this
     license at any time.

     This Specification is supplied 'as is', and Ciena makes no
     warranty, either express or implied, as to the use, operation,
     condition, or performance of the Specification. You agree
     that Ciena has no liability for your use of the Specification.";

  revision 2023-01-11 {
    description
      "Initial revision";
    reference
      "No specific reference; standard not available.";
  }

  deviation /system-report:system-report-generate/system-report:input/system-report:tls-service-profile {
    deviate not-supported;
  }

  deviation /system-report:system-report-generate/system-report:input/system-report:file-transfer-syntax/system-report:component/system-report:filename {
     deviate not-supported;
  }

  deviation /system-report:system-report-generate/system-report:input/system-report:file-transfer-syntax/system-report:component/system-report:port {
     deviate not-supported;
  }

  deviation /system-report:system-report-upload/system-report:input/system-report:tls-service-profile {
    deviate not-supported;
  }

  deviation /system-report:system-report-upload/system-report:input/system-report:file-transfer-syntax/system-report:component/system-report:port {
     deviate not-supported;
  }
}
